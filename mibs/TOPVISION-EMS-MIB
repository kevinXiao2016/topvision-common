--*******************************************************************
--TOPVISION-EMS-MIB.my: EMS MIB file
--
--Created by Rod John
--
--Topvision      
--
--
--*******************************************************************

TOPVISION-EMS-MIB DEFINITIONS ::= BEGIN 


IMPORTS
        IpAddress,
	Unsigned32,
	Integer32, 
	Counter32,
	OBJECT-TYPE,
	TimeTicks,
	Gauge32, 
    enterprises,	
	Counter64,
	enterprises,
	MODULE-IDENTITY, 
	OBJECT-IDENTITY
                    FROM SNMPv2-SMI
        DateAndTime,
	DisplayString
                    FROM SNMPv2-TC;


--
-- Node definitions
--
	
		-- 1.3.6.1.4.1.32285
		sumaRoot OBJECT IDENTIFIER ::= { enterprises 32285 }

		
		-- 1.3.6.1.4.1.32285.11
		topvisionRoot OBJECT IDENTIFIER ::= { sumaRoot 11 }

                -- 1.3.6.1.4.1.32285.11.5
		topvisionEmsTree OBJECT IDENTIFIER ::= { topvisionRoot 5 }

	
topEmsNorthBoundIdent	OBJECT IDENTIFIER ::={ topvisionEmsTree 1 }
topEmsNorthBoundTrapObject	OBJECT IDENTIFIER ::={ topEmsNorthBoundIdent 1 } 


topEmsNorthBoundAlarmSequenceNumber OBJECT-TYPE
      SYNTAX Unsigned32
      MAX-ACCESS accessible-for-notify
      STATUS current
      DESCRIPTION
        "
        A unique sequence number for each alarm generated by ems."
      ::= { topEmsNorthBoundTrapObject 1 }


topEmsNorthBoundAlarmHost OBJECT-TYPE
      SYNTAX IpAddress
      MAX-ACCESS accessible-for-notify
      STATUS current
      DESCRIPTION
        " Alarm Host IpAddress"
      ::= { topEmsNorthBoundTrapObject 2 }



topEmsNorthBoundAlarmInstance OBJECT-TYPE
      SYNTAX OCTET STRING ( SIZE (0..256) )
      MAX-ACCESS accessible-for-notify
      STATUS current
      DESCRIPTION
        "Alarm instance, indicates the detailed managed object, which
        detects faults.
        "
      ::= { topEmsNorthBoundTrapObject 3 }


topEmsNorthBoundAlarmAdditionalText OBJECT-TYPE
      SYNTAX OCTET STRING ( SIZE (0..256) )
      MAX-ACCESS accessible-for-notify
      STATUS current
      DESCRIPTION
        "Additional info to the alarm, for further desciption of the
        alarm. The format of it shall be related to each kind alarm
        defined in alarm reference table"
      ::= { topEmsNorthBoundTrapObject 4 }


topEmsNorthBoundAlarmCode OBJECT-TYPE
      SYNTAX INTEGER (0..127)
      MAX-ACCESS accessible-for-notify
      STATUS current
      DESCRIPTION
        "Topvison EMS Alarm Code"
      ::= { topEmsNorthBoundTrapObject 5 }

 topEmsNorthBoundAlarmSeverity OBJECT-TYPE
      SYNTAX INTEGER
        {
        clear(0),
        info(1),
        warning(2),
        minor(3),
        major(4),
        serverity(5),
        critical(6)
        }
      MAX-ACCESS accessible-for-notify
      STATUS current
      DESCRIPTION
        "alarm severity"
      ::= { topEmsNorthBoundTrapObject 6 }

 topEmsNorthBoundAlarmOccurTime OBJECT-TYPE
      SYNTAX DateAndTime
      MAX-ACCESS accessible-for-notify
      STATUS current
      DESCRIPTION
        "alarm occurTime"
      ::= { topEmsNorthBoundTrapObject 7 }


topEmsNorthBoundHeartbeatLabel OBJECT IDENTIFIER ::={ topEmsNorthBoundIdent 2 } 

END
