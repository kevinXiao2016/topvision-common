--
-- SUMA-IP-ROUTE-MIB.mib
-- MIB generated by MG-SOFT Visual MIB Builder Version 4.0 Build 349
-- Tuesday, March 18, 2014 at 14:13:31
--

	SUMA-IP-ROUTE-MIB DEFINITIONS ::= BEGIN
 
		IMPORTS
			TimeTicks, IpAddress, Unsigned32, Counter64, 
			OBJECT-TYPE, OBJECT-IDENTITY			
				FROM SNMPv2-SMI
			topIPRouting
				FROM SUMA-EPONEOC-EPON-MIB			
			RowStatus, TimeStamp, DisplayString, MacAddress, TEXTUAL-CONVENTION, DateAndTime	
				FROM SNMPv2-TC;
	
--
-- Textual conventions
--

--
-- Node definitions
--		
		-- 1.3.6.1.4.1.32285.11.2.3.12.2
		 topIPRouteInfoObjects OBJECT IDENTIFIER ::= { topIPRouting 2 }

		
		-- 1.3.6.1.4.1.32285.11.2.3.12.2.1
		topIPStaticRouteConfigTable OBJECT-TYPE
			SYNTAX SEQUENCE OF TopIPStaticRouteConfigEntry
			MAX-ACCESS not-accessible
			STATUS current
			DESCRIPTION
				"The table about the infomation of IP route."
			::= { topIPRouteInfoObjects 1 }

		
		-- 1.3.6.1.4.1.32285.11.2.3.12.2.1.1
		topIPStaticRouteConfigEntry OBJECT-TYPE
			SYNTAX TopIPStaticRouteConfigEntry
			MAX-ACCESS not-accessible
			STATUS current
			DESCRIPTION
				"Entry of the IP route information."
			INDEX { topIPStaticRouteDstIpAddrIndex, topIPStaticRouteDstIpMaskIndex, topIPStaticRouteNextHopIndex }
			::= { topIPStaticRouteConfigTable 1 }

		
		TopIPStaticRouteConfigEntry ::=
			SEQUENCE { 
				topIPStaticRouteDstIpAddrIndex
					IpAddress,
				topIPStaticRouteDstIpMaskIndex
					IpAddress,
				topIPStaticRouteNextHopIndex
					IpAddress,
				topIPStaticRouteDistance
					INTEGER,
				topIPStaticRouteTrack
					INTEGER,
				topIPStaticRouteRowStatus
					RowStatus
			 }

		-- 1.3.6.1.4.1.32285.11.2.3.12.2.1.1.1
		topIPStaticRouteDstIpAddrIndex OBJECT-TYPE
			SYNTAX IpAddress
			MAX-ACCESS not-accessible
			STATUS current
			DESCRIPTION
				"This object indicates the destination
				IP address of the route-static."
			::= { topIPStaticRouteConfigEntry 1 }

		
		-- 1.3.6.1.4.1.32285.11.2.3.12.2.1.1.2
		topIPStaticRouteDstIpMaskIndex OBJECT-TYPE
			SYNTAX IpAddress
			MAX-ACCESS not-accessible
			STATUS current
			DESCRIPTION
				"This object indicates the subnet mask address of the route-static."
			::= { topIPStaticRouteConfigEntry 2 }

		
		-- 1.3.6.1.4.1.32285.11.2.3.12.2.1.1.3
		topIPStaticRouteNextHopIndex OBJECT-TYPE
			SYNTAX IpAddress
			MAX-ACCESS not-accessible
			STATUS current
			DESCRIPTION
				"The Next Hop IP Address."
			::= { topIPStaticRouteConfigEntry 3 }

		
		-- 1.3.6.1.4.1.32285.11.2.3.12.2.1.1.4
		topIPStaticRouteDistance OBJECT-TYPE
			SYNTAX INTEGER (1..255)
			MAX-ACCESS read-write
			STATUS current
			DESCRIPTION
				"This object indicates the distance of the route-static."
			DEFVAL { '1'b }
			::= { topIPStaticRouteConfigEntry 4 }

		
		-- 1.3.6.1.4.1.32285.11.2.3.12.2.1.1.5
		topIPStaticRouteTrack OBJECT-TYPE
			SYNTAX INTEGER
				{
				default(0),
				bfd(1),
				icmp(2),
				delect(3)
				}
			MAX-ACCESS read-write
			STATUS current
			DESCRIPTION
				"This object indicates the track function of the route-static."
			DEFVAL { 0 }
			::= { topIPStaticRouteConfigEntry 5 }

		
		-- 1.3.6.1.4.1.32285.11.2.3.12.2.1.1.6
		topIPStaticRouteRowStatus OBJECT-TYPE
			SYNTAX RowStatus
			MAX-ACCESS read-create
			STATUS current
			DESCRIPTION
				"Row Status. This object indicates the row status of this table:
				createAndGo(4): indicates that a row is created.
				destroy(6): indicates that a row is deleted."
			::= { topIPStaticRouteConfigEntry 6 }

		
		-- 1.3.6.1.4.1.32285.11.2.3.12.2.2
		topIPRouteBlockInfoTable OBJECT-TYPE
			SYNTAX SEQUENCE OF TopIPRouteBlockInfoEntry
			MAX-ACCESS not-accessible
			STATUS current
			DESCRIPTION
				"The table about the infomation  block of IP route."
			::= { topIPRouteInfoObjects 2 }

		
		-- 1.3.6.1.4.1.32285.11.2.3.12.2.2.1
		topIPRouteBlockInfoEntry OBJECT-TYPE
			SYNTAX TopIPRouteBlockInfoEntry
			MAX-ACCESS not-accessible
			STATUS current
			DESCRIPTION
				"The entry about the infomation  block of IP route."
			INDEX { topIPRouteBlockIndex, topIPRouteBlockProtTypeIndex }
			::= { topIPRouteBlockInfoTable 1 }

		
		TopIPRouteBlockInfoEntry ::=
			SEQUENCE { 
				topIPRouteBlockIndex
					INTEGER,
				topIPRouteBlockProtTypeIndex
					INTEGER,
				topIPRouteBlockRealCount
					INTEGER,
				topIPRouteBlockInfoList
					OCTET STRING
			 }

		-- 1.3.6.1.4.1.32285.11.2.3.12.2.2.1.1
		topIPRouteBlockIndex OBJECT-TYPE
			SYNTAX INTEGER
			MAX-ACCESS not-accessible
			STATUS current
			DESCRIPTION
				"The serial number of the route block info."
			::= { topIPRouteBlockInfoEntry 1 }

		
		-- 1.3.6.1.4.1.32285.11.2.3.12.2.2.1.2
		topIPRouteBlockProtTypeIndex OBJECT-TYPE
			SYNTAX INTEGER
				{
				all(0),
				kernel(1),
				connect(2),
				static(3),
				rip(4),
				ripng(5),
				ospf(6),
				ospf6(7),
				isis(8),
				bgp(9),
				hsls(10),
				olsr(11),
				babel(12)
				}
			MAX-ACCESS not-accessible
			STATUS current
			DESCRIPTION
				"The type of IP route protocol."
			::= { topIPRouteBlockInfoEntry 2 }

		
		-- 1.3.6.1.4.1.32285.11.2.3.12.2.2.1.3
		topIPRouteBlockRealCount OBJECT-TYPE
			SYNTAX INTEGER
			MAX-ACCESS read-only
			STATUS current
			DESCRIPTION
				"Get actual ip routing number include in the route block."
			::= { topIPRouteBlockInfoEntry 3 }

		
		-- 1.3.6.1.4.1.32285.11.2.3.12.2.2.1.4
		topIPRouteBlockInfoList OBJECT-TYPE
			SYNTAX OCTET STRING (SIZE (840))
			MAX-ACCESS read-only
			STATUS current
			DESCRIPTION
				"The route block contains detailed ip route info.
				."
			::= { topIPRouteBlockInfoEntry 4 }

		
		-- 1.3.6.1.4.1.32285.11.2.3.12.2.3
		topIPRouteFibTable OBJECT-TYPE
			SYNTAX SEQUENCE OF TopIPRouteFibEntry
			MAX-ACCESS not-accessible
			STATUS current
			DESCRIPTION
				"The table about the infomation of IP route FIB."
			::= { topIPRouteInfoObjects 3 }

		
		-- 1.3.6.1.4.1.32285.11.2.3.12.2.3.1
		topIPRouteFibEntry OBJECT-TYPE
			SYNTAX TopIPRouteFibEntry
			MAX-ACCESS not-accessible
			STATUS current
			DESCRIPTION
				"The entry about the infomation of IP route FIB."
			INDEX { topIPRouteFibDstIpAddrIndex, topIPRouteFibDstIpMaskIndex, topIPRouteFibNextHopAddrIndex }
			::= { topIPRouteFibTable 1 }

		
		TopIPRouteFibEntry ::=
			SEQUENCE { 
				topIPRouteFibDstIpAddrIndex
					IpAddress,
				topIPRouteFibDstIpMaskIndex
					IpAddress,
				topIPRouteFibNextHopAddrIndex
					IpAddress,
				topIPRouteFibProtType
					INTEGER
			 }

		-- 1.3.6.1.4.1.32285.11.2.3.12.2.3.1.1
		topIPRouteFibDstIpAddrIndex OBJECT-TYPE
			SYNTAX IpAddress
			MAX-ACCESS not-accessible
			STATUS current
			DESCRIPTION
				"This object indicates the destination
				IP address of the route FIB."
			::= { topIPRouteFibEntry 1 }

		
		-- 1.3.6.1.4.1.32285.11.2.3.12.2.3.1.2
		topIPRouteFibDstIpMaskIndex OBJECT-TYPE
			SYNTAX IpAddress
			MAX-ACCESS not-accessible
			STATUS current
			DESCRIPTION
				"This object indicates the subnet mask address of the route FIB."
			::= { topIPRouteFibEntry 2 }

		
		-- 1.3.6.1.4.1.32285.11.2.3.12.2.3.1.3
		topIPRouteFibNextHopAddrIndex OBJECT-TYPE
			SYNTAX IpAddress
			MAX-ACCESS not-accessible
			STATUS current
			DESCRIPTION
				"Get actual nex-hop number from the route FIB."
			::= { topIPRouteFibEntry 3 }

		
		-- 1.3.6.1.4.1.32285.11.2.3.12.2.3.1.4
		topIPRouteFibProtType OBJECT-TYPE
			SYNTAX INTEGER
				{
				kernel(1),
				connect(2),
				static(3),
				rip(4),
				ripng(5),
				ospf(6),
				ospf6(7),
				isis(8),
				bgp(9),
				hsls(10),
				olsr(11),
				babel(12)
				}
			MAX-ACCESS read-only
			STATUS current
			DESCRIPTION
				"The type of IP route protocol.every byte maybe be assigned value.such as 1(host),2(static),3(isis),4(ospf),5(direct)."
			::= { topIPRouteFibEntry 4 }

	
	END

	
--
-- SUMA-IP-ROUTE-MIB.mib
--
