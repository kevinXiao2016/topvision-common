--
-- SUMA-VOIP-MIB.mib
-- MIB generated by MG-SOFT Visual MIB Builder Version 4.0 Build 349
-- Tuesday, June 27, 2017 at 11:44:03
--

--  SUMA-VOIP-MIB.my
-- MIB generated by MG-SOFT Visual MIB Builder Version 4.0 Build 349
-- Monday, June 19, 2017 at 15:16:33
-- 
--  SUMA-GPON-MIB.my
-- MIB generated by MG-SOFT Visual MIB Builder Version 4.0 Build 349
-- Tuesday, December 20, 2016 at 09:00:41
-- 
--  SUMA-GPON-MIB.my
-- MIB generated by MG-SOFT Visual MIB Builder Version 4.0 Build 349
-- Monday, December 19, 2016 at 14:05:25
-- 
--  SUMA-GPON-MIB.my
-- MIB generated by MG-SOFT Visual MIB Builder Version 4.0 Build 349
-- Sunday, December 18, 2016 at 14:46:38
-- 
--  SUMA-GPON-MIB.mib
-- MIB generated by MG-SOFT Visual MIB Builder Version 4.0 Build 349
-- Wednesday, October 19, 2011 at 15:54:31
-- 

	SUMA-VOIP-MIB DEFINITIONS ::= BEGIN
 
		IMPORTS
			enterprises, IpAddress, Unsigned32, OBJECT-TYPE			
				FROM SNMPv2-SMI			
			RowStatus, TEXTUAL-CONVENTION			
				FROM SNMPv2-TC;
	
	
--
-- Textual conventions
--
	
--  Textual conventions
-- 
-- Textual conventions
-- 
-- Textual conventions
-- 
-- Textual conventions
-- 
		TopGPonSlotIndex ::= TEXTUAL-CONVENTION
			STATUS current
			DESCRIPTION 
				"This represents the slot number in the epon shelf."
			SYNTAX INTEGER (1..18)

		TopGPonPonIndex ::= TEXTUAL-CONVENTION
			STATUS current
			DESCRIPTION 
				"This represents the PON number in the epon board."
			SYNTAX INTEGER (1..8)

		TopGPonOnuAuthNum ::= TEXTUAL-CONVENTION
			STATUS current
			DESCRIPTION 
				"This represents the ONU auth number in the epon board."
			SYNTAX INTEGER (1..128)

		TopGPonUniPortIndex ::= TEXTUAL-CONVENTION
			STATUS current
			DESCRIPTION 
				"This represents the ONU uni number in the epon board."
			SYNTAX INTEGER (1..32)

		TopGPonSniIndex ::= TEXTUAL-CONVENTION
			STATUS current
			DESCRIPTION 
				"This represents the sni port number in the uplink board."
			SYNTAX INTEGER (1..8)

		TopGPonDeviceIndex ::= TEXTUAL-CONVENTION
			STATUS current
			DESCRIPTION 
				"From MSB on, OLT slot index-8bits, PON/SNI port-8bits, 
				OnuNUM-8bits and UNI port-8bits.
				OLT PON/SNI Port - OnuNum and UNI port shall be set to 0."
			SYNTAX Unsigned32

	
--
-- Node definitions
--
	
--  Node definitions
-- 
-- Node definitions
-- 
-- Textual conventions
-- 
-- Node definitions
-- 1.3.6.1.4.1.32285
-- 1.3.6.1.4.1.32285
		-- 1.3.6.1.4.1.32285
		sumaRoot OBJECT IDENTIFIER ::= { enterprises 32285 }

		
--   1.3.6.1.4.1.32285.11
-- 1.3.6.1.4.1.32285.11
		-- 1.3.6.1.4.1.32285.11
		topvisionRoot OBJECT IDENTIFIER ::= { sumaRoot 11 }

		
--   1.3.6.1.4.1.32285.11.6
-- 1.3.6.1.4.1.32285.11.6
		-- 1.3.6.1.4.1.32285.11.6
		topvisionVoipTree OBJECT IDENTIFIER ::= { topvisionRoot 6 }

		
--   1.3.6.1.4.1.32285.11.6.1
-- 1.3.6.1.4.1.32285.11.6.1
		-- 1.3.6.1.4.1.32285.11.6.1
		topSIPProfileObjects OBJECT IDENTIFIER ::= { topvisionVoipTree 1 }

		
--   1.3.6.1.4.1.32285.11.6.1.1
-- 1.3.6.1.4.1.32285.11.6.1.1
		-- 1.3.6.1.4.1.32285.11.6.1.1
		topSIPAgentProfInfoTable OBJECT-TYPE
			SYNTAX SEQUENCE OF TopSIPAgentProfInfoEntry
			MAX-ACCESS not-accessible
			STATUS current
			DESCRIPTION
				"Description."
			::= { topSIPProfileObjects 1 }

		
--   1.3.6.1.4.1.32285.11.6.1.1.1
-- 1.3.6.1.4.1.32285.11.6.1.1.1
		-- 1.3.6.1.4.1.32285.11.6.1.1.1
		topSIPAgentProfInfoEntry OBJECT-TYPE
			SYNTAX TopSIPAgentProfInfoEntry
			MAX-ACCESS not-accessible
			STATUS current
			DESCRIPTION
				"Description."
			INDEX { topSIPAgtProfIdx }
			::= { topSIPAgentProfInfoTable 1 }

		
		TopSIPAgentProfInfoEntry ::=
			SEQUENCE { 
				topSIPAgtProfIdx
					INTEGER,
				topSIPAgtProfName
					OCTET STRING,
				topSIPAgtProxyAddr
					OCTET STRING,
				topSIPAgtProxyPort
					INTEGER,
				topSIPAgtSecProxyAddr
					OCTET STRING,
				topSIPAgtSecProxyPort
					INTEGER,
				topSIPAgtOutboundAddr
					OCTET STRING,
				topSIPAgtOutboundPort
					INTEGER,
				topSIPAgtSecOutboundAddr
					OCTET STRING,
				topSIPAgtSecOutboundPort
					INTEGER,
				topSIPAgtSignalTransMod
					INTEGER,
				topSIPAgtSignalPort
					INTEGER,
				topSIPAgtSignalDscp
					INTEGER,
				topSIPAgtRegAddr
					OCTET STRING,
				topSIPAgtRegPort
					INTEGER,
				topSIPAgtSecRegAddr
					OCTET STRING,
				topSIPAgtSecRegPort
					INTEGER,
				topSIPAgtReqExpTime
					INTEGER,
				topSIPAgtRereqHdStartTime
					INTEGER,
				topSIPAgtHeartBeatMode
					INTEGER,
				topSIPAgtHeartBeatCycle
					INTEGER,
				topSIPAgtHeartBeatCnt
					INTEGER,
				topSIPAgtServType
					INTEGER,
				topSIPAgtBindCnt
					INTEGER,
				topSIPAgtRowStatus
					RowStatus
			 }

--   1.3.6.1.4.1.32285.11.6.1.1.1.1
-- 1.3.6.1.4.1.32285.11.6.1.1.1.1
		-- 1.3.6.1.4.1.32285.11.6.1.1.1.1
		topSIPAgtProfIdx OBJECT-TYPE
			SYNTAX INTEGER (1..64)
			MAX-ACCESS not-accessible
			STATUS current
			DESCRIPTION
				"Description."
			::= { topSIPAgentProfInfoEntry 1 }

		
--   1.3.6.1.4.1.32285.11.6.1.1.1.2
-- 1.3.6.1.4.1.32285.11.6.1.1.1.2
		-- 1.3.6.1.4.1.32285.11.6.1.1.1.2
		topSIPAgtProfName OBJECT-TYPE
			SYNTAX OCTET STRING (SIZE (1..31))
			MAX-ACCESS read-write
			STATUS current
			DESCRIPTION
				"Description."
			::= { topSIPAgentProfInfoEntry 2 }

		
--   1.3.6.1.4.1.32285.11.6.1.1.1.3
-- 1.3.6.1.4.1.32285.11.6.1.1.1.3
		-- 1.3.6.1.4.1.32285.11.6.1.1.1.3
		topSIPAgtProxyAddr OBJECT-TYPE
			SYNTAX OCTET STRING (SIZE (0..63))
			MAX-ACCESS read-write
			STATUS current
			DESCRIPTION
				"Description."
			::= { topSIPAgentProfInfoEntry 3 }

		
--   1.3.6.1.4.1.32285.11.6.1.1.1.4
-- 1.3.6.1.4.1.32285.11.6.1.1.1.4
		-- 1.3.6.1.4.1.32285.11.6.1.1.1.4
		topSIPAgtProxyPort OBJECT-TYPE
			SYNTAX INTEGER (0..65535)
			MAX-ACCESS read-write
			STATUS current
			DESCRIPTION
				"Description."
			DEFVAL { 0 }
			::= { topSIPAgentProfInfoEntry 4 }

		
--   1.3.6.1.4.1.32285.11.6.1.1.1.5
-- 1.3.6.1.4.1.32285.11.6.1.1.1.5
		-- 1.3.6.1.4.1.32285.11.6.1.1.1.5
		topSIPAgtSecProxyAddr OBJECT-TYPE
			SYNTAX OCTET STRING (SIZE (0..63))
			MAX-ACCESS read-write
			STATUS current
			DESCRIPTION
				"Description."
			::= { topSIPAgentProfInfoEntry 5 }

		
--   1.3.6.1.4.1.32285.11.6.1.1.1.6
-- 1.3.6.1.4.1.32285.11.6.1.1.1.6
		-- 1.3.6.1.4.1.32285.11.6.1.1.1.6
		topSIPAgtSecProxyPort OBJECT-TYPE
			SYNTAX INTEGER (0..65535)
			MAX-ACCESS read-write
			STATUS current
			DESCRIPTION
				"Description."
			DEFVAL { 0 }
			::= { topSIPAgentProfInfoEntry 6 }

		
--   1.3.6.1.4.1.32285.11.6.1.1.1.7
-- 1.3.6.1.4.1.32285.11.6.1.1.1.7
		-- 1.3.6.1.4.1.32285.11.6.1.1.1.7
		topSIPAgtOutboundAddr OBJECT-TYPE
			SYNTAX OCTET STRING (SIZE (0..63))
			MAX-ACCESS read-write
			STATUS current
			DESCRIPTION
				"Description."
			::= { topSIPAgentProfInfoEntry 7 }

		
--   1.3.6.1.4.1.32285.11.6.1.1.1.8
-- 1.3.6.1.4.1.32285.11.6.1.1.1.8
		-- 1.3.6.1.4.1.32285.11.6.1.1.1.8
		topSIPAgtOutboundPort OBJECT-TYPE
			SYNTAX INTEGER (0..65535)
			MAX-ACCESS read-write
			STATUS current
			DESCRIPTION
				"Description."
			DEFVAL { 0 }
			::= { topSIPAgentProfInfoEntry 8 }

		
--   1.3.6.1.4.1.32285.11.6.1.1.1.9
-- 1.3.6.1.4.1.32285.11.6.1.1.1.9
		-- 1.3.6.1.4.1.32285.11.6.1.1.1.9
		topSIPAgtSecOutboundAddr OBJECT-TYPE
			SYNTAX OCTET STRING (SIZE (0..63))
			MAX-ACCESS read-write
			STATUS current
			DESCRIPTION
				"Description."
			::= { topSIPAgentProfInfoEntry 9 }

		
--   1.3.6.1.4.1.32285.11.6.1.1.1.10
-- 1.3.6.1.4.1.32285.11.6.1.1.1.10
		-- 1.3.6.1.4.1.32285.11.6.1.1.1.10
		topSIPAgtSecOutboundPort OBJECT-TYPE
			SYNTAX INTEGER (0..65535)
			MAX-ACCESS read-write
			STATUS current
			DESCRIPTION
				"Description."
			DEFVAL { 0 }
			::= { topSIPAgentProfInfoEntry 10 }

		
--   1.3.6.1.4.1.32285.11.6.1.1.1.11
-- 1.3.6.1.4.1.32285.11.6.1.1.1.11
		-- 1.3.6.1.4.1.32285.11.6.1.1.1.11
		topSIPAgtSignalTransMod OBJECT-TYPE
			SYNTAX INTEGER
				{
				udp(1),
				tcp(2)
				}
			MAX-ACCESS read-write
			STATUS current
			DESCRIPTION
				"Description."
			DEFVAL { udp }
			::= { topSIPAgentProfInfoEntry 11 }

		
--   1.3.6.1.4.1.32285.11.6.1.1.1.12
-- 1.3.6.1.4.1.32285.11.6.1.1.1.12
		-- 1.3.6.1.4.1.32285.11.6.1.1.1.12
		topSIPAgtSignalPort OBJECT-TYPE
			SYNTAX INTEGER (0..65535)
			MAX-ACCESS read-write
			STATUS current
			DESCRIPTION
				"Description."
			DEFVAL { 5070 }
			::= { topSIPAgentProfInfoEntry 12 }

		
--   1.3.6.1.4.1.32285.11.6.1.1.1.13
-- 1.3.6.1.4.1.32285.11.6.1.1.1.13
		-- 1.3.6.1.4.1.32285.11.6.1.1.1.13
		topSIPAgtSignalDscp OBJECT-TYPE
			SYNTAX INTEGER (0..63)
			MAX-ACCESS read-write
			STATUS current
			DESCRIPTION
				"Description."
			DEFVAL { 46 }
			::= { topSIPAgentProfInfoEntry 13 }

		
--   1.3.6.1.4.1.32285.11.6.1.1.1.14
-- 1.3.6.1.4.1.32285.11.6.1.1.1.14
		-- 1.3.6.1.4.1.32285.11.6.1.1.1.14
		topSIPAgtRegAddr OBJECT-TYPE
			SYNTAX OCTET STRING (SIZE (0..63))
			MAX-ACCESS read-write
			STATUS current
			DESCRIPTION
				"Description."
			::= { topSIPAgentProfInfoEntry 14 }

		
--   1.3.6.1.4.1.32285.11.6.1.1.1.15
-- 1.3.6.1.4.1.32285.11.6.1.1.1.15
		-- 1.3.6.1.4.1.32285.11.6.1.1.1.15
		topSIPAgtRegPort OBJECT-TYPE
			SYNTAX INTEGER (0..65535)
			MAX-ACCESS read-write
			STATUS current
			DESCRIPTION
				"Description."
			DEFVAL { 0 }
			::= { topSIPAgentProfInfoEntry 15 }

		
--   1.3.6.1.4.1.32285.11.6.1.1.1.16
-- 1.3.6.1.4.1.32285.11.6.1.1.1.16
		-- 1.3.6.1.4.1.32285.11.6.1.1.1.16
		topSIPAgtSecRegAddr OBJECT-TYPE
			SYNTAX OCTET STRING (SIZE (0..63))
			MAX-ACCESS read-write
			STATUS current
			DESCRIPTION
				"Description."
			::= { topSIPAgentProfInfoEntry 16 }

		
--   1.3.6.1.4.1.32285.11.6.1.1.1.17
-- 1.3.6.1.4.1.32285.11.6.1.1.1.17
		-- 1.3.6.1.4.1.32285.11.6.1.1.1.17
		topSIPAgtSecRegPort OBJECT-TYPE
			SYNTAX INTEGER (0..65535)
			MAX-ACCESS read-write
			STATUS current
			DESCRIPTION
				"Description."
			DEFVAL { 0 }
			::= { topSIPAgentProfInfoEntry 17 }

		
--   1.3.6.1.4.1.32285.11.6.1.1.1.18
-- 1.3.6.1.4.1.32285.11.6.1.1.1.18
		-- 1.3.6.1.4.1.32285.11.6.1.1.1.18
		topSIPAgtReqExpTime OBJECT-TYPE
			SYNTAX INTEGER (1..65534)
			UNITS "s"
			MAX-ACCESS read-write
			STATUS current
			DESCRIPTION
				"Description."
			DEFVAL { 600 }
			::= { topSIPAgentProfInfoEntry 18 }

		
--   1.3.6.1.4.1.32285.11.6.1.1.1.19
-- 1.3.6.1.4.1.32285.11.6.1.1.1.19
		-- 1.3.6.1.4.1.32285.11.6.1.1.1.19
		topSIPAgtRereqHdStartTime OBJECT-TYPE
			SYNTAX INTEGER (1..65534)
			UNITS "s"
			MAX-ACCESS read-write
			STATUS current
			DESCRIPTION
				"Description."
			DEFVAL { 300 }
			::= { topSIPAgentProfInfoEntry 19 }

		
--   1.3.6.1.4.1.32285.11.6.1.1.1.20
-- 1.3.6.1.4.1.32285.11.6.1.1.1.20
		-- 1.3.6.1.4.1.32285.11.6.1.1.1.20
		topSIPAgtHeartBeatMode OBJECT-TYPE
			SYNTAX INTEGER
				{
				disable(0),
				enable(1)
				}
			MAX-ACCESS read-write
			STATUS current
			DESCRIPTION
				"Description."
			DEFVAL { disable }
			::= { topSIPAgentProfInfoEntry 20 }

		
--   1.3.6.1.4.1.32285.11.6.1.1.1.21
-- 1.3.6.1.4.1.32285.11.6.1.1.1.21
		-- 1.3.6.1.4.1.32285.11.6.1.1.1.21
		topSIPAgtHeartBeatCycle OBJECT-TYPE
			SYNTAX INTEGER (1..1000)
			UNITS "s"
			MAX-ACCESS read-write
			STATUS current
			DESCRIPTION
				"Description."
			DEFVAL { 60 }
			::= { topSIPAgentProfInfoEntry 21 }

		
--   1.3.6.1.4.1.32285.11.6.1.1.1.22
-- 1.3.6.1.4.1.32285.11.6.1.1.1.22
		-- 1.3.6.1.4.1.32285.11.6.1.1.1.22
		topSIPAgtHeartBeatCnt OBJECT-TYPE
			SYNTAX INTEGER (1..30)
			MAX-ACCESS read-write
			STATUS current
			DESCRIPTION
				"Description."
			DEFVAL { 3 }
			::= { topSIPAgentProfInfoEntry 22 }

		
--   1.3.6.1.4.1.32285.11.6.1.1.1.23
-- 1.3.6.1.4.1.32285.11.6.1.1.1.23
		-- 1.3.6.1.4.1.32285.11.6.1.1.1.23
		topSIPAgtServType OBJECT-TYPE
			SYNTAX INTEGER
				{
				sip(1),
				ims(2)
				}
			MAX-ACCESS read-write
			STATUS current
			DESCRIPTION
				"Description."
			DEFVAL { sip }
			::= { topSIPAgentProfInfoEntry 23 }

		
--   1.3.6.1.4.1.32285.11.6.1.1.1.24
-- 1.3.6.1.4.1.32285.11.6.1.1.1.24
		-- 1.3.6.1.4.1.32285.11.6.1.1.1.24
		topSIPAgtBindCnt OBJECT-TYPE
			SYNTAX INTEGER
			MAX-ACCESS read-only
			STATUS current
			DESCRIPTION
				"Description."
			::= { topSIPAgentProfInfoEntry 24 }

		
--   1.3.6.1.4.1.32285.11.6.1.1.1.25
-- 1.3.6.1.4.1.32285.11.6.1.1.1.25
		-- 1.3.6.1.4.1.32285.11.6.1.1.1.25
		topSIPAgtRowStatus OBJECT-TYPE
			SYNTAX RowStatus
			MAX-ACCESS read-create
			STATUS current
			DESCRIPTION
				"Description."
			::= { topSIPAgentProfInfoEntry 25 }

		
--  1.3.6.1.4.1.32285.11.6.1.2
		-- 1.3.6.1.4.1.32285.11.6.1.2
		topVoipMediaProfInfoTable OBJECT-TYPE
			SYNTAX SEQUENCE OF TopVoipMediaProfInfoEntry
			MAX-ACCESS not-accessible
			STATUS current
			DESCRIPTION
				"Description."
			::= { topSIPProfileObjects 2 }

		
--  1.3.6.1.4.1.32285.11.6.1.2.1
		-- 1.3.6.1.4.1.32285.11.6.1.2.1
		topVoipMediaProfInfoEntry OBJECT-TYPE
			SYNTAX TopVoipMediaProfInfoEntry
			MAX-ACCESS not-accessible
			STATUS current
			DESCRIPTION
				"Description.Voip media profile"
			INDEX { topVoipMediaProfIdx }
			::= { topVoipMediaProfInfoTable 1 }

		
		TopVoipMediaProfInfoEntry ::=
			SEQUENCE { 
				topVoipMediaProfIdx
					INTEGER,
				topVoipMediaProfName
					OCTET STRING,
				topVoipMediaFaxmode
					INTEGER,
				topVoipMediaNegotiate
					INTEGER,
				topVoipMediaBindCnt
					INTEGER,
				topVoipMediaRowStatus
					RowStatus
			 }

--  1.3.6.1.4.1.32285.11.6.1.2.1.1
		-- 1.3.6.1.4.1.32285.11.6.1.2.1.1
		topVoipMediaProfIdx OBJECT-TYPE
			SYNTAX INTEGER (1..64)
			MAX-ACCESS not-accessible
			STATUS current
			DESCRIPTION
				"Description."
			::= { topVoipMediaProfInfoEntry 1 }

		
--  1.3.6.1.4.1.32285.11.6.1.2.1.2
		-- 1.3.6.1.4.1.32285.11.6.1.2.1.2
		topVoipMediaProfName OBJECT-TYPE
			SYNTAX OCTET STRING (SIZE (1..31))
			MAX-ACCESS read-write
			STATUS current
			DESCRIPTION
				"Description.default: onu_voipmedia_profile_xx"
			::= { topVoipMediaProfInfoEntry 2 }

		
--  1.3.6.1.4.1.32285.11.6.1.2.1.3
		-- 1.3.6.1.4.1.32285.11.6.1.2.1.3
		topVoipMediaFaxmode OBJECT-TYPE
			SYNTAX INTEGER
				{
				passthru(0),
				t38(1)
				}
			MAX-ACCESS read-write
			STATUS current
			DESCRIPTION
				"Description.0 - Passthru  1 - T.38"
			DEFVAL { t38 }
			::= { topVoipMediaProfInfoEntry 3 }

		
--  1.3.6.1.4.1.32285.11.6.1.2.1.4
		-- 1.3.6.1.4.1.32285.11.6.1.2.1.4
		topVoipMediaNegotiate OBJECT-TYPE
			SYNTAX INTEGER
				{
				negotiate(0),
				self-switch(1)
				}
			MAX-ACCESS read-write
			STATUS current
			DESCRIPTION
				"Description."
			DEFVAL { negotiate }
			::= { topVoipMediaProfInfoEntry 4 }

		
--  1.3.6.1.4.1.32285.11.6.1.2.1.5
		-- 1.3.6.1.4.1.32285.11.6.1.2.1.5
		topVoipMediaBindCnt OBJECT-TYPE
			SYNTAX INTEGER
			MAX-ACCESS read-only
			STATUS current
			DESCRIPTION
				"Description."
			::= { topVoipMediaProfInfoEntry 5 }

		
--  1.3.6.1.4.1.32285.11.6.1.2.1.6
		-- 1.3.6.1.4.1.32285.11.6.1.2.1.6
		topVoipMediaRowStatus OBJECT-TYPE
			SYNTAX RowStatus
			MAX-ACCESS read-create
			STATUS current
			DESCRIPTION
				"Description."
			::= { topVoipMediaProfInfoEntry 6 }

		
--  1.3.6.1.4.1.32285.11.6.1.3
		-- 1.3.6.1.4.1.32285.11.6.1.3
		topSIPSrvProfInfoTable OBJECT-TYPE
			SYNTAX SEQUENCE OF TopSIPSrvProfInfoEntry
			MAX-ACCESS not-accessible
			STATUS current
			DESCRIPTION
				"Description."
			::= { topSIPProfileObjects 3 }

		
--  1.3.6.1.4.1.32285.11.6.1.3.1
		-- 1.3.6.1.4.1.32285.11.6.1.3.1
		topSIPSrvProfInfoEntry OBJECT-TYPE
			SYNTAX TopSIPSrvProfInfoEntry
			MAX-ACCESS not-accessible
			STATUS current
			DESCRIPTION
				"Description."
			INDEX { topSIPSrvProfIdx }
			::= { topSIPSrvProfInfoTable 1 }

		
		TopSIPSrvProfInfoEntry ::=
			SEQUENCE { 
				topSIPSrvProfIdx
					INTEGER,
				topSIPSrvProfName
					OCTET STRING,
				topSIPSrvProfCallWait
					INTEGER,
				topSIPSrvProf3Way
					INTEGER,
				topSIPSrvProfCallTransfer
					INTEGER,
				topSIPSrvProfCallHold
					INTEGER,
				topSIPSrvProfCallPark
					INTEGER,
				topSIPSrvProfDND
					INTEGER,
				topSIPSrvProfMWI
					INTEGER,
				topSIPSrvProfHotline
					INTEGER,
				topSIPSrvProfHotlineNum
					OCTET STRING,
				topSIPSrvProfHotDelay
					INTEGER,
				topSIPSrvProfBindCnt
					INTEGER,
				topSIPSrvProfRowStatus
					RowStatus
			 }

--  1.3.6.1.4.1.32285.11.6.1.3.1.1
		-- 1.3.6.1.4.1.32285.11.6.1.3.1.1
		topSIPSrvProfIdx OBJECT-TYPE
			SYNTAX INTEGER (1..64)
			MAX-ACCESS read-write
			STATUS current
			DESCRIPTION
				"Description."
			::= { topSIPSrvProfInfoEntry 1 }

		
--  1.3.6.1.4.1.32285.11.6.1.3.1.2
		-- 1.3.6.1.4.1.32285.11.6.1.3.1.2
		topSIPSrvProfName OBJECT-TYPE
			SYNTAX OCTET STRING (SIZE (1..31))
			MAX-ACCESS read-write
			STATUS current
			DESCRIPTION
				"Description.default:onu_sipsrv_profile_xx"
			::= { topSIPSrvProfInfoEntry 2 }

		
--  1.3.6.1.4.1.32285.11.6.1.3.1.3
		-- 1.3.6.1.4.1.32285.11.6.1.3.1.3
		topSIPSrvProfCallWait OBJECT-TYPE
			SYNTAX INTEGER
				{
				enable(1),
				disable(2)
				}
			MAX-ACCESS read-write
			STATUS current
			DESCRIPTION
				"Description."
			DEFVAL { enable }
			::= { topSIPSrvProfInfoEntry 3 }

		
--  1.3.6.1.4.1.32285.11.6.1.3.1.4
		-- 1.3.6.1.4.1.32285.11.6.1.3.1.4
		topSIPSrvProf3Way OBJECT-TYPE
			SYNTAX INTEGER
				{
				enable(1),
				disable(2)
				}
			MAX-ACCESS read-write
			STATUS current
			DESCRIPTION
				"Description."
			DEFVAL { enable }
			::= { topSIPSrvProfInfoEntry 4 }

		
--  1.3.6.1.4.1.32285.11.6.1.3.1.5
		-- 1.3.6.1.4.1.32285.11.6.1.3.1.5
		topSIPSrvProfCallTransfer OBJECT-TYPE
			SYNTAX INTEGER
				{
				enable(1),
				disable(2)
				}
			MAX-ACCESS read-write
			STATUS current
			DESCRIPTION
				"Description."
			DEFVAL { disable }
			::= { topSIPSrvProfInfoEntry 5 }

		
--  1.3.6.1.4.1.32285.11.6.1.3.1.6
		-- 1.3.6.1.4.1.32285.11.6.1.3.1.6
		topSIPSrvProfCallHold OBJECT-TYPE
			SYNTAX INTEGER
				{
				enable(1),
				disable(2)
				}
			MAX-ACCESS read-write
			STATUS current
			DESCRIPTION
				"Description."
			DEFVAL { enable }
			::= { topSIPSrvProfInfoEntry 6 }

		
--  1.3.6.1.4.1.32285.11.6.1.3.1.7
		-- 1.3.6.1.4.1.32285.11.6.1.3.1.7
		topSIPSrvProfCallPark OBJECT-TYPE
			SYNTAX INTEGER
				{
				disable(0),
				enable(1)
				}
			MAX-ACCESS read-write
			STATUS current
			DESCRIPTION
				"Description."
			DEFVAL { disable }
			::= { topSIPSrvProfInfoEntry 7 }

		
--  1.3.6.1.4.1.32285.11.6.1.3.1.8
		-- 1.3.6.1.4.1.32285.11.6.1.3.1.8
		topSIPSrvProfDND OBJECT-TYPE
			SYNTAX INTEGER
				{
				enable(1),
				disable(2)
				}
			MAX-ACCESS read-write
			STATUS current
			DESCRIPTION
				"Description."
			DEFVAL { disable }
			::= { topSIPSrvProfInfoEntry 8 }

		
--  1.3.6.1.4.1.32285.11.6.1.3.1.9
		-- 1.3.6.1.4.1.32285.11.6.1.3.1.9
		topSIPSrvProfMWI OBJECT-TYPE
			SYNTAX INTEGER
				{
				enable(1),
				disable(2)
				}
			MAX-ACCESS read-write
			STATUS current
			DESCRIPTION
				"Description."
			DEFVAL { disable }
			::= { topSIPSrvProfInfoEntry 9 }

		
--  1.3.6.1.4.1.32285.11.6.1.3.1.10
		-- 1.3.6.1.4.1.32285.11.6.1.3.1.10
		topSIPSrvProfHotline OBJECT-TYPE
			SYNTAX INTEGER
				{
				enable(1),
				disable(2)
				}
			MAX-ACCESS read-write
			STATUS current
			DESCRIPTION
				"Description."
			DEFVAL { disable }
			::= { topSIPSrvProfInfoEntry 10 }

		
--  1.3.6.1.4.1.32285.11.6.1.3.1.11
		-- 1.3.6.1.4.1.32285.11.6.1.3.1.11
		topSIPSrvProfHotlineNum OBJECT-TYPE
			SYNTAX OCTET STRING (SIZE (1..32))
			MAX-ACCESS read-write
			STATUS current
			DESCRIPTION
				"Description."
			::= { topSIPSrvProfInfoEntry 11 }

		
--  1.3.6.1.4.1.32285.11.6.1.3.1.12
		-- 1.3.6.1.4.1.32285.11.6.1.3.1.12
		topSIPSrvProfHotDelay OBJECT-TYPE
			SYNTAX INTEGER
				{
				enable(1),
				disable(2)
				}
			MAX-ACCESS read-write
			STATUS current
			DESCRIPTION
				"Description."
			DEFVAL { disable }
			::= { topSIPSrvProfInfoEntry 12 }

		
--  1.3.6.1.4.1.32285.11.6.1.3.1.13
		-- 1.3.6.1.4.1.32285.11.6.1.3.1.13
		topSIPSrvProfBindCnt OBJECT-TYPE
			SYNTAX INTEGER
			MAX-ACCESS read-only
			STATUS current
			DESCRIPTION
				"Description."
			::= { topSIPSrvProfInfoEntry 13 }

		
--  1.3.6.1.4.1.32285.11.6.1.3.1.14
		-- 1.3.6.1.4.1.32285.11.6.1.3.1.14
		topSIPSrvProfRowStatus OBJECT-TYPE
			SYNTAX RowStatus
			MAX-ACCESS read-create
			STATUS current
			DESCRIPTION
				"Description."
			::= { topSIPSrvProfInfoEntry 14 }

		
--  1.3.6.1.4.1.32285.11.6.1.4
		-- 1.3.6.1.4.1.32285.11.6.1.4
		topDigitMapProfInfoTable OBJECT-TYPE
			SYNTAX SEQUENCE OF TopDigitMapProfInfoEntry
			MAX-ACCESS not-accessible
			STATUS current
			DESCRIPTION
				"Description."
			::= { topSIPProfileObjects 4 }

		
--  1.3.6.1.4.1.32285.11.6.1.4.1
		-- 1.3.6.1.4.1.32285.11.6.1.4.1
		topDigitMapProfInfoEntry OBJECT-TYPE
			SYNTAX TopDigitMapProfInfoEntry
			MAX-ACCESS not-accessible
			STATUS current
			DESCRIPTION
				"Description."
			INDEX { topDigitMapProfIdx }
			::= { topDigitMapProfInfoTable 1 }

		
		TopDigitMapProfInfoEntry ::=
			SEQUENCE { 
				topDigitMapProfIdx
					INTEGER,
				topDigitMapProfName
					OCTET STRING,
				topDigitMapCirtDialTime
					INTEGER,
				topDigitMapPartDialTime
					INTEGER,
				topDigitMapFormat
					INTEGER,
				topDigitMapDialPlanToken
					OCTET STRING,
				topDigitMapBindCnt
					INTEGER,
				topDigitMapRowStatus
					RowStatus
			 }

--  1.3.6.1.4.1.32285.11.6.1.4.1.1
		-- 1.3.6.1.4.1.32285.11.6.1.4.1.1
		topDigitMapProfIdx OBJECT-TYPE
			SYNTAX INTEGER (1..64)
			MAX-ACCESS read-write
			STATUS current
			DESCRIPTION
				"Description."
			::= { topDigitMapProfInfoEntry 1 }

		
--  1.3.6.1.4.1.32285.11.6.1.4.1.2
		-- 1.3.6.1.4.1.32285.11.6.1.4.1.2
		topDigitMapProfName OBJECT-TYPE
			SYNTAX OCTET STRING (SIZE (1..31))
			MAX-ACCESS read-write
			STATUS current
			DESCRIPTION
				"Description.default:onu_digitmap_profile_xx"
			::= { topDigitMapProfInfoEntry 2 }

		
--  1.3.6.1.4.1.32285.11.6.1.4.1.3
		-- 1.3.6.1.4.1.32285.11.6.1.4.1.3
		topDigitMapCirtDialTime OBJECT-TYPE
			SYNTAX INTEGER (1..65535)
			UNITS "ms"
			MAX-ACCESS read-write
			STATUS current
			DESCRIPTION
				"Description."
			DEFVAL { 4000 }
			::= { topDigitMapProfInfoEntry 3 }

		
--  1.3.6.1.4.1.32285.11.6.1.4.1.4
		-- 1.3.6.1.4.1.32285.11.6.1.4.1.4
		topDigitMapPartDialTime OBJECT-TYPE
			SYNTAX INTEGER (1..65535)
			UNITS "ms"
			MAX-ACCESS read-write
			STATUS current
			DESCRIPTION
				"Description."
			DEFVAL { 16000 }
			::= { topDigitMapProfInfoEntry 4 }

		
--  1.3.6.1.4.1.32285.11.6.1.4.1.5
		-- 1.3.6.1.4.1.32285.11.6.1.4.1.5
		topDigitMapFormat OBJECT-TYPE
			SYNTAX INTEGER
				{
				not-defined(0),
				h248(1),
				ncs(2),
				vendor-specific(3)
				}
			MAX-ACCESS read-write
			STATUS current
			DESCRIPTION
				"Description."
			DEFVAL { not-defined }
			::= { topDigitMapProfInfoEntry 5 }

		
--  1.3.6.1.4.1.32285.11.6.1.4.1.6
		-- 1.3.6.1.4.1.32285.11.6.1.4.1.6
		topDigitMapDialPlanToken OBJECT-TYPE
			SYNTAX OCTET STRING (SIZE (1..1024))
			MAX-ACCESS read-write
			STATUS current
			DESCRIPTION
				"Description. use | separate"
			::= { topDigitMapProfInfoEntry 6 }

		
--  1.3.6.1.4.1.32285.11.6.1.4.1.7
		-- 1.3.6.1.4.1.32285.11.6.1.4.1.7
		topDigitMapBindCnt OBJECT-TYPE
			SYNTAX INTEGER
			MAX-ACCESS read-only
			STATUS current
			DESCRIPTION
				"Description."
			::= { topDigitMapProfInfoEntry 7 }

		
--  1.3.6.1.4.1.32285.11.6.1.4.1.8
		-- 1.3.6.1.4.1.32285.11.6.1.4.1.8
		topDigitMapRowStatus OBJECT-TYPE
			SYNTAX RowStatus
			MAX-ACCESS read-create
			STATUS current
			DESCRIPTION
				"Description."
			::= { topDigitMapProfInfoEntry 8 }

		
--   1.3.6.1.4.1.32285.11.6.2
-- 1.3.6.1.4.1.32285.11.6.2
		-- 1.3.6.1.4.1.32285.11.6.2
		topSIPPstnUserTable OBJECT-TYPE
			SYNTAX SEQUENCE OF TopSIPPstnUserEntry
			MAX-ACCESS not-accessible
			STATUS current
			DESCRIPTION
				"Description."
			::= { topvisionVoipTree 2 }

		
--   1.3.6.1.4.1.32285.11.6.2.1
-- 1.3.6.1.4.1.32285.11.6.2.1
		-- 1.3.6.1.4.1.32285.11.6.2.1
		topSIPPstnUserEntry OBJECT-TYPE
			SYNTAX TopSIPPstnUserEntry
			MAX-ACCESS not-accessible
			STATUS current
			DESCRIPTION
				"Description."
			INDEX { topSIPPstnUserSlotIdx, topSIPPstnUserPortIndx, topSIPPstnUserOnuIdx, topSIPPstnUserPotsIdx }
			::= { topSIPPstnUserTable 1 }

		
		TopSIPPstnUserEntry ::=
			SEQUENCE { 
				topSIPPstnUserSlotIdx
					INTEGER,
				topSIPPstnUserPortIndx
					INTEGER,
				topSIPPstnUserOnuIdx
					INTEGER,
				topSIPPstnUserPotsIdx
					INTEGER,
				topSIPPstnUserTelno
					OCTET STRING,
				topSIPPstnUserName
					OCTET STRING,
				topSIPPstnUserPwd
					OCTET STRING,
				topSIPPstnUserForwardType
					INTEGER,
				topSIPPstnUserForwardNum
					OCTET STRING,
				topSIPPstnUserForwardTime
					INTEGER,
				topSIPPstnUserDigitmapId
					INTEGER,
				topSIPPstnUserSipsrvId
					INTEGER
			 }

--   1.3.6.1.4.1.32285.11.6.2.1.1
-- 1.3.6.1.4.1.32285.11.6.2.1.1
		-- 1.3.6.1.4.1.32285.11.6.2.1.1
		topSIPPstnUserSlotIdx OBJECT-TYPE
			SYNTAX INTEGER
			MAX-ACCESS not-accessible
			STATUS current
			DESCRIPTION
				"Description."
			::= { topSIPPstnUserEntry 1 }

		
--   1.3.6.1.4.1.32285.11.6.2.1.2
-- 1.3.6.1.4.1.32285.11.6.2.1.2
		-- 1.3.6.1.4.1.32285.11.6.2.1.2
		topSIPPstnUserPortIndx OBJECT-TYPE
			SYNTAX INTEGER
			MAX-ACCESS not-accessible
			STATUS current
			DESCRIPTION
				"Description."
			::= { topSIPPstnUserEntry 2 }

		
--   1.3.6.1.4.1.32285.11.6.2.1.3
-- 1.3.6.1.4.1.32285.11.6.2.1.3
		-- 1.3.6.1.4.1.32285.11.6.2.1.3
		topSIPPstnUserOnuIdx OBJECT-TYPE
			SYNTAX INTEGER
			MAX-ACCESS not-accessible
			STATUS current
			DESCRIPTION
				"Description."
			::= { topSIPPstnUserEntry 3 }

		
--   1.3.6.1.4.1.32285.11.6.2.1.4
-- 1.3.6.1.4.1.32285.11.6.2.1.4
		-- 1.3.6.1.4.1.32285.11.6.2.1.4
		topSIPPstnUserPotsIdx OBJECT-TYPE
			SYNTAX INTEGER
			MAX-ACCESS not-accessible
			STATUS current
			DESCRIPTION
				"Description."
			::= { topSIPPstnUserEntry 4 }

		
--   1.3.6.1.4.1.32285.11.6.2.1.5
-- 1.3.6.1.4.1.32285.11.6.2.1.5
		-- 1.3.6.1.4.1.32285.11.6.2.1.5
		topSIPPstnUserTelno OBJECT-TYPE
			SYNTAX OCTET STRING (SIZE (1..64))
			MAX-ACCESS read-write
			STATUS current
			DESCRIPTION
				"Description.GPON:1-64  EPON:1-16"
			::= { topSIPPstnUserEntry 5 }

		
--   1.3.6.1.4.1.32285.11.6.2.1.6
-- 1.3.6.1.4.1.32285.11.6.2.1.6
		-- 1.3.6.1.4.1.32285.11.6.2.1.6
		topSIPPstnUserName OBJECT-TYPE
			SYNTAX OCTET STRING (SIZE (0..32))
			MAX-ACCESS read-write
			STATUS current
			DESCRIPTION
				"Description.GPON:1-64  EPON:1-16"
			::= { topSIPPstnUserEntry 6 }

		
--   1.3.6.1.4.1.32285.11.6.2.1.7
-- 1.3.6.1.4.1.32285.11.6.2.1.7
		-- 1.3.6.1.4.1.32285.11.6.2.1.7
		topSIPPstnUserPwd OBJECT-TYPE
			SYNTAX OCTET STRING (SIZE (1..24))
			MAX-ACCESS read-write
			STATUS current
			DESCRIPTION
				"Description.GPON:1-64  EPON:1-16"
			::= { topSIPPstnUserEntry 7 }

		
--   1.3.6.1.4.1.32285.11.6.2.1.5
-- 1.3.6.1.4.1.32285.11.6.2.1.8
		-- 1.3.6.1.4.1.32285.11.6.2.1.8
		topSIPPstnUserForwardType OBJECT-TYPE
			SYNTAX INTEGER (0..3)
			MAX-ACCESS read-write
			STATUS current
			DESCRIPTION
				"Description.0-disable 1-busy;2-no reply;3-unconditional"
			DEFVAL { 0 }
			::= { topSIPPstnUserEntry 8 }

		
--   1.3.6.1.4.1.32285.11.6.2.1.5
-- 1.3.6.1.4.1.32285.11.6.2.1.9
		-- 1.3.6.1.4.1.32285.11.6.2.1.9
		topSIPPstnUserForwardNum OBJECT-TYPE
			SYNTAX OCTET STRING (SIZE (1..64))
			MAX-ACCESS read-write
			STATUS current
			DESCRIPTION
				"Description.GPON:1-64  EPON:1-16  0:none"
			::= { topSIPPstnUserEntry 9 }

		
		-- 1.3.6.1.4.1.32285.11.6.2.1.10
		topSIPPstnUserForwardTime OBJECT-TYPE
			SYNTAX INTEGER (5..55)
			MAX-ACCESS read-write
			STATUS current
			DESCRIPTION
				"Description.unit s"
			::= { topSIPPstnUserEntry 10 }

		
--  1.3.6.1.4.1.32285.11.6.2.1.10
		-- 1.3.6.1.4.1.32285.11.6.2.1.11
		topSIPPstnUserDigitmapId OBJECT-TYPE
			SYNTAX INTEGER (0..64)
			MAX-ACCESS read-write
			STATUS current
			DESCRIPTION
				"Description.onu-digitmap-profile id   0:none"
			DEFVAL { 0 }
			::= { topSIPPstnUserEntry 11 }

		
--  1.3.6.1.4.1.32285.11.6.2.1.11
		-- 1.3.6.1.4.1.32285.11.6.2.1.12
		topSIPPstnUserSipsrvId OBJECT-TYPE
			SYNTAX INTEGER (0..64)
			MAX-ACCESS read-write
			STATUS current
			DESCRIPTION
				"Description.onu-sipsrv-profile id"
			DEFVAL { 0 }
			::= { topSIPPstnUserEntry 12 }

		
--   1.3.6.1.4.1.32285.11.6.3
-- 1.3.6.1.4.1.32285.11.6.3
		-- 1.3.6.1.4.1.32285.11.6.3
		topVoIPLineStatusTable OBJECT-TYPE
			SYNTAX SEQUENCE OF TopVoIPLineStatusEntry
			MAX-ACCESS not-accessible
			STATUS current
			DESCRIPTION
				"Description."
			::= { topvisionVoipTree 3 }

		
--   1.3.6.1.4.1.32285.11.6.3.1
-- 1.3.6.1.4.1.32285.11.6.3.1
		-- 1.3.6.1.4.1.32285.11.6.3.1
		topVoIPLineStatusEntry OBJECT-TYPE
			SYNTAX TopVoIPLineStatusEntry
			MAX-ACCESS not-accessible
			STATUS current
			DESCRIPTION
				"Description."
			INDEX { topVoIPLineSlotIdx, topVoIPLinePortIndx, topVoIPLineOnuIdx, topVoIPLinePotsIdx }
			::= { topVoIPLineStatusTable 1 }

		
		TopVoIPLineStatusEntry ::=
			SEQUENCE { 
				topVoIPLineSlotIdx
					INTEGER,
				topVoIPLinePortIndx
					INTEGER,
				topVoIPLineOnuIdx
					INTEGER,
				topVoIPLinePotsIdx
					INTEGER,
				topVoIPLineCodec
					INTEGER,
				topVoIPLineServStatus
					INTEGER,
				topVoIPLineSessType
					INTEGER,
				topVoIPLineState
					INTEGER
			 }

--   1.3.6.1.4.1.32285.11.6.3.1.1
-- 1.3.6.1.4.1.32285.11.6.3.1.1
		-- 1.3.6.1.4.1.32285.11.6.3.1.1
		topVoIPLineSlotIdx OBJECT-TYPE
			SYNTAX INTEGER
			MAX-ACCESS not-accessible
			STATUS current
			DESCRIPTION
				"Description."
			::= { topVoIPLineStatusEntry 1 }

		
--   1.3.6.1.4.1.32285.11.6.3.1.2
-- 1.3.6.1.4.1.32285.11.6.3.1.2
		-- 1.3.6.1.4.1.32285.11.6.3.1.2
		topVoIPLinePortIndx OBJECT-TYPE
			SYNTAX INTEGER
			MAX-ACCESS not-accessible
			STATUS current
			DESCRIPTION
				"Description."
			::= { topVoIPLineStatusEntry 2 }

		
--   1.3.6.1.4.1.32285.11.6.3.1.3
-- 1.3.6.1.4.1.32285.11.6.3.1.3
		-- 1.3.6.1.4.1.32285.11.6.3.1.3
		topVoIPLineOnuIdx OBJECT-TYPE
			SYNTAX INTEGER
			MAX-ACCESS not-accessible
			STATUS current
			DESCRIPTION
				"Description."
			::= { topVoIPLineStatusEntry 3 }

		
--   1.3.6.1.4.1.32285.11.6.3.1.4
-- 1.3.6.1.4.1.32285.11.6.3.1.4
		-- 1.3.6.1.4.1.32285.11.6.3.1.4
		topVoIPLinePotsIdx OBJECT-TYPE
			SYNTAX INTEGER
			MAX-ACCESS not-accessible
			STATUS current
			DESCRIPTION
				"Description."
			::= { topVoIPLineStatusEntry 4 }

		
--   1.3.6.1.4.1.32285.11.6.3.1.5
-- 1.3.6.1.4.1.32285.11.6.3.1.5
		-- 1.3.6.1.4.1.32285.11.6.3.1.5
		topVoIPLineCodec OBJECT-TYPE
			SYNTAX INTEGER (1..10)
			MAX-ACCESS read-only
			STATUS current
			DESCRIPTION
				"0 pcmu
				1 reserved1
				2 reserved2
				3 gsm
				4 g723
				5 dvi4-8k
				6 dvi4-16k
				7 lpc
				8 pcma
				9 g722
				10 l16-2c
				11 l16-1c
				12 qcelp
				13 cn
				14 mpa
				15 g728
				16 dvi4-11k
				17 dvi4-22k
				18 g729
				19~95 reserved
				255 NULL"
			::= { topVoIPLineStatusEntry 5 }

		
--   1.3.6.1.4.1.32285.11.6.3.1.6
-- 1.3.6.1.4.1.32285.11.6.3.1.6
		-- 1.3.6.1.4.1.32285.11.6.3.1.6
		topVoIPLineServStatus OBJECT-TYPE
			SYNTAX INTEGER (0..14)
			MAX-ACCESS read-only
			STATUS current
			DESCRIPTION
				"0 None/initial
				1 Registered
				2 In session
				3 Failed registration - icmp error
				4 Failed registration - failed tcp
				5 Failed registration - failed authentication
				6 Failed registration - timeout
				7 Failed registration - server fail code
				8 Failed invite - icmp error
				9 Failed invite - failed tcp
				10 Failed invite - failed authentication
				11 Failed invite - timeout
				12 Failed invite - server fail code
				13 Port not configured
				14 Config done
				15 Disabled by switch"
			::= { topVoIPLineStatusEntry 6 }

		
--   1.3.6.1.4.1.32285.11.6.3.1.7
-- 1.3.6.1.4.1.32285.11.6.3.1.7
		-- 1.3.6.1.4.1.32285.11.6.3.1.7
		topVoIPLineSessType OBJECT-TYPE
			SYNTAX INTEGER (0..5)
			MAX-ACCESS read-only
			STATUS current
			DESCRIPTION
				"0 Idle/none
				1 2way
				2 3way
				3 Fax
				4 Telem
				5 Conference"
			::= { topVoIPLineStatusEntry 7 }

		
--   1.3.6.1.4.1.32285.11.6.3.1.8
-- 1.3.6.1.4.1.32285.11.6.3.1.8
		-- 1.3.6.1.4.1.32285.11.6.3.1.8
		topVoIPLineState OBJECT-TYPE
			SYNTAX INTEGER (0..10)
			MAX-ACCESS read-only
			STATUS current
			DESCRIPTION
				"0 Idle, on-hook
				1 Off-hook dial tone
				2 Dialling
				3 Ringing or FSK alerting/data
				4 Audible ringback
				5 Connecting
				6 Connected
				7 Disconnecting, audible indication
				8 Receiver off hook (ROH), no tone
				9 ROH with tone
				10 Unknown or undefined"
			::= { topVoIPLineStatusEntry 8 }

		
--   1.3.6.1.4.1.32285.11.6.2
-- 1.3.6.1.4.1.32285.11.6.4
		-- 1.3.6.1.4.1.32285.11.6.4
		topOnuIfPotsInfoTable OBJECT-TYPE
			SYNTAX SEQUENCE OF TopOnuIfPotsInfoEntry
			MAX-ACCESS not-accessible
			STATUS current
			DESCRIPTION
				"Description."
			::= { topvisionVoipTree 4 }

		
--   1.3.6.1.4.1.32285.11.6.2.1
-- 1.3.6.1.4.1.32285.11.6.4.1
		-- 1.3.6.1.4.1.32285.11.6.4.1
		topOnuIfPotsInfoEntry OBJECT-TYPE
			SYNTAX TopOnuIfPotsInfoEntry
			MAX-ACCESS not-accessible
			STATUS current
			DESCRIPTION
				"Description."
			INDEX { topOnuIfPotsSlotIdx, topOnuIfPotsPortIndx, topOnuIfPotsOnuIdx, topOnuIfPotsPotsIdx }
			::= { topOnuIfPotsInfoTable 1 }

		
		TopOnuIfPotsInfoEntry ::=
			SEQUENCE { 
				topOnuIfPotsSlotIdx
					INTEGER,
				topOnuIfPotsPortIndx
					INTEGER,
				topOnuIfPotsOnuIdx
					INTEGER,
				topOnuIfPotsPotsIdx
					INTEGER,
				topOnuIfPotsAdminState
					INTEGER
			 }

--   1.3.6.1.4.1.32285.11.6.2.1.1
-- 1.3.6.1.4.1.32285.11.6.4.1.1
		-- 1.3.6.1.4.1.32285.11.6.4.1.1
		topOnuIfPotsSlotIdx OBJECT-TYPE
			SYNTAX INTEGER
			MAX-ACCESS not-accessible
			STATUS current
			DESCRIPTION
				"Description."
			::= { topOnuIfPotsInfoEntry 1 }

		
--   1.3.6.1.4.1.32285.11.6.2.1.2
-- 1.3.6.1.4.1.32285.11.6.4.1.2
		-- 1.3.6.1.4.1.32285.11.6.4.1.2
		topOnuIfPotsPortIndx OBJECT-TYPE
			SYNTAX INTEGER
			MAX-ACCESS not-accessible
			STATUS current
			DESCRIPTION
				"Description."
			::= { topOnuIfPotsInfoEntry 2 }

		
--   1.3.6.1.4.1.32285.11.6.2.1.3
-- 1.3.6.1.4.1.32285.11.6.4.1.3
		-- 1.3.6.1.4.1.32285.11.6.4.1.3
		topOnuIfPotsOnuIdx OBJECT-TYPE
			SYNTAX INTEGER
			MAX-ACCESS not-accessible
			STATUS current
			DESCRIPTION
				"Description."
			::= { topOnuIfPotsInfoEntry 3 }

		
--   1.3.6.1.4.1.32285.11.6.2.1.4
-- 1.3.6.1.4.1.32285.11.6.4.1.4
		-- 1.3.6.1.4.1.32285.11.6.4.1.4
		topOnuIfPotsPotsIdx OBJECT-TYPE
			SYNTAX INTEGER
			MAX-ACCESS not-accessible
			STATUS current
			DESCRIPTION
				"Description."
			::= { topOnuIfPotsInfoEntry 4 }

		
--   1.3.6.1.4.1.32285.11.6.2.1.5
-- 1.3.6.1.4.1.32285.11.6.4.1.5
		-- 1.3.6.1.4.1.32285.11.6.4.1.5
		topOnuIfPotsAdminState OBJECT-TYPE
			SYNTAX INTEGER
				{
				enable(1),
				disable(2)
				}
			MAX-ACCESS read-write
			STATUS current
			DESCRIPTION
				"Description."
			DEFVAL { disable }
			::= { topOnuIfPotsInfoEntry 5 }

		
--   1.3.6.1.4.1.32285.11.6.2
-- 1.3.6.1.4.1.32285.11.6.5
		-- 1.3.6.1.4.1.32285.11.6.5
		topOnuIfSipTable OBJECT-TYPE
			SYNTAX SEQUENCE OF TopOnuIfSipEntry
			MAX-ACCESS not-accessible
			STATUS current
			DESCRIPTION
				"Description."
			::= { topvisionVoipTree 5 }

		
--   1.3.6.1.4.1.32285.11.6.2.1
-- 1.3.6.1.4.1.32285.11.6.5.1
		-- 1.3.6.1.4.1.32285.11.6.5.1
		topOnuIfSipEntry OBJECT-TYPE
			SYNTAX TopOnuIfSipEntry
			MAX-ACCESS not-accessible
			STATUS current
			DESCRIPTION
				"Description."
			INDEX { topOnuIfSipSlotIdx, topOnuIfSipPortIdx, topOnuIfSipOnuIdx, topOnuIfSipPotsIdx }
			::= { topOnuIfSipTable 1 }

		
		TopOnuIfSipEntry ::=
			SEQUENCE { 
				topOnuIfSipSlotIdx
					INTEGER,
				topOnuIfSipPortIdx
					INTEGER,
				topOnuIfSipOnuIdx
					INTEGER,
				topOnuIfSipPotsIdx
					INTEGER,
				topOnuIfSipSipAgtId
					INTEGER,
				topOnuIfSipVoipMediaId
					INTEGER
			 }

--   1.3.6.1.4.1.32285.11.6.2.1.1
-- 1.3.6.1.4.1.32285.11.6.5.1.1
		-- 1.3.6.1.4.1.32285.11.6.5.1.1
		topOnuIfSipSlotIdx OBJECT-TYPE
			SYNTAX INTEGER
			MAX-ACCESS not-accessible
			STATUS current
			DESCRIPTION
				"Description."
			::= { topOnuIfSipEntry 1 }

		
--   1.3.6.1.4.1.32285.11.6.2.1.2
-- 1.3.6.1.4.1.32285.11.6.5.1.2
		-- 1.3.6.1.4.1.32285.11.6.5.1.2
		topOnuIfSipPortIdx OBJECT-TYPE
			SYNTAX INTEGER
			MAX-ACCESS not-accessible
			STATUS current
			DESCRIPTION
				"Description."
			::= { topOnuIfSipEntry 2 }

		
--   1.3.6.1.4.1.32285.11.6.2.1.3
-- 1.3.6.1.4.1.32285.11.6.5.1.3
		-- 1.3.6.1.4.1.32285.11.6.5.1.3
		topOnuIfSipOnuIdx OBJECT-TYPE
			SYNTAX INTEGER
			MAX-ACCESS not-accessible
			STATUS current
			DESCRIPTION
				"Description."
			::= { topOnuIfSipEntry 3 }

		
--   1.3.6.1.4.1.32285.11.6.2.1.4
-- 1.3.6.1.4.1.32285.11.6.5.1.4
		-- 1.3.6.1.4.1.32285.11.6.5.1.4
		topOnuIfSipPotsIdx OBJECT-TYPE
			SYNTAX INTEGER
			MAX-ACCESS not-accessible
			STATUS current
			DESCRIPTION
				"Description."
			::= { topOnuIfSipEntry 4 }

		
--   1.3.6.1.4.1.32285.11.6.2.1.5
-- 1.3.6.1.4.1.32285.11.6.5.1.5
		-- 1.3.6.1.4.1.32285.11.6.5.1.5
		topOnuIfSipSipAgtId OBJECT-TYPE
			SYNTAX INTEGER (0..64)
			MAX-ACCESS read-write
			STATUS current
			DESCRIPTION
				"Description.onu-sipagent-profile id"
			::= { topOnuIfSipEntry 5 }

		
--   1.3.6.1.4.1.32285.11.6.2.1.6
-- 1.3.6.1.4.1.32285.11.6.5.1.6
		-- 1.3.6.1.4.1.32285.11.6.5.1.6
		topOnuIfSipVoipMediaId OBJECT-TYPE
			SYNTAX INTEGER (0..64)
			MAX-ACCESS read-write
			STATUS current
			DESCRIPTION
				"Description.onu-voipmedia-profile id"
			::= { topOnuIfSipEntry 6 }

		
--   1.3.6.1.4.1.32285.11.6.2
-- 1.3.6.1.4.1.32285.11.6.6
		-- 1.3.6.1.4.1.32285.11.6.6
		topOnuVoipIPTable OBJECT-TYPE
			SYNTAX SEQUENCE OF TopOnuVoipIPEntry
			MAX-ACCESS not-accessible
			STATUS current
			DESCRIPTION
				"Description."
			::= { topvisionVoipTree 6 }

		
--   1.3.6.1.4.1.32285.11.6.2.1
-- 1.3.6.1.4.1.32285.11.6.6.1
		-- 1.3.6.1.4.1.32285.11.6.6.1
		topOnuVoipIPEntry OBJECT-TYPE
			SYNTAX TopOnuVoipIPEntry
			MAX-ACCESS not-accessible
			STATUS current
			DESCRIPTION
				"Description."
			INDEX { topOnuVoipIPSlotIdx, topOnuVoipIPPortIdx, topOnuVoipIPOnuIdx, topOnuVoipIPPotsIdx }
			::= { topOnuVoipIPTable 1 }

		
		TopOnuVoipIPEntry ::=
			SEQUENCE { 
				topOnuVoipIPSlotIdx
					INTEGER,
				topOnuVoipIPPortIdx
					INTEGER,
				topOnuVoipIPOnuIdx
					INTEGER,
				topOnuVoipIPPotsIdx
					INTEGER,
				topOnuVoipIPConfigMode
					INTEGER,
				topOnuVoipIPAddress
					IpAddress,
				topOnuVoipIPMask
					IpAddress,
				topOnuVoipIPGetway
					IpAddress,
				topOnuVoipIPPrimaryDNS
					IpAddress,
				topOnuVoipIPSecondaryDNS
					IpAddress,
				topOnuVoipIPVlan
					INTEGER,
				topOnuVoipIPVlanPri
					INTEGER,
				topOnuVoipIPRowStatus
					RowStatus
			 }

--   1.3.6.1.4.1.32285.11.6.2.1.1
-- 1.3.6.1.4.1.32285.11.6.6.1.1
		-- 1.3.6.1.4.1.32285.11.6.6.1.1
		topOnuVoipIPSlotIdx OBJECT-TYPE
			SYNTAX INTEGER
			MAX-ACCESS not-accessible
			STATUS current
			DESCRIPTION
				"Description."
			::= { topOnuVoipIPEntry 1 }

		
--   1.3.6.1.4.1.32285.11.6.2.1.2
-- 1.3.6.1.4.1.32285.11.6.6.1.2
		-- 1.3.6.1.4.1.32285.11.6.6.1.2
		topOnuVoipIPPortIdx OBJECT-TYPE
			SYNTAX INTEGER
			MAX-ACCESS not-accessible
			STATUS current
			DESCRIPTION
				"Description."
			::= { topOnuVoipIPEntry 2 }

		
--   1.3.6.1.4.1.32285.11.6.2.1.3
-- 1.3.6.1.4.1.32285.11.6.6.1.3
		-- 1.3.6.1.4.1.32285.11.6.6.1.3
		topOnuVoipIPOnuIdx OBJECT-TYPE
			SYNTAX INTEGER
			MAX-ACCESS not-accessible
			STATUS current
			DESCRIPTION
				"Description."
			::= { topOnuVoipIPEntry 3 }

		
--   1.3.6.1.4.1.32285.11.6.2.1.4
-- 1.3.6.1.4.1.32285.11.6.6.1.4
		-- 1.3.6.1.4.1.32285.11.6.6.1.4
		topOnuVoipIPPotsIdx OBJECT-TYPE
			SYNTAX INTEGER
			MAX-ACCESS not-accessible
			STATUS current
			DESCRIPTION
				"Description."
			::= { topOnuVoipIPEntry 4 }

		
--   1.3.6.1.4.1.32285.11.6.2.1.5
-- 1.3.6.1.4.1.32285.11.6.6.1.5
		-- 1.3.6.1.4.1.32285.11.6.6.1.5
		topOnuVoipIPConfigMode OBJECT-TYPE
			SYNTAX INTEGER
				{
				dhcp(1),
				static(2)
				}
			MAX-ACCESS read-write
			STATUS current
			DESCRIPTION
				"Description."
			DEFVAL { dhcp }
			::= { topOnuVoipIPEntry 5 }

		
--   1.3.6.1.4.1.32285.11.6.2.1.6
-- 1.3.6.1.4.1.32285.11.6.6.1.6
		-- 1.3.6.1.4.1.32285.11.6.6.1.6
		topOnuVoipIPAddress OBJECT-TYPE
			SYNTAX IpAddress
			MAX-ACCESS read-write
			STATUS current
			DESCRIPTION
				"Description."
			::= { topOnuVoipIPEntry 6 }

		
--   1.3.6.1.4.1.32285.11.6.2.1.7
-- 1.3.6.1.4.1.32285.11.6.6.1.7
		-- 1.3.6.1.4.1.32285.11.6.6.1.7
		topOnuVoipIPMask OBJECT-TYPE
			SYNTAX IpAddress
			MAX-ACCESS read-write
			STATUS current
			DESCRIPTION
				"Description."
			::= { topOnuVoipIPEntry 7 }

		
--   1.3.6.1.4.1.32285.11.6.2.1.5
-- 1.3.6.1.4.1.32285.11.6.6.1.8
		-- 1.3.6.1.4.1.32285.11.6.6.1.8
		topOnuVoipIPGetway OBJECT-TYPE
			SYNTAX IpAddress
			MAX-ACCESS read-write
			STATUS current
			DESCRIPTION
				"Description."
			::= { topOnuVoipIPEntry 8 }

		
--  1.3.6.1.4.1.32285.11.6.6.1.9
		-- 1.3.6.1.4.1.32285.11.6.6.1.9
		topOnuVoipIPPrimaryDNS OBJECT-TYPE
			SYNTAX IpAddress
			MAX-ACCESS read-write
			STATUS current
			DESCRIPTION
				"Description."
			::= { topOnuVoipIPEntry 9 }

		
--  1.3.6.1.4.1.32285.11.6.6.1.10
		-- 1.3.6.1.4.1.32285.11.6.6.1.10
		topOnuVoipIPSecondaryDNS OBJECT-TYPE
			SYNTAX IpAddress
			MAX-ACCESS read-write
			STATUS current
			DESCRIPTION
				"Description."
			::= { topOnuVoipIPEntry 10 }

		
--  1.3.6.1.4.1.32285.11.6.6.1.11
		-- 1.3.6.1.4.1.32285.11.6.6.1.11
		topOnuVoipIPVlan OBJECT-TYPE
			SYNTAX INTEGER (1..4096)
			MAX-ACCESS read-write
			STATUS current
			DESCRIPTION
				"Description."
			::= { topOnuVoipIPEntry 11 }

		
--  1.3.6.1.4.1.32285.11.6.6.1.12
		-- 1.3.6.1.4.1.32285.11.6.6.1.12
		topOnuVoipIPVlanPri OBJECT-TYPE
			SYNTAX INTEGER (0..7)
			MAX-ACCESS read-write
			STATUS current
			DESCRIPTION
				"Description."
			::= { topOnuVoipIPEntry 12 }

		
--  1.3.6.1.4.1.32285.11.6.6.1.13
		-- 1.3.6.1.4.1.32285.11.6.6.1.13
		topOnuVoipIPRowStatus OBJECT-TYPE
			SYNTAX RowStatus
			MAX-ACCESS read-create
			STATUS current
			DESCRIPTION
				"Description."
			::= { topOnuVoipIPEntry 13 }

		
	
	END

--
-- SUMA-VOIP-MIB.mib
--
