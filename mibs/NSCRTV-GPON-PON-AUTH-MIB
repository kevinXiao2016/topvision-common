--
-- NSCRTV-EPONEOC-GPON-PON-AUTH-MIB.mib
-- MIB generated by MG-SOFT Visual MIB Builder Version 4.0 Build 349
-- Friday, September 30, 2016 at 09:45:40
--

	NSCRTV-EPONEOC-GPON-PON-AUTH-MIB DEFINITIONS ::= BEGIN
 
		IMPORTS
			BridgeId, Timeout			
				FROM BRIDGE-MIB			
			enterprises, TimeTicks, IpAddress, Unsigned32, Gauge32, 
			Counter32, Counter64, OBJECT-TYPE, OBJECT-IDENTITY, 
			NOTIFICATION-TYPE			
				FROM SNMPv2-SMI			
			DateAndTime, TruthValue, RowStatus, MacAddress, DisplayString, 
			TimeStamp, TEXTUAL-CONVENTION			
				FROM SNMPv2-TC;

--
-- Textual conventions
--
		GponCardIndex ::= TEXTUAL-CONVENTION
			STATUS current
			DESCRIPTION 
				"     
				For easy presenting the chassis view by NMS, bCardIndex shall be formatted
				in a following manner:                        
				    Four bytes of INTEGER, from the most significant byte to the least significant
				    bytes
				        -----------------------------------------------------------------------------
				Reserved byte Reserved byte   Reserved byte Sub-slot 2-bit Main-slot 6-bit        
				Notes:
				-----         
				1. Reserved bytes shall be set to 0.        
				2. The main-slot shall be started from 1, and shall be in a consecutive manner,
				   for all slots, including service slots, control slots, switch slots, power
				slots,FAN slots, etc.For example, 1, 2, 3          
				3. The sub-slot shall be started from 1, and shall be in a consecutive manner.
				   For example, 1, 2. If no sub-slot concept of a main-slot, set to 0.        
				4. For fixed device, if no slot concept, NE shall set both main-slot and sub-slot
				to 0, to indicate this is meaningless. For modulized device, they MUST not be
				set to 0.This definition shall applied to both OLT and ONU.        
				5. For trunk, since there is no slot concept, set main-slot to all-1 and sub-slot
				to 0. This definition shall applied to both OLT and ONU.
				
				For example, 
				0x00 00 00 0A, represents main-slot 10, no sub-slot
				0x00 00 00 42, represents main-slot 2, sub-slot 1
				0x00 00 00 3F, represents a trunk
				"
			SYNTAX Unsigned32

		GponPortIndex ::= TEXTUAL-CONVENTION
			STATUS current
			DESCRIPTION 
				"       
				The device port number shall start from 1. Nunber 0 had specific meaning, stands
				for portIndex is meaningless, for the situation defined.
				"
			SYNTAX INTEGER (0..255)

		GponDeviceIndex ::= TEXTUAL-CONVENTION
			STATUS current
			DESCRIPTION 
				"
				Gpon olt/onu
				ONU ID       
				Olt device-8bit OLT Card-8bit Pon port-8bit OnuNUM-8bit        
				Note: 
				----        
				1. OLT device must not be 0.        
				2. Card here shall confirm the last byte definition of GponCardIndex
				   to indicate the main-slot and sub-slot index.         
				3. Pon port must not be 0.
				4. The useful ONU logical ID MUST never be set to 0, where NUM of 0 has
				   another meaning, to indicate that the ONU logical ID is meaningless,
				   or said to not applied.
				        
				Usage guide:
				-----------        
				This TC could be used for OLT SNI, OLT PON port, OLT ONU ID
				ONU UNI, OLT device, trunk.         
				If the refered MIB object does not have clear definition,
				refer to the following:
				Applied Obj  - Descriptions of Index
				------------------------------------------------------------------
				OLT Pon Port - OnuNum shall be set to 0,
				OLT SNI    - Same as OLT Pon Port         
				OLT onu ID   - Set OnuNUM to corresponding ONU logical ID         
				ONU UNI    - Same as OLT ONU ID
				OLT device   - Set card, pon port and OnuNUM to 0
				Trunk    - Card to 0x3F, pon port to trunk ID, OnuNUM to 0
				         Olt device to corresponding ONU device       
				"
			SYNTAX Unsigned32


--
-- Node definitions
--
	
		-- 1.3.6.1.4.1.17409
		nscrtvRoot OBJECT IDENTIFIER ::= { enterprises 17409 }

		
		-- 1.3.6.1.4.1.17409.2
		nscrtvFTTxTree OBJECT IDENTIFIER ::= { nscrtvRoot 2 }

		
--      DESCRIPTION
		-- 1.3.6.1.4.1.17409.2.8
		gponTree OBJECT IDENTIFIER ::= { nscrtvFTTxTree 8 }


		
-- ------------------------------------------------------------------------------
-- ponPortObjects(1.3.6.1.4.1.17409.2.8.3)
-- ------------------------------------------------------------------------------ 
        -- 1.3.6.1.4.1.17409.2.8.3
		ponPortObjects OBJECT IDENTIFIER ::= { gponTree 3 }
		
		
		-- 1.3.6.1.4.1.17409.2.8.3.4
		ponOnuAuthenticationModeTable OBJECT-TYPE
			SYNTAX SEQUENCE OF PonOnuAuthenticationModeEntry
			MAX-ACCESS not-accessible
			STATUS current
			DESCRIPTION			" "
			::= { ponPortObjects 4 }

		
		-- 1.3.6.1.4.1.17409.2.8.3.4.1
		ponOnuAuthenticationModeEntry OBJECT-TYPE
			SYNTAX PonOnuAuthenticationModeEntry
			MAX-ACCESS not-accessible
			STATUS current
			DESCRIPTION
				"The ponOnuAuthenticationModeEntry Information"
			INDEX { ponAuthenDeviceIndex, ponAuthenCardIndex, ponAuthenPortIndex }
			::= { ponOnuAuthenticationModeTable 1 }

		
		PonOnuAuthenticationModeEntry ::=
			SEQUENCE { 
				ponAuthenDeviceIndex
					INTEGER,
				ponAuthenCardIndex
					GponCardIndex,
				ponAuthenPortIndex
					GponPortIndex,
				ponOnuAuthenMode
					INTEGER,
				ponAutoFindEnable
					INTEGER
			 }

		-- 1.3.6.1.4.1.17409.2.8.3.4.1.1
		ponAuthenDeviceIndex OBJECT-TYPE
			SYNTAX INTEGER
			MAX-ACCESS not-accessible
			STATUS current
			DESCRIPTION
				" "
			::= { ponOnuAuthenticationModeEntry 1 }

		
		-- 1.3.6.1.4.1.17409.2.8.3.4.1.2
		ponAuthenCardIndex OBJECT-TYPE
			SYNTAX GponCardIndex
			MAX-ACCESS not-accessible
			STATUS current
			DESCRIPTION			" "
			::= { ponOnuAuthenticationModeEntry 2 }

		
		-- 1.3.6.1.4.1.17409.2.8.3.4.1.3
		ponAuthenPortIndex OBJECT-TYPE
			SYNTAX GponPortIndex
			MAX-ACCESS not-accessible
			STATUS current
			DESCRIPTION
				"pon"
			::= { ponOnuAuthenticationModeEntry 3 }

		
		-- 1.3.6.1.4.1.17409.2.8.3.4.1.4
		ponOnuAuthenMode OBJECT-TYPE
			SYNTAX INTEGER
				{
				sn(1),
				sn-pwd(2),
				loid(3),
				loid-pwd(4),
				pwd(5),
				auto(6),
				mix(7)
				}
			MAX-ACCESS read-write
			STATUS current
			DESCRIPTION
				"Authen mode;This is mode in authen"
			::= { ponOnuAuthenticationModeEntry 4 }
			
		
		-- 1.3.6.1.4.1.17409.2.8.3.4.1.5
		ponAutoFindEnable OBJECT-TYPE
			SYNTAX INTEGER
				{
				enable(1),
				disable(2)
				}
			MAX-ACCESS read-write
			STATUS current
			DESCRIPTION
				"AutoFindEnable."
			DEFVAL { enable }
			::= { ponOnuAuthenticationModeEntry 5 }
	
	
	END

--
-- NSCRTV-EPONEOC-GPON-PON-AUTH-MIB.my
--
