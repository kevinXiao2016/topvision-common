--
-- SUMA-EPONEOC-EPON-MIB.mib
-- MIB generated by MG-SOFT Visual MIB Builder Version 4.0 Build 349
-- Wednesday, October 19, 2011 at 15:54:31
--

	SUMA-EPONEOC-EPON-MIB DEFINITIONS ::= BEGIN
 
		IMPORTS
			enterprises, TimeTicks, IpAddress, Unsigned32, Counter64, 
			OBJECT-TYPE, OBJECT-IDENTITY			
				FROM SNMPv2-SMI			
			RowStatus, TimeStamp, DisplayString, MacAddress, TEXTUAL-CONVENTION, DateAndTime	
				FROM SNMPv2-TC;	
--
-- Textual conventions
--
	
		TopEponAlarmCode ::= TEXTUAL-CONVENTION
			STATUS current
			DESCRIPTION 
				"Alarm codes, uniquely indentifies each kind of alarm.
				Refer to EPON alarm definition table"
			SYNTAX INTEGER (1..65535)

		TopEPonSlotIndex ::= TEXTUAL-CONVENTION
			STATUS current
			DESCRIPTION 
				"This represents the slot number in the epon shelf."
			SYNTAX INTEGER (1..18)

		TopEPonPonIndex ::= TEXTUAL-CONVENTION
			STATUS current
			DESCRIPTION 
				"This represents the PON number in the epon board."
			SYNTAX INTEGER (1..8)

		EponDeviceIndex ::= TEXTUAL-CONVENTION
			STATUS current
			DESCRIPTION 
				"From MSB on, OLT slot index-8bits, PON/SNI port-8bits, 
				OnuNUM-8bits and UNI port-8bits.
				OLT PON/SNI Port - OnuNum and UNI port shall be set to 0."
			SYNTAX Unsigned32

		TopEPonOnuAuthNum ::= TEXTUAL-CONVENTION
			STATUS current
			DESCRIPTION 
				"This represents the ONU auth number in the epon board."
			SYNTAX INTEGER (1..128)

		TopEPonUniPortIndex ::= TEXTUAL-CONVENTION
			STATUS current
			DESCRIPTION 
				"This represents the ONU uni number in the epon board."
			SYNTAX INTEGER (1..32)

		TopEponStatsThresholdType ::= TEXTUAL-CONVENTION
			STATUS current
			DESCRIPTION 
				"1- InOctets
				2 InPkts
				3 InBroadcastPkts
				4 InMulticastPkts
				5 InPkts64Octets
				6 InPkts65to127Octets
				7 InPkts128to255Octets
				8 InPkts256to511Octets
				9 InPkts512to1023Octets
				10 InPkts1024to1518Octets
				11 InPkts1519to1522Octets
				12 InUndersizePkts
				13 InOversizePkts
				14 InFragments
				15 InMpcpFrames
				16 InMpcpOctets
				17 InOAMFrames
				18 InOAMOctets
				19 InCRCErrorPkts
				20 InDropEvents
				21 InJabbers
				22 InCollision
				23 OutOctets
				24 OutPkts
				25 OutBroadcastPkts
				26 OutMulticastPkts
				27 OutPkts64Octets
				28 OutPkts65to127Octets
				29 OutPkts128to255Octets
				30 OutPkts256to511Octets
				31 OutPkts512to1023Octets
				32 OutPkts1024to1518Octets
				33 OutPkts1519o1522Octets
				34 OutUndersizePkts
				35 OutOversizePkts
				36 OutFragments
				37 OutMpcpFrames
				38 OutMpcpOctets
				39 OutOAMFrames
				40 OutOAMOctets
				41 OutCRCErrorPkts
				42 OutDropEvents
				43 OutJabbers
				44 OutCollision
				50 Temperature
				Note:
				----------------------------------------------------------------
				1. For 50 Temperature, this parameter shall only applied to
				a. Slot level, for each service/switch/management card, for
				chassis-based system.
				b. Node-level, for fixed box.
				2. For 50 Temperature, shall be applied to both OLT and ONU
				3. For 50 Temperature, since no 15-min performance data collection
				are required, system shall ensure the temperature polling interval
				no less than 5 seconds. The alarm shall be only generated when the
				threshold is acrossed for three continuous intervals, and shall be
				cleared, when the threshold is not accrossed any more, for three
				continous intervals.
				"
			SYNTAX INTEGER (1..1024)

		TopEPonSniIndex ::= TEXTUAL-CONVENTION
			STATUS current
			DESCRIPTION 
				"This represents the sni port number in the uplink board."
			SYNTAX INTEGER (1..8)

	
--
-- Node definitions
--
	
		-- 1.3.6.1.4.1.32285
		sumaRoot OBJECT IDENTIFIER ::= { enterprises 32285 }

		
		-- 1.3.6.1.4.1.32285.11
		topvisionRoot OBJECT IDENTIFIER ::= { sumaRoot 11 }

		
		-- 1.3.6.1.4.1.32285.11.1
		topvisionHFCCcmtsTree OBJECT IDENTIFIER ::= { topvisionRoot 1 }

		
		-- 1.3.6.1.4.1.32285.11.2
		topvisionEponEocTree OBJECT IDENTIFIER ::= { topvisionRoot 2 }

		
		-- 1.3.6.1.4.1.32285.11.2.1
		propertyIdent OBJECT IDENTIFIER ::= { topvisionEponEocTree 1 }

		
		-- 1.3.6.1.4.1.32285.11.2.1.1
		topSysOlt8601 OBJECT IDENTIFIER ::= { propertyIdent 1 }

		
		-- 1.3.6.1.4.1.32285.11.2.1.2
		topSysOlt8602 OBJECT IDENTIFIER ::= { propertyIdent 2 }

		
		-- 1.3.6.1.4.1.32285.11.2.1.2.1
		topSysOlt8602-E OBJECT IDENTIFIER ::= { topSysOlt8602 1 }

		
		-- 1.3.6.1.4.1.32285.11.2.1.2.1.1
		topSysOltMeua OBJECT IDENTIFIER ::= { topSysOlt8602-E 1 }

		
		-- 1.3.6.1.4.1.32285.11.2.1.2.1.2
		topSysOltMeub OBJECT IDENTIFIER ::= { topSysOlt8602-E 2 }

		
		-- 1.3.6.1.4.1.32285.11.2.1.2.2
		topSysOlt8602-EF OBJECT IDENTIFIER ::= { topSysOlt8602 2 }

		
		-- 1.3.6.1.4.1.32285.11.2.1.2.2.1
		topSysOltMefa OBJECT IDENTIFIER ::= { topSysOlt8602-EF 1 }

		
		-- 1.3.6.1.4.1.32285.11.2.1.2.2.2
		topSysOltMefb OBJECT IDENTIFIER ::= { topSysOlt8602-EF 2 }

		
		-- 1.3.6.1.4.1.32285.11.2.1.3
		topSysOlt8603 OBJECT IDENTIFIER ::= { propertyIdent 3 }

		

		-- 1.3.6.1.4.1.32285.11.2.2
		topAlarmsIdent OBJECT IDENTIFIER ::= { topvisionEponEocTree 2 }

		
		-- 1.3.6.1.4.1.32285.11.2.3
		topvisionEponTree OBJECT IDENTIFIER ::= { topvisionEponEocTree 3 }

		
		-- 1.3.6.1.4.1.32285.11.2.3.1
		topSystemObjects OBJECT IDENTIFIER ::= { topvisionEponTree 1 }

		
		-- 1.3.6.1.4.1.32285.11.2.3.1.1
		topSysGlobalObjects OBJECT IDENTIFIER ::= { topSystemObjects 1 }

		
		-- 1.3.6.1.4.1.32285.11.2.3.1.1.1
		topSysSnmpHostIp OBJECT-TYPE
			SYNTAX IpAddress
			MAX-ACCESS read-write
			STATUS current
			DESCRIPTION
				"SNMP Host Ip Address"
			::= { topSysGlobalObjects 1 }

		
		-- 1.3.6.1.4.1.32285.11.2.3.1.1.2
		topSysSnmpHostIpMask OBJECT-TYPE
			SYNTAX IpAddress
			MAX-ACCESS read-write
			STATUS current
			DESCRIPTION
				"IP address mask"
			::= { topSysGlobalObjects 2 }

		
		-- 1.3.6.1.4.1.32285.11.2.3.1.1.3
		topSysSnmpVersion OBJECT-TYPE
			SYNTAX INTEGER
				{
				snmpv1(1),
				snmpv2c(2),
				snmpv3(3),
				all(4)
				}
			MAX-ACCESS read-write
			STATUS current
			DESCRIPTION
				"The version of the Trap PDUs forwarded to the host.
				default v1 v2 v3 supported."
			DEFVAL { 4 }
			::= { topSysGlobalObjects 3 }

		
		-- 1.3.6.1.4.1.32285.11.2.3.1.1.4
		topSysReadCommunity OBJECT-TYPE
			SYNTAX OCTET STRING (SIZE (1..63))
			MAX-ACCESS read-write
			STATUS current
			DESCRIPTION
				"snmp read community"
			DEFVAL { "public" }
			::= { topSysGlobalObjects 4 }

		
		-- 1.3.6.1.4.1.32285.11.2.3.1.1.5
		topSysWriteCommunity OBJECT-TYPE
			SYNTAX OCTET STRING (SIZE (1..63))
			MAX-ACCESS read-write
			STATUS current
			DESCRIPTION
				"snmp write community"
			DEFVAL { "private" }
			::= { topSysGlobalObjects 5 }

		
		-- 1.3.6.1.4.1.32285.11.2.3.1.1.6
		topSysSnmpPort OBJECT-TYPE
			SYNTAX INTEGER (161 | 1025..65534)
			MAX-ACCESS read-write
			STATUS current
			DESCRIPTION
				"not supported at present."
			::= { topSysGlobalObjects 6 }

		
		-- 1.3.6.1.4.1.32285.11.2.3.1.1.7
		topSysInBandMaxBW OBJECT-TYPE
			SYNTAX INTEGER (1..3000)
			UNITS "pps"
			MAX-ACCESS read-write
			STATUS current
			DESCRIPTION
				"Max bandwidth, unit:pps"
			::= { topSysGlobalObjects 7 }

		
		-- 1.3.6.1.4.1.32285.11.2.3.1.1.8
		topSysTimeZoneName OBJECT-TYPE
			SYNTAX OCTET STRING (SIZE (1..31))
			MAX-ACCESS read-write
			STATUS current
			DESCRIPTION
				"System clock time zone-name, default:DefaultZoneName."
			DEFVAL { "DefaultZoneName" }
			::= { topSysGlobalObjects 8 }

		
		-- 1.3.6.1.4.1.32285.11.2.3.1.1.9
		topSysTimeZoneOpFlag OBJECT-TYPE
			SYNTAX INTEGER
				{
				minus(0),
				add(1)
				}
			MAX-ACCESS read-write
			STATUS current
			DESCRIPTION
				"Zone-time  operator:0-minus 1-add"
			::= { topSysGlobalObjects 9 }

		
		-- 1.3.6.1.4.1.32285.11.2.3.1.1.10
		topSysTimeZoneOffsetHour OBJECT-TYPE
			SYNTAX INTEGER (0..12)
			MAX-ACCESS read-write
			STATUS current
			DESCRIPTION
				"Zone-time offset-hour."
			::= { topSysGlobalObjects 10 }

		
		-- 1.3.6.1.4.1.32285.11.2.3.1.1.11
		topSysTimeZoneOffsetMin OBJECT-TYPE
			SYNTAX INTEGER (0..59)
			MAX-ACCESS read-write
			STATUS current
			DESCRIPTION
				"Zone-time offset-minute."
			::= { topSysGlobalObjects 11 }

		
		-- 1.3.6.1.4.1.32285.11.2.3.1.2
		topSysOltObjects OBJECT IDENTIFIER ::= { topSystemObjects 2 }

		
		-- 1.3.6.1.4.1.32285.11.2.3.1.2.1
		topSysOltRackNum OBJECT-TYPE
			SYNTAX INTEGER
			MAX-ACCESS read-write
			STATUS current
			DESCRIPTION
				"ID of the cabinet, which contains the cuurent OLT.
				Staring index is 1."
			::= { topSysOltObjects 1 }

		
		-- 1.3.6.1.4.1.32285.11.2.3.1.2.2
		topSysOltFrameNum OBJECT-TYPE
			SYNTAX INTEGER
			MAX-ACCESS read-write
			STATUS current
			DESCRIPTION
				"ID of the OLT frame, which indicate the index or postion 
				in the current cabinet, and started with 1."
			::= { topSysOltObjects 2 }

		
		-- 1.3.6.1.4.1.32285.11.2.3.1.2.3
		topSysOltSave OBJECT-TYPE
			SYNTAX INTEGER
				{
				noOperation(0),
				save(1)
				}
			MAX-ACCESS read-write
			STATUS current
			DESCRIPTION
				"save(1) current config to OLT, and noOperation(0),
				other values are reserved."
			::= { topSysOltObjects 3 }

		
		-- 1.3.6.1.4.1.32285.11.2.3.1.2.4
		topSysOltSaveStatus OBJECT-TYPE
			SYNTAX INTEGER
				{
				saving(1),
				savedOrReady(2),
				savedFail(3)
				}
			MAX-ACCESS read-only
			STATUS current
			DESCRIPTION
				"save status. saving(1) represent in progress of saving operation,
				saved(2) represent completion of saving operation,
				savedFail(3) represent failure of saving operation."
			::= { topSysOltObjects 4 }

		
		-- 1.3.6.1.4.1.32285.11.2.3.1.2.5
		topSysOltReset OBJECT-TYPE
			SYNTAX INTEGER
				{
				noOperation(0),
				reset(1)
				}
			MAX-ACCESS read-write
			STATUS current
			DESCRIPTION
				"Reset OLT system, including MPU and all other boards under this OLT.
				noOperation(0), and other values are reserved."
			::= { topSysOltObjects 5 }

		
		-- 1.3.6.1.4.1.32285.11.2.3.1.2.6
		topSysOltRestoreFactoryConfig OBJECT-TYPE
			SYNTAX INTEGER
				{
				noOperation(0),
				restore(1)
				}
			MAX-ACCESS read-write
			STATUS current
			DESCRIPTION
				"Description."
			DEFVAL { 0 }
			::= { topSysOltObjects 6 }

		
		-- 1.3.6.1.4.1.32285.11.2.3.1.2.7
		topSysOltSoftwareVersion OBJECT-TYPE
			SYNTAX OCTET STRING
			MAX-ACCESS read-only
			STATUS current
			DESCRIPTION
				"Description."
			::= { topSysOltObjects 7 }

		
		-- 1.3.6.1.4.1.32285.11.2.3.1.2.8
		topSysOltOpenStatus OBJECT-TYPE
			SYNTAX INTEGER
				{
				open(1),
				close(2),
				notsupport(255)
				}
			MAX-ACCESS read-only
			STATUS current
			DESCRIPTION
				"Shell status of wild OLT:1.open(1)2.close(2)3.not support(255)"
			::= { topSysOltObjects 8 }

		

		-- 1.3.6.1.4.1.32285.11.2.3.1.3
		topSysBoardObjects OBJECT IDENTIFIER ::= { topSystemObjects 3 }

		
		-- 1.3.6.1.4.1.32285.11.2.3.1.3.1
		topSysBoardTable OBJECT-TYPE
			SYNTAX SEQUENCE OF TopSysBoardEntry
			MAX-ACCESS not-accessible
			STATUS current
			DESCRIPTION
				"This table shall include rows for all slots, including the slots has
				a presence state of 'NotInstalled'. In case of board absence, 
				return 0."
			::= { topSysBoardObjects 1 }

		
		-- 1.3.6.1.4.1.32285.11.2.3.1.3.1.1
		topSysBoardEntry OBJECT-TYPE
			SYNTAX TopSysBoardEntry
			MAX-ACCESS not-accessible
			STATUS current
			DESCRIPTION
				"The slot number within the epon chassis. This is used
				as the index into topSysBoardEntry."
			INDEX { topSysBdSlotIndex }
			::= { topSysBoardTable 1 }

		
		TopSysBoardEntry ::=
			SEQUENCE { 
				topSysBdSlotIndex
					TopEPonSlotIndex,
				topSysBdPreConfigType
					INTEGER,
				topSysBdActualType
					INTEGER,
				topSysBdCPUUseRatio
					INTEGER,
				topSysBdlMemSize
					INTEGER,
				topSysBdFreeMemSize
					INTEGER,
				topSysBdTotalFlashOctets
					INTEGER,
				topSysBdFreeFlashOctets
					INTEGER,
				topSysBdCurrentTemperature
					INTEGER,
				topSysBdTempDetectEnable
					INTEGER,
				topSysBdLampStatus
					INTEGER,
				topSysBdReset
					INTEGER
			 }

		-- 1.3.6.1.4.1.32285.11.2.3.1.3.1.1.1
		topSysBdSlotIndex OBJECT-TYPE
			SYNTAX TopEPonSlotIndex
			MAX-ACCESS not-accessible
			STATUS current
			DESCRIPTION
				"The slot number within the epon chassis. This is used
				as the index into eponSlotStatustable."
			::= { topSysBoardEntry 1 }

		
		-- 1.3.6.1.4.1.32285.11.2.3.1.3.1.1.2
		topSysBdPreConfigType OBJECT-TYPE
			SYNTAX INTEGER
				{
				non-board(0),
				mpua(1),
				mpub(2),
				epua(3),
				epub(4),
				geua(5),
				geub(6),
				xgua(7),
				xgub(8),
				xguc(9),
				xpua(10),
				mpu-geua(11),
				mpu-geub(12),
				mpu-xguc(13),
				gpua(14),
				epuc(15),
				epud(16),
				meua(17),
				meub(18),
				mefa(19),
				mefb(20),
				unknown(255)
				}
			MAX-ACCESS read-write
			STATUS current
			DESCRIPTION
				"This object provides the model of the card actually inserted
				into the corresponding slot in the chassis. Only the first byte
				in this integer value is available.PreConfig is read-only for Master/Slave board."
			::= { topSysBoardEntry 2 }

		
		-- 1.3.6.1.4.1.32285.11.2.3.1.3.1.1.3
		topSysBdActualType OBJECT-TYPE
			SYNTAX INTEGER
				{
				non-board(0),
				mpua(1),
				mpub(2),
				epua(3),
				epub(4),
				geua(5),
				geub(6),
				xgua(7),
				xgub(8),
				xguc(9),
				xpua(10),
				vpua(11),
				meua(12),
				meub(13),
				mefa(14),
				mefb(15),
				unknown(255)
				}
			MAX-ACCESS read-only
			STATUS current
			DESCRIPTION
				"actual board type"
			::= { topSysBoardEntry 3 }

		
		-- 1.3.6.1.4.1.32285.11.2.3.1.3.1.1.4
		topSysBdCPUUseRatio OBJECT-TYPE
			SYNTAX INTEGER (1..100)
			MAX-ACCESS read-only
			STATUS current
			DESCRIPTION
				"The using ratio of the CPU."
			::= { topSysBoardEntry 4 }

		
		-- 1.3.6.1.4.1.32285.11.2.3.1.3.1.1.5
		topSysBdlMemSize OBJECT-TYPE
			SYNTAX INTEGER
			MAX-ACCESS read-only
			STATUS current
			DESCRIPTION
				"The total memory size in MB."
			::= { topSysBoardEntry 5 }

		
		-- 1.3.6.1.4.1.32285.11.2.3.1.3.1.1.6
		topSysBdFreeMemSize OBJECT-TYPE
			SYNTAX INTEGER
			MAX-ACCESS read-only
			STATUS current
			DESCRIPTION
				"The free memory size in MPUA and EPUA,in units of byte."
			::= { topSysBoardEntry 6 }

		
		-- 1.3.6.1.4.1.32285.11.2.3.1.3.1.1.7
		topSysBdTotalFlashOctets OBJECT-TYPE
			SYNTAX INTEGER
			MAX-ACCESS read-only
			STATUS current
			DESCRIPTION
				"The total size of the flash in MCU or LPU,in units of kilo byte."
			::= { topSysBoardEntry 7 }

		
		-- 1.3.6.1.4.1.32285.11.2.3.1.3.1.1.8
		topSysBdFreeFlashOctets OBJECT-TYPE
			SYNTAX INTEGER
			MAX-ACCESS read-only
			STATUS current
			DESCRIPTION
				"The total size of the flash in MCU or LPU,in units of kilo byte."
			::= { topSysBoardEntry 8 }

		
		-- 1.3.6.1.4.1.32285.11.2.3.1.3.1.1.9
		topSysBdCurrentTemperature OBJECT-TYPE
			SYNTAX INTEGER
			MAX-ACCESS read-only
			STATUS current
			DESCRIPTION
				"The current temprature"
			::= { topSysBoardEntry 9 }

		
		-- 1.3.6.1.4.1.32285.11.2.3.1.3.1.1.10
		topSysBdTempDetectEnable OBJECT-TYPE
			SYNTAX INTEGER
				{
				enable(1),
				disable(2)
				}
			MAX-ACCESS read-write
			STATUS current
			DESCRIPTION
				"enable/disable temprature detecting"
			::= { topSysBoardEntry 10 }

		
		-- 1.3.6.1.4.1.32285.11.2.3.1.3.1.1.11
		topSysBdLampStatus OBJECT-TYPE
			SYNTAX INTEGER
			MAX-ACCESS read-only
			STATUS current
			DESCRIPTION
				"LAMP status.
				BOARD-TYPE  MSB-BYTE 2nd-BYTE 3rd-BYTE LSB-BYTE
				MPU       SD(1)MS(0) RUN      ALARM    reserved
				EPU         reserved RUN      ALARM    reserved
				GEUA        reserved RUN      ALARM    reserved
				XGUA        reserved RUN      ALARM    reserved
				FAN         reserved RUN      ALARM    reserved
				For MSB-BYTE:
				  the bit 0 for HA and 1-master, 0-slave,
				  the bit 1 for SD card present status and 1-SD present,0-SD unpresent;
				For 2nd-BYTE:
				  1-running, 2-loading;
				For 3rd-BYTE:
				  1-no alarm, 2-alarm;
				For LSB-BYTE:
				  the reserved bytes are set to 0."
			::= { topSysBoardEntry 11 }

		
		-- 1.3.6.1.4.1.32285.11.2.3.1.3.1.1.12
		topSysBdReset OBJECT-TYPE
			SYNTAX INTEGER
				{
				noOperation(0),
				reset(1)
				}
			MAX-ACCESS read-write
			STATUS current
			DESCRIPTION
				"reset(1) board, noOperation(0), other values are reserved."
			::= { topSysBoardEntry 12 }


		-- 1.3.6.1.4.1.32285.11.2.3.1.3.1.2
		topSysBoardMapTable OBJECT-TYPE
			SYNTAX SEQUENCE OF TopSysBoardMapEntry
			MAX-ACCESS not-accessible
			STATUS current
			DESCRIPTION
				"This table is for physical slot mapping to logic slot only."
			::= { topSysBoardObjects 2 }

		
		-- 1.3.6.1.4.1.32285.11.2.3.1.3.1.2
		topSysBoardMapEntry OBJECT-TYPE
			SYNTAX TopSysBoardMapEntry
			MAX-ACCESS not-accessible
			STATUS current
			DESCRIPTION
				"The slot number within the epon chassis. This is used
				as the index into topSysBoardMapEntry."
			INDEX { topSysBdMapPhySlotIndex }
			::= { topSysBoardMapTable 1 }

		
		TopSysBoardMapEntry ::=
			SEQUENCE { 
				topSysBdMapPhySlotIndex
					TopEPonSlotIndex,
				topSysBdMapLogSlot
					INTEGER
			 }

		-- 1.3.6.1.4.1.32285.11.2.3.1.3.1.2.1
		topSysBdMapPhySlotIndex OBJECT-TYPE
			SYNTAX TopEPonSlotIndex
			MAX-ACCESS not-accessible
			STATUS current
			DESCRIPTION
				"The slot number within the epon chassis. This is used
				as the index into eponSlotStatustable."
			::= { topSysBoardMapEntry 1 }

		-- 1.3.6.1.4.1.32285.11.2.3.1.3.1.2.2
		topSysBdMapLogSlot OBJECT-TYPE
			SYNTAX INTEGER
			MAX-ACCESS read-only
			STATUS current
			DESCRIPTION
				"0-logical slot number of the current active master control board,
				for instance, logical slot 0 present for physical slot 9&10.
				this table will allowed to access on the basis of physical slot only,
				but all other service will be on the basis of logical slot."
			::= { topSysBoardMapEntry 2 }

		
		-- 1.3.6.1.4.1.32285.11.2.3.1.4
		topSysPowerObjects OBJECT IDENTIFIER ::= { topSystemObjects 4 }

		
		-- 1.3.6.1.4.1.32285.11.2.3.1.4.1
		topSysPowerPropertyTable OBJECT-TYPE
			SYNTAX SEQUENCE OF TopSysPowerPropertyEntry
			MAX-ACCESS not-accessible
			STATUS current
			DESCRIPTION
				"power management"
			::= { topSysPowerObjects 1 }

		
		-- 1.3.6.1.4.1.32285.11.2.3.1.4.1.1
		topSysPowerPropertyEntry OBJECT-TYPE
			SYNTAX TopSysPowerPropertyEntry
			MAX-ACCESS not-accessible
			STATUS current
			DESCRIPTION
				"power management entry"
			INDEX { topSysPowerCardIndex }
			::= { topSysPowerPropertyTable 1 }

		
		TopSysPowerPropertyEntry ::=
			SEQUENCE { 
				topSysPowerCardIndex
					INTEGER,
				topSysPowerSupplyType
					INTEGER,
				topSysPowerSupplyACVoltage
					INTEGER,
				topSysPowerSupplyACTemperature
					INTEGER
			 }

		-- 1.3.6.1.4.1.32285.11.2.3.1.4.1.1.1
		topSysPowerCardIndex OBJECT-TYPE
			SYNTAX INTEGER (20..21)
			MAX-ACCESS not-accessible
			STATUS current
			DESCRIPTION
				"power slot is 20,21"
			::= { topSysPowerPropertyEntry 1 }

		
		-- 1.3.6.1.4.1.32285.11.2.3.1.4.1.1.2
		topSysPowerSupplyType OBJECT-TYPE
			SYNTAX INTEGER
				{
				powerDC(1),
				powerAC(2)
				}
			MAX-ACCESS read-only
			STATUS current
			DESCRIPTION
				"DC-1;AC-2"
			::= { topSysPowerPropertyEntry 2 }

		
		-- 1.3.6.1.4.1.32285.11.2.3.1.4.1.1.3
		topSysPowerSupplyACVoltage OBJECT-TYPE
			SYNTAX INTEGER
			MAX-ACCESS read-only
			STATUS current
			DESCRIPTION
				"AC power voltage"
			::= { topSysPowerPropertyEntry 3 }

		
		-- 1.3.6.1.4.1.32285.11.2.3.1.4.1.1.4
		topSysPowerSupplyACTemperature OBJECT-TYPE
			SYNTAX INTEGER
			MAX-ACCESS read-only
			STATUS current
			DESCRIPTION
				"AC power temperature"
			::= { topSysPowerPropertyEntry 4 }

		
		-- 1.3.6.1.4.1.32285.11.2.3.1.5
		topSysFanObjects OBJECT IDENTIFIER ::= { topSystemObjects 5 }

		
		-- 1.3.6.1.4.1.32285.11.2.3.1.5.1
		topSysFanPropertyTable OBJECT-TYPE
			SYNTAX SEQUENCE OF TopSysFanPropertyEntry
			MAX-ACCESS not-accessible
			STATUS current
			DESCRIPTION
				"fan management"
			::= { topSysFanObjects 1 }

		
		-- 1.3.6.1.4.1.32285.11.2.3.1.5.1.1
		topSysFanPropertyEntry OBJECT-TYPE
			SYNTAX TopSysFanPropertyEntry
			MAX-ACCESS not-accessible
			STATUS current
			DESCRIPTION
				"fan management entry "
			INDEX { topSysFanCardIndex, topSysFanIndex }
			::= { topSysFanPropertyTable 1 }

		
		TopSysFanPropertyEntry ::=
			SEQUENCE { 
				topSysFanCardIndex
					INTEGER,
				topSysFanIndex
					INTEGER,
				topSysFanSpeedControl
					INTEGER,
				topSysFanSpeed
					INTEGER,
				topSysFanLampStatus
					INTEGER
			 }

		-- 1.3.6.1.4.1.32285.11.2.3.1.5.1.1.1
		topSysFanCardIndex OBJECT-TYPE
			SYNTAX INTEGER (19)
			MAX-ACCESS not-accessible
			STATUS current
			DESCRIPTION
				"fan slot index"
			::= { topSysFanPropertyEntry 1 }

		
		-- 1.3.6.1.4.1.32285.11.2.3.1.5.1.1.2
		topSysFanIndex OBJECT-TYPE
			SYNTAX INTEGER (1..3)
			MAX-ACCESS not-accessible
			STATUS current
			DESCRIPTION
				"fan slot index"
			::= { topSysFanPropertyEntry 2 }

		
		-- 1.3.6.1.4.1.32285.11.2.3.1.5.1.1.3
		topSysFanSpeedControl OBJECT-TYPE
			SYNTAX INTEGER
				{
				autoSpeed(1),
				lowSpeed(2),
				middleSpeed(3),
				highSpeed(4)
				}
			MAX-ACCESS read-write
			STATUS current
			DESCRIPTION
				"fan speed level"
			::= { topSysFanPropertyEntry 3 }

		
		-- 1.3.6.1.4.1.32285.11.2.3.1.5.1.1.4
		topSysFanSpeed OBJECT-TYPE
			SYNTAX INTEGER
			MAX-ACCESS read-only
			STATUS current
			DESCRIPTION
				"fan speed unit:rps"
			::= { topSysFanPropertyEntry 4 }

		
		-- 1.3.6.1.4.1.32285.11.2.3.1.5.1.1.5
		topSysFanLampStatus OBJECT-TYPE
			SYNTAX INTEGER
			MAX-ACCESS read-only
			STATUS current
			DESCRIPTION
				"LAMP status.
				BOARD-TYPE  MSB-BYTE 2nd-BYTE 3rd-BYTE LSB-BYTE
				FAN         reserved RUN      ALARM    reserved
				for each byte, 
				2nd-BYTE    1-running, 2-loading.
				3rd-BYTE    1-no alarm, 2-alarm.
				the reserved bytes are set to 0."
			::= { topSysFanPropertyEntry 5 }

		
		-- 1.3.6.1.4.1.32285.11.2.3.1.6
		topSysHaMgmtObjects OBJECT IDENTIFIER ::= { topSystemObjects 6 }

		
		-- 1.3.6.1.4.1.32285.11.2.3.1.6.1
		topSysMasterSlotNum OBJECT-TYPE
			SYNTAX INTEGER (9..10)
			MAX-ACCESS read-only
			STATUS current
			DESCRIPTION
				"The number of slot which this mcu resides in."
			::= { topSysHaMgmtObjects 1 }

		
		-- 1.3.6.1.4.1.32285.11.2.3.1.6.2
		topSysMasterSlaveSynAction OBJECT-TYPE
			SYNTAX INTEGER
				{
				noOperation(0), 
				syncApp(1),
				syncConfig(2)
				}
			MAX-ACCESS read-write
			STATUS current
			DESCRIPTION
				"Sync app soft or config for master to slave."
			::= { topSysHaMgmtObjects 2 }
			
		
		-- 1.3.6.1.4.1.32285.11.2.3.1.6.3
		topSysMasterSlaveSyncStatus OBJECT-TYPE
			SYNTAX INTEGER
				{
				idle(0),
				syncAppInprogress(1),
				syncCfgInprogress(2),
				syncAppFail(3),
				syncAppSucc(4),
				syncCfgFail(5),
				syncCfgSucc(6)
				}
			MAX-ACCESS read-only
			STATUS current
			DESCRIPTION
				"sync status."
			::= { topSysHaMgmtObjects 3 }

		-- 1.3.6.1.4.1.32285.11.2.3.1.6.4
		topSysMasterSlaveEnable OBJECT-TYPE
			SYNTAX INTEGER
				{
				enable(1),
				disable(2)
				}
			MAX-ACCESS read-write
			STATUS current
			DESCRIPTION
				"Description."
			::= { topSysHaMgmtObjects 4 }
			
		-- 1.3.6.1.4.1.32285.11.2.3.1.7
		topSysErrInfoObjects OBJECT IDENTIFIER ::= { topSystemObjects 7 }

		-- 1.3.6.1.4.1.32285.11.2.3.1.7.1
		topSysErrInfoTable OBJECT-TYPE
			SYNTAX SEQUENCE OF TopSysErrInfoEntry
			MAX-ACCESS not-accessible
			STATUS current
			DESCRIPTION
				"error code information."
			::= { topSysErrInfoObjects 1 }
				
		-- 1.3.6.1.4.1.32285.11.2.3.1.7.1.1
		topSysErrInfoEntry OBJECT-TYPE
			SYNTAX TopSysErrInfoEntry
			MAX-ACCESS not-accessible
			STATUS current
			DESCRIPTION
				"error code information entry."
			INDEX { topSysErrInfoLangIndex, topSysErrInfoIdIndex }
			::= { topSysErrInfoTable 1 }
		TopSysErrInfoEntry ::=
			SEQUENCE { 
				topSysErrInfoLangIndex
					INTEGER,
				topSysErrInfoIdIndex
					INTEGER,
				topSysErrInfoDescription
					OCTET STRING
			 }
			 
		-- 1.3.6.1.4.1.32285.11.2.3.1.7.1.1.1
		topSysErrInfoLangIndex OBJECT-TYPE
			SYNTAX INTEGER (0..255)
			MAX-ACCESS not-accessible
			STATUS current
			DESCRIPTION
				"error information language index: English(0), Simplified Chinese(1), Traditional Chinese(2)."
			::= { topSysErrInfoEntry 1 }
			
		-- 1.3.6.1.4.1.32285.11.2.3.1.7.1.1.2
		topSysErrInfoIdIndex OBJECT-TYPE
			SYNTAX INTEGER (1025..16777216)
			MAX-ACCESS not-accessible
			STATUS current
			DESCRIPTION
				"error information id index."
			::= { topSysErrInfoEntry 2 }

		-- 1.3.6.1.4.1.32285.11.2.3.1.7.1.1.3
		topSysErrInfoDescription OBJECT-TYPE
			SYNTAX OCTET STRING (SIZE (1..63))
			MAX-ACCESS read-only
			STATUS current
			DESCRIPTION
				"error information description."
			::= { topSysErrInfoEntry 3 }

		
		-- 1.3.6.1.4.1.32285.11.2.3.1.8
		topSysMacObjects OBJECT IDENTIFIER ::= { topSystemObjects 8 }

		
		-- 1.3.6.1.4.1.32285.11.2.3.1.8.1
		topSysMacSyncObjects OBJECT IDENTIFIER ::= { topSysMacObjects 1 }

		
		-- 1.3.6.1.4.1.32285.11.2.3.1.8.1.1
		topSysMacSyncSet OBJECT-TYPE
			SYNTAX INTEGER { syncAction(1) }
			MAX-ACCESS read-write
			STATUS current
			DESCRIPTION
				"Description."
			::= { topSysMacSyncObjects 1 }

		
		-- 1.3.6.1.4.1.32285.11.2.3.1.8.2
		topSysMacTable OBJECT-TYPE
			SYNTAX SEQUENCE OF TopSysMacEntry
			MAX-ACCESS not-accessible
			STATUS current
			DESCRIPTION
				"Description."
			::= { topSysMacObjects 2 }

		
		-- 1.3.6.1.4.1.32285.11.2.3.1.8.2.1
		topSysMacEntry OBJECT-TYPE
			SYNTAX TopSysMacEntry
			MAX-ACCESS not-accessible
			STATUS current
			DESCRIPTION
				"Description."
			INDEX { topSysMacIndex }
			::= { topSysMacTable 1 }

		
		TopSysMacEntry ::=
			SEQUENCE { 
				topSysMacIndex
					INTEGER,
				topSysMacAddr
					MacAddress,
				topSysMacVid
					INTEGER,
				topSysMacSlot
					INTEGER,
				topSysMacPort
					INTEGER,
				topSysMacFlag
					INTEGER
			 }

		-- 1.3.6.1.4.1.32285.11.2.3.1.8.2.1.1
		topSysMacIndex OBJECT-TYPE
			SYNTAX INTEGER (0..32767)
			MAX-ACCESS not-accessible
			STATUS current
			DESCRIPTION
				"Description."
			::= { topSysMacEntry 1 }

		
		-- 1.3.6.1.4.1.32285.11.2.3.1.8.2.1.2
		topSysMacAddr OBJECT-TYPE
			SYNTAX MacAddress
			MAX-ACCESS read-only
			STATUS current
			DESCRIPTION
				"Description."
			::= { topSysMacEntry 2 }

		
		-- 1.3.6.1.4.1.32285.11.2.3.1.8.2.1.3
		topSysMacVid OBJECT-TYPE
			SYNTAX INTEGER (1..4094)
			MAX-ACCESS read-only
			STATUS current
			DESCRIPTION
				"Description."
			::= { topSysMacEntry 3 }

		
		-- 1.3.6.1.4.1.32285.11.2.3.1.8.2.1.4
		topSysMacSlot OBJECT-TYPE
			SYNTAX INTEGER
			MAX-ACCESS read-only
			STATUS current
			DESCRIPTION
				"Description."
			::= { topSysMacEntry 4 }

		
		-- 1.3.6.1.4.1.32285.11.2.3.1.8.2.1.5
		topSysMacPort OBJECT-TYPE
			SYNTAX INTEGER
			MAX-ACCESS read-only
			STATUS current
			DESCRIPTION
				"Description."
			::= { topSysMacEntry 5 }

		
		-- 1.3.6.1.4.1.32285.11.2.3.1.8.2.1.6
		topSysMacFlag OBJECT-TYPE
			SYNTAX INTEGER
				{
				dynamic(0),
				static(1)
				}
			MAX-ACCESS read-only
			STATUS current
			DESCRIPTION
				"Description."
			::= { topSysMacEntry 6 }

		
		-- 1.3.6.1.4.1.32285.11.2.3.1.8.3
		topSysMacAgeObjects OBJECT IDENTIFIER ::= { topSysMacObjects 3 }

		
		-- 1.3.6.1.4.1.32285.11.2.3.1.8.3.1
		topSysMacAgingTime OBJECT-TYPE
			SYNTAX INTEGER (0..50000)
			UNITS "sec"
			MAX-ACCESS read-write
			STATUS current
			DESCRIPTION
				"Description."
			DEFVAL { 1200 }
			::= { topSysMacAgeObjects 1 }

		
		-- 1.3.6.1.4.1.32285.11.2.3.1.8.3.2
		topSysArpAgingTime OBJECT-TYPE
			SYNTAX INTEGER (1..60)
			UNITS "min"
			MAX-ACCESS read-write
			STATUS current
			DESCRIPTION
				"Description."
			DEFVAL { 20 }
			::= { topSysMacAgeObjects 2 }

		
-- The table just only supports get-function, no walk-function.
		-- 1.3.6.1.4.1.32285.11.2.3.1.8.4
		topSysMacLocationMapTable OBJECT-TYPE
			SYNTAX SEQUENCE OF TopSysMacLocationMapEntry
			MAX-ACCESS not-accessible
			STATUS current
			DESCRIPTION
				"Description."
			::= { topSysMacObjects 4 }

		
		-- 1.3.6.1.4.1.32285.11.2.3.1.8.4.1
		topSysMacLocationMapEntry OBJECT-TYPE
			SYNTAX TopSysMacLocationMapEntry
			MAX-ACCESS not-accessible
			STATUS current
			DESCRIPTION
				"Description."
			INDEX { topSysMacLocMapIndex }
			::= { topSysMacLocationMapTable 1 }

		
		TopSysMacLocationMapEntry ::=
			SEQUENCE { 
				topSysMacLocMapIndex
					MacAddress,
				topSysMacLocMapSlot
					INTEGER,
				topSysMacLocMapPort
					INTEGER,
				topSysMacLocMapOnuId
					INTEGER,
				topSysMacLocMapUniId
					INTEGER
			 }

		-- 1.3.6.1.4.1.32285.11.2.3.1.8.4.1.1
		topSysMacLocMapIndex OBJECT-TYPE
			SYNTAX MacAddress
			MAX-ACCESS not-accessible
			STATUS current
			DESCRIPTION
				"Description."
			::= { topSysMacLocationMapEntry 1 }

		
		-- 1.3.6.1.4.1.32285.11.2.3.1.8.4.1.2
		topSysMacLocMapSlot OBJECT-TYPE
			SYNTAX INTEGER
			MAX-ACCESS read-only
			STATUS current
			DESCRIPTION
				"Description."
			::= { topSysMacLocationMapEntry 2 }

		
		-- 1.3.6.1.4.1.32285.11.2.3.1.8.4.1.3
		topSysMacLocMapPort OBJECT-TYPE
			SYNTAX INTEGER
			MAX-ACCESS read-only
			STATUS current
			DESCRIPTION
				"Description."
			::= { topSysMacLocationMapEntry 3 }

		
		-- 1.3.6.1.4.1.32285.11.2.3.1.8.4.1.4
		topSysMacLocMapOnuId OBJECT-TYPE
			SYNTAX INTEGER
			MAX-ACCESS read-only
			STATUS current
			DESCRIPTION
				"Description."
			::= { topSysMacLocationMapEntry 4 }

		
		-- 1.3.6.1.4.1.32285.11.2.3.1.8.4.1.5
		topSysMacLocMapUniId OBJECT-TYPE
			SYNTAX INTEGER
			MAX-ACCESS read-only
			STATUS current
			DESCRIPTION
				"Description."
			::= { topSysMacLocationMapEntry 5 }

		
		-- 1.3.6.1.4.1.32285.11.2.3.1.9
		topSysOptCfgObjects OBJECT IDENTIFIER ::= { topSystemObjects 9 }

		
		-- 1.3.6.1.4.1.32285.11.2.3.1.9.1
		topSysOptAlarmTable OBJECT-TYPE
			SYNTAX SEQUENCE OF TopSysOptAlarmEntry
			MAX-ACCESS not-accessible
			STATUS current
			DESCRIPTION
				"Description."
			::= { topSysOptCfgObjects 1 }

		
		-- 1.3.6.1.4.1.32285.11.2.3.1.9.1.1
		topSysOptAlarmEntry OBJECT-TYPE
			SYNTAX TopSysOptAlarmEntry
			MAX-ACCESS not-accessible
			STATUS current
			DESCRIPTION
				"Description."
			INDEX { topSysOptAlarmIndex }
			::= { topSysOptAlarmTable 1 }

		
		TopSysOptAlarmEntry ::=
			SEQUENCE { 
				topSysOptAlarmIndex
					INTEGER,
				topSysOptAlarmSwitch
					INTEGER,
				topSysOptAlarmSoapTime
					INTEGER
			 }

		-- 1.3.6.1.4.1.32285.11.2.3.1.9.1.1.1
		topSysOptAlarmIndex OBJECT-TYPE
			SYNTAX INTEGER
			MAX-ACCESS not-accessible
			STATUS current
			DESCRIPTION
				"Index for optical alarm."
			::= { topSysOptAlarmEntry 1 }

		
		-- 1.3.6.1.4.1.32285.11.2.3.1.9.1.1.2
		topSysOptAlarmSwitch OBJECT-TYPE
			SYNTAX INTEGER
			MAX-ACCESS read-write
			STATUS current
			DESCRIPTION
				"The optical alarm global switch state:1--enable,2--disable."
			::= { topSysOptAlarmEntry 2 }

		
		-- 1.3.6.1.4.1.32285.11.2.3.1.9.1.1.3
		topSysOptAlarmSoapTime OBJECT-TYPE
			SYNTAX INTEGER
			MAX-ACCESS read-write
			STATUS current
			DESCRIPTION
				"Soap time :at least 5,must in units of 5 seconds,such as 5,10,15,20."
			::= { topSysOptAlarmEntry 3 }

		-- 1.3.6.1.4.1.32285.11.2.3.1.10
		topSysOltUpgradeObjects OBJECT IDENTIFIER ::= { topSystemObjects 10 }

		
		-- 1.3.6.1.4.1.32285.11.2.3.1.10.1
		topSysCpldUpgTable OBJECT-TYPE
			SYNTAX SEQUENCE OF TopSysCpldUpgEntry
			MAX-ACCESS not-accessible
			STATUS current
			DESCRIPTION
				"Description."
			::= { topSysOltUpgradeObjects 1 }

		
		-- 1.3.6.1.4.1.32285.11.2.3.1.10.1.1
		topSysCpldUpgEntry OBJECT-TYPE
			SYNTAX TopSysCpldUpgEntry
			MAX-ACCESS not-accessible
			STATUS current
			DESCRIPTION
				"Description."
			INDEX { topSysCpldUpgIdx }
			::= { topSysCpldUpgTable 1 }

		
		TopSysCpldUpgEntry ::=
			SEQUENCE { 
				topSysCpldUpgIdx
					INTEGER,
				topSysCpldUpgSlot
					INTEGER,
				topSysCpldUpgStatus
					INTEGER
			 }

		-- 1.3.6.1.4.1.32285.11.2.3.1.10.1.1.1
		topSysCpldUpgIdx OBJECT-TYPE
			SYNTAX INTEGER
			MAX-ACCESS not-accessible
			STATUS current
			DESCRIPTION
				"Upgrade Index."
			::= { topSysCpldUpgEntry 1 }

		
		-- 1.3.6.1.4.1.32285.11.2.3.1.10.1.1.2
		topSysCpldUpgSlot OBJECT-TYPE
			SYNTAX INTEGER
			MAX-ACCESS read-write
			STATUS current
			DESCRIPTION
				"slot:pn8601(1-18);pn8602(1-3);pn8603(1-8)."
			::= { topSysCpldUpgEntry 2 }

		
		-- 1.3.6.1.4.1.32285.11.2.3.1.10.1.1.3
		topSysCpldUpgStatus OBJECT-TYPE
			SYNTAX INTEGER
			MAX-ACCESS read-only
			STATUS current
			DESCRIPTION
				"Upgrade status:1-idle;2-upgrading;3-success;4-failure.."
			::= { topSysCpldUpgEntry 3 }

		
		-- 1.3.6.1.4.1.32285.11.2.3.1.10.2
		topSysBootromUpgTable OBJECT-TYPE
			SYNTAX SEQUENCE OF TopSysBootromUpgEntry
			MAX-ACCESS not-accessible
			STATUS current
			DESCRIPTION
				"Description."
			::= { topSysOltUpgradeObjects 2 }

		
		-- 1.3.6.1.4.1.32285.11.2.3.1.10.2.1
		topSysBootromUpgEntry OBJECT-TYPE
			SYNTAX TopSysBootromUpgEntry
			MAX-ACCESS not-accessible
			STATUS current
			DESCRIPTION
				"Description."
			INDEX { topSysBootromUpgIdx }
			::= { topSysBootromUpgTable 1 }

		
		TopSysBootromUpgEntry ::=
			SEQUENCE { 
				topSysBootromUpgIdx
					INTEGER,
				topSysBootromUpgSlot
					INTEGER,
				topSysBootromUpgStatus
					INTEGER
			 }

		-- 1.3.6.1.4.1.32285.11.2.3.1.10.2.1.1
		topSysBootromUpgIdx OBJECT-TYPE
			SYNTAX INTEGER
			MAX-ACCESS not-accessible
			STATUS current
			DESCRIPTION
				"Upgrade index."
			::= { topSysBootromUpgEntry 1 }

		
		-- 1.3.6.1.4.1.32285.11.2.3.1.10.2.1.2
		topSysBootromUpgSlot OBJECT-TYPE
			SYNTAX INTEGER
			MAX-ACCESS read-write
			STATUS current
			DESCRIPTION
				"slot:pn8601(1-18);pn8602(1-3);pn8603(1-8)."
			::= { topSysBootromUpgEntry 2 }

		
		-- 1.3.6.1.4.1.32285.11.2.3.1.10.2.1.3
		topSysBootromUpgStatus OBJECT-TYPE
			SYNTAX INTEGER
			MAX-ACCESS read-only
			STATUS current
			DESCRIPTION
				"Upgrade status:1-idle;2-upgrading;3-success;4-failure."
			::= { topSysBootromUpgEntry 3 }

		
		-- 1.3.6.1.4.1.32285.11.2.3.1.11
		topSysFileDirObjects OBJECT IDENTIFIER ::= { topSystemObjects 11 }

		
		-- 1.3.6.1.4.1.32285.11.2.3.1.11.1
		topSysFileDirTable OBJECT-TYPE
			SYNTAX SEQUENCE OF TopSysFileDirEntry
			MAX-ACCESS not-accessible
			STATUS current
			DESCRIPTION
				"Description."
			::= { topSysFileDirObjects 1 }

		
		-- 1.3.6.1.4.1.32285.11.2.3.1.11.1.1
		topSysFileDirEntry OBJECT-TYPE
			SYNTAX TopSysFileDirEntry
			MAX-ACCESS not-accessible
			STATUS current
			DESCRIPTION
				"Description."
			INDEX { topSysFileDirTypeIdx }
			::= { topSysFileDirTable 1 }

		
		TopSysFileDirEntry ::=
			SEQUENCE { 
				topSysFileDirTypeIdx
					INTEGER,
				topSysFileDirPath
					OCTET STRING,
				topSysFileDirAttr
					INTEGER
			 }

		-- 1.3.6.1.4.1.32285.11.2.3.1.11.1.1.1
		topSysFileDirTypeIdx OBJECT-TYPE
			SYNTAX INTEGER
				{
				file-mpu(1),
				file-epu(2),
				file-xpu(3),
				file-gpu(4),
				file-npu(5),
				file-geu(6),
				file-xgu(7),
				file-bootrom(8),
				file-mpu-bak(9),
				file-epu-bak(10),
				file-xpu-bak(11),
				file-gpu-bak(12),
				file-npu-bak(13),
				file-geu-bak(14),
				file-xgu-bak(15),
				file-bootrom-bak(16),
				dir-onu(17),
				file-config(18),
				dir-log(19),
				file-mpub(20),
				file-mpub-bak(21),
				file-oem(22),
				dir-default-root(255)
				}
			MAX-ACCESS not-accessible
			STATUS current
			DESCRIPTION
				"Description."
			::= { topSysFileDirEntry 1 }

		
		-- 1.3.6.1.4.1.32285.11.2.3.1.11.1.1.2
		topSysFileDirPath OBJECT-TYPE
			SYNTAX OCTET STRING (SIZE (1..255))
			MAX-ACCESS read-only
			STATUS current
			DESCRIPTION
				"Description."
			::= { topSysFileDirEntry 2 }

		
		-- 1.3.6.1.4.1.32285.11.2.3.1.11.1.1.3
		topSysFileDirAttr OBJECT-TYPE
			SYNTAX INTEGER
				{
				file-path(1),
				dir-path(2)
				}
			MAX-ACCESS read-only
			STATUS current
			DESCRIPTION
				"Description."
			::= { topSysFileDirEntry 3 }

		
		-- 1.3.6.1.4.1.32285.11.2.3.1.12
		topSysIpInfoObjects OBJECT IDENTIFIER ::= { topSystemObjects 12 }

		
		-- 1.3.6.1.4.1.32285.11.2.3.1.12.1
		topSysIpLocationMapTable OBJECT-TYPE
			SYNTAX SEQUENCE OF TopSysIpLocationMapEntry
			MAX-ACCESS not-accessible
			STATUS current
			DESCRIPTION
				"IP location CPE"
			::= { topSysIpInfoObjects 1 }

		
		-- 1.3.6.1.4.1.32285.11.2.3.1.12.1.1
		topSysIpLocationMapEntry OBJECT-TYPE
			SYNTAX TopSysIpLocationMapEntry
			MAX-ACCESS not-accessible
			STATUS current
			DESCRIPTION
				"IP Location CPE."
			INDEX { topSysIpLocMapIndex }
			::= { topSysIpLocationMapTable 1 }

		
		TopSysIpLocationMapEntry ::=
			SEQUENCE { 
				topSysIpLocMapIndex
					IpAddress,
				topSysIpLocMapMac
					OCTET STRING,
				topSysIpLocMapSlot
					INTEGER,
				topSysIpLocMapPort
					INTEGER,
				topSysIpLocMapOnuId
					INTEGER,
				topDhcpIpInfoType
					INTEGER
			 }

		-- 1.3.6.1.4.1.32285.11.2.3.1.12.1.1.1
		topSysIpLocMapIndex OBJECT-TYPE
			SYNTAX IpAddress
			MAX-ACCESS not-accessible
			STATUS current
			DESCRIPTION
				"IP Address."
			::= { topSysIpLocationMapEntry 1 }

		
		-- 1.3.6.1.4.1.32285.11.2.3.1.12.1.1.2
		topSysIpLocMapMac OBJECT-TYPE
			SYNTAX OCTET STRING (SIZE (6))
			MAX-ACCESS read-only
			STATUS current
			DESCRIPTION
				"MAC Address."
			::= { topSysIpLocationMapEntry 2 }

		
		-- 1.3.6.1.4.1.32285.11.2.3.1.12.1.1.3
		topSysIpLocMapSlot OBJECT-TYPE
			SYNTAX INTEGER
			MAX-ACCESS read-only
			STATUS current
			DESCRIPTION
				"Slot ID."
			::= { topSysIpLocationMapEntry 3 }

		
		-- 1.3.6.1.4.1.32285.11.2.3.1.12.1.1.4
		topSysIpLocMapPort OBJECT-TYPE
			SYNTAX INTEGER
			MAX-ACCESS read-only
			STATUS current
			DESCRIPTION
				"PON Port ID."
			::= { topSysIpLocationMapEntry 4 }

		
		-- 1.3.6.1.4.1.32285.11.2.3.1.12.1.1.5
		topSysIpLocMapOnuId OBJECT-TYPE
			SYNTAX INTEGER
			MAX-ACCESS read-only
			STATUS current
			DESCRIPTION
				"ONU ID."
			::= { topSysIpLocationMapEntry 5 }

		
		-- 1.3.6.1.4.1.32285.11.2.3.1.12.1.1.6
		topDhcpIpInfoType OBJECT-TYPE
			SYNTAX INTEGER
				{
				cm(0),
				host(1),
				mta(2),
				stb(3)
				}
			MAX-ACCESS read-only
			STATUS current
			DESCRIPTION
				"CPE type. 0:cm,1:host,2:mta,3:stb."
			::= { topSysIpLocationMapEntry 6 }

		
		-- 1.3.6.1.4.1.32285.11.2.3.1.12.2
		topDhcpIpInfoTable OBJECT-TYPE
			SYNTAX SEQUENCE OF TopDhcpIpInfoEntry
			MAX-ACCESS not-accessible
			STATUS current
			DESCRIPTION
				"DHCP CPE Info."
			::= { topSysIpInfoObjects 2 }

		
		-- 1.3.6.1.4.1.32285.11.2.3.1.12.2.1
		topDhcpIpInfoEntry OBJECT-TYPE
			SYNTAX TopDhcpIpInfoEntry
			MAX-ACCESS not-accessible
			STATUS current
			DESCRIPTION
				"DHCP CPE Info."
			INDEX { topDhcpIpInfoSlotIndex, topDhcpIpInfoPortIndex, topDhcpIpInfoOnuIndex }
			::= { topDhcpIpInfoTable 1 }

		
		TopDhcpIpInfoEntry ::=
			SEQUENCE { 
				topDhcpIpInfoSlotIndex
					INTEGER,
				topDhcpIpInfoPortIndex
					INTEGER,
				topDhcpIpInfoOnuIndex
					INTEGER,
				topDhcpIpInfoTotal
					OCTET STRING
			 }

		-- 1.3.6.1.4.1.32285.11.2.3.1.12.2.1.1
		topDhcpIpInfoSlotIndex OBJECT-TYPE
			SYNTAX INTEGER
			MAX-ACCESS not-accessible
			STATUS current
			DESCRIPTION
				"Slot ID."
			::= { topDhcpIpInfoEntry 1 }

		
		-- 1.3.6.1.4.1.32285.11.2.3.1.12.2.1.2
		topDhcpIpInfoPortIndex OBJECT-TYPE
			SYNTAX INTEGER
			MAX-ACCESS not-accessible
			STATUS current
			DESCRIPTION
				"PON Port ID."
			::= { topDhcpIpInfoEntry 2 }

		
		-- 1.3.6.1.4.1.32285.11.2.3.1.12.2.1.3
		topDhcpIpInfoOnuIndex OBJECT-TYPE
			SYNTAX INTEGER
			MAX-ACCESS not-accessible
			STATUS current
			DESCRIPTION
				"ONU ID."
			::= { topDhcpIpInfoEntry 3 }

		
		-- 1.3.6.1.4.1.32285.11.2.3.1.12.2.1.4
		topDhcpIpInfoTotal OBJECT-TYPE
			SYNTAX OCTET STRING (SIZE (0..2816))
			MAX-ACCESS read-only
			STATUS current
			DESCRIPTION
				"CPE Info.Every entry has 11 bytes, byte 0 to byte 3 is IP address, byte 4 to byte 9 is MAC address, byte 10 is CPE type. Max 256 entries.  "
			::= { topDhcpIpInfoEntry 4 }

		
		-- 1.3.6.1.4.1.32285.11.2.3.2
		topSniObjects OBJECT IDENTIFIER ::= { topvisionEponTree 2 }

		
		-- 1.3.6.1.4.1.32285.11.2.3.2.1
		topSniAttributeTable OBJECT-TYPE
			SYNTAX SEQUENCE OF TopSniAttributeEntry
			MAX-ACCESS not-accessible
			STATUS current
			DESCRIPTION
				"A list of topSniAttributeTable entries. "
			::= { topSniObjects 1 }

		
		-- 1.3.6.1.4.1.32285.11.2.3.2.1.1
		topSniAttributeEntry OBJECT-TYPE
			SYNTAX TopSniAttributeEntry
			MAX-ACCESS not-accessible
			STATUS current
			DESCRIPTION
				"The topSniAttributeEntry Information"
			INDEX { topSniAttrCardIndex, topSniAttrPortIndex }
			::= { topSniAttributeTable 1 }

		
		TopSniAttributeEntry ::=
			SEQUENCE { 
				topSniAttrCardIndex
					INTEGER,
				topSniAttrPortIndex
					INTEGER,
				topSniAttrFlowCtrlEnable
					INTEGER,
				topSniAttrIngressRate
					INTEGER,
				topSniAttrEgressRate
					INTEGER,
				topSniAttrActualSpeed
					Unsigned32,
				topSniAttrPortType
					INTEGER
			 }

		-- 1.3.6.1.4.1.32285.11.2.3.2.1.1.1
		topSniAttrCardIndex OBJECT-TYPE
			SYNTAX INTEGER (0..18)
			MAX-ACCESS not-accessible
			STATUS current
			DESCRIPTION
				"Card Index"
			::= { topSniAttributeEntry 1 }

		
		-- 1.3.6.1.4.1.32285.11.2.3.2.1.1.2
		topSniAttrPortIndex OBJECT-TYPE
			SYNTAX INTEGER
			MAX-ACCESS not-accessible
			STATUS current
			DESCRIPTION
				"Port Index"
			::= { topSniAttributeEntry 2 }

		
		-- 1.3.6.1.4.1.32285.11.2.3.2.1.1.3
		topSniAttrFlowCtrlEnable OBJECT-TYPE
			SYNTAX INTEGER
				{
				enable(1),
				disable(2)
				}
			MAX-ACCESS read-write
			STATUS current
			DESCRIPTION
				"Flow control en/disable"
			DEFVAL { 2 }
			::= { topSniAttributeEntry 3 }

		
		-- 1.3.6.1.4.1.32285.11.2.3.2.1.1.4
		topSniAttrIngressRate OBJECT-TYPE
			SYNTAX INTEGER
			UNITS "kbps"
			MAX-ACCESS read-write
			STATUS current
			DESCRIPTION
				"rate limit. unit:kbps"
			DEFVAL { '0'b }
			::= { topSniAttributeEntry 4 }

		
		-- 1.3.6.1.4.1.32285.11.2.3.2.1.1.5
		topSniAttrEgressRate OBJECT-TYPE
			SYNTAX INTEGER
			UNITS "kbps"
			MAX-ACCESS read-write
			STATUS current
			DESCRIPTION
				"rate limit. unit:kbps"
			DEFVAL { '0'b }
			::= { topSniAttributeEntry 5 }

		
		-- 1.3.6.1.4.1.32285.11.2.3.2.1.1.6
		topSniAttrActualSpeed OBJECT-TYPE
			SYNTAX Unsigned32
			UNITS "mbps"
			MAX-ACCESS read-only
			STATUS current
			DESCRIPTION
				"port actual speed "
			DEFVAL { 0 }
			::= { topSniAttributeEntry 6 }

		
		-- 1.3.6.1.4.1.32285.11.2.3.2.1.1.7
		topSniAttrPortType OBJECT-TYPE
			SYNTAX INTEGER
				{
				geCopper(1),
				geFiber(2),
				xeFiber(3)
				}
			MAX-ACCESS read-only
			STATUS current
			DESCRIPTION
				"sni port type"
			DEFVAL { 1 }
			::= { topSniAttributeEntry 7 }

		
		-- 1.3.6.1.4.1.32285.11.2.3.2.2
		topSniRedirectTable OBJECT-TYPE
			SYNTAX SEQUENCE OF TopSniRedirectEntry
			MAX-ACCESS not-accessible
			STATUS current
			DESCRIPTION
				"a list of topSniRedirectTable entries."
			::= { topSniObjects 2 }

		
		-- 1.3.6.1.4.1.32285.11.2.3.2.2.1
		topSniRedirectEntry OBJECT-TYPE
			SYNTAX TopSniRedirectEntry
			MAX-ACCESS not-accessible
			STATUS current
			DESCRIPTION
				"The Redirect Information."
			INDEX { topSniRedirectGroupSrcPort }
			::= { topSniRedirectTable 1 }

		
		TopSniRedirectEntry ::=
			SEQUENCE { 
				topSniRedirectGroupSrcPort
					INTEGER,
				topSniRedirectGroupDirection
					INTEGER,
				topSniRedirectGroupName
					DisplayString,
				topSniRedirectGroupDstPort
					INTEGER,
				topSniRedirectGroupRowstatus
					RowStatus
			 }

		-- 1.3.6.1.4.1.32285.11.2.3.2.2.1.1
		topSniRedirectGroupSrcPort OBJECT-TYPE
			SYNTAX INTEGER
			MAX-ACCESS not-accessible
			STATUS current
			DESCRIPTION
				"Redirect Group source port.
				The highest byte is SLOT index, then port index.
				the lowest byte reserved 0."
			::= { topSniRedirectEntry 1 }

		
		-- 1.3.6.1.4.1.32285.11.2.3.2.2.1.2
		topSniRedirectGroupDirection OBJECT-TYPE
			SYNTAX INTEGER
				{
				ingress(1),
				egress(2),
				biDirection(3)
				}
			MAX-ACCESS read-create
			STATUS current
			DESCRIPTION
				"direction"
			::= { topSniRedirectEntry 2 }

		
		-- 1.3.6.1.4.1.32285.11.2.3.2.2.1.3
		topSniRedirectGroupName OBJECT-TYPE
			SYNTAX DisplayString (SIZE (1..63))
			MAX-ACCESS read-create
			STATUS current
			DESCRIPTION
				"Redirect Group description"
			DEFVAL { "REDIRECT_GROUP_1" }
			::= { topSniRedirectEntry 3 }

		
		-- 1.3.6.1.4.1.32285.11.2.3.2.2.1.4
		topSniRedirectGroupDstPort OBJECT-TYPE
			SYNTAX INTEGER
			MAX-ACCESS read-create
			STATUS current
			DESCRIPTION
				"Redirect Group destination port.
				The highest byte is SLOT index, port index.
				the lowest two bytes are reserved 0."
			::= { topSniRedirectEntry 4 }

		
		-- 1.3.6.1.4.1.32285.11.2.3.2.2.1.5
		topSniRedirectGroupRowstatus OBJECT-TYPE
			SYNTAX RowStatus
			MAX-ACCESS read-create
			STATUS current
			DESCRIPTION
				"Redirect Group Rowstatus"
			::= { topSniRedirectEntry 5 }

		
		-- 1.3.6.1.4.1.32285.11.2.3.2.3
		topSniOptInfoTable OBJECT-TYPE
			SYNTAX SEQUENCE OF TopSniOptInfoEntry
			MAX-ACCESS not-accessible
			STATUS current
			DESCRIPTION
				"a list of topSniOptInfoTable entries."
			::= { topSniObjects 3 }

		
		-- 1.3.6.1.4.1.32285.11.2.3.2.3.1
		topSniOptInfoEntry OBJECT-TYPE
			SYNTAX TopSniOptInfoEntry
			MAX-ACCESS not-accessible
			STATUS current
			DESCRIPTION
				"The topSniOptInfoEntry Information."
			INDEX { topSniOptInfoCardIndex, topSniOptInfoPortIndex }
			::= { topSniOptInfoTable 1 }

		
		TopSniOptInfoEntry ::=
			SEQUENCE { 
				topSniOptInfoCardIndex
					TopEPonSlotIndex,
				topSniOptInfoPortIndex
					TopEPonSniIndex,
				topSniOptInfoIdentifier
					INTEGER,
				topSniOptInfoVendorName
					OCTET STRING,
				topSniOptInfoWaveLength
					INTEGER,
				topSniOptInfoVendorPN
					OCTET STRING,
				topSniOptInfoVendorSN
					OCTET STRING,
				topSniOptInfoDateCode
					OCTET STRING,
				topSniOptInfoWorkingTemp
					INTEGER,
				topSniOptInfoWorkingVoltage
					INTEGER,
				topSniOptInfoBiasCurrent
					INTEGER,
				topSniOptInfoTxPower
					INTEGER,
				topSniOptInfoRxPower
					INTEGER,
				topSniOptInfoBitRate
					INTEGER
			 }

		-- 1.3.6.1.4.1.32285.11.2.3.2.3.1.1
		topSniOptInfoCardIndex OBJECT-TYPE
			SYNTAX TopEPonSlotIndex
			MAX-ACCESS not-accessible
			STATUS current
			DESCRIPTION
				"slot index."
			::= { topSniOptInfoEntry 1 }

		
		-- 1.3.6.1.4.1.32285.11.2.3.2.3.1.2
		topSniOptInfoPortIndex OBJECT-TYPE
			SYNTAX TopEPonSniIndex
			MAX-ACCESS not-accessible
			STATUS current
			DESCRIPTION
				"port index."
			::= { topSniOptInfoEntry 2 }

		
		-- 1.3.6.1.4.1.32285.11.2.3.2.3.1.3
		topSniOptInfoIdentifier OBJECT-TYPE
			SYNTAX INTEGER
			MAX-ACCESS read-only
			STATUS current
			DESCRIPTION
				"optical  Identifier type."
			::= { topSniOptInfoEntry 3 }

		
		-- 1.3.6.1.4.1.32285.11.2.3.2.3.1.4
		topSniOptInfoVendorName OBJECT-TYPE
			SYNTAX OCTET STRING (SIZE (1..16))
			MAX-ACCESS read-only
			STATUS current
			DESCRIPTION
				"optical vendor name ."
			::= { topSniOptInfoEntry 4 }

		
		-- 1.3.6.1.4.1.32285.11.2.3.2.3.1.5
		topSniOptInfoWaveLength OBJECT-TYPE
			SYNTAX INTEGER
			MAX-ACCESS read-only
			STATUS current
			DESCRIPTION
				"optical wave length."
			::= { topSniOptInfoEntry 5 }

		
		-- 1.3.6.1.4.1.32285.11.2.3.2.3.1.6
		topSniOptInfoVendorPN OBJECT-TYPE
			SYNTAX OCTET STRING (SIZE (1..16))
			MAX-ACCESS read-only
			STATUS current
			DESCRIPTION
				"optical vendor PN code."
			::= { topSniOptInfoEntry 6 }

		
		-- 1.3.6.1.4.1.32285.11.2.3.2.3.1.7
		topSniOptInfoVendorSN OBJECT-TYPE
			SYNTAX OCTET STRING (SIZE (1..16))
			MAX-ACCESS read-only
			STATUS current
			DESCRIPTION
				"optical vendor SN code."
			::= { topSniOptInfoEntry 7 }

		
		-- 1.3.6.1.4.1.32285.11.2.3.2.3.1.8
		topSniOptInfoDateCode OBJECT-TYPE
			SYNTAX OCTET STRING (SIZE (8))
			MAX-ACCESS read-only
			STATUS current
			DESCRIPTION
				"optical vendor date ."
			::= { topSniOptInfoEntry 8 }

		
		-- 1.3.6.1.4.1.32285.11.2.3.2.3.1.9
		topSniOptInfoWorkingTemp OBJECT-TYPE
			SYNTAX INTEGER
			UNITS "C"
			MAX-ACCESS read-only
			STATUS current
			DESCRIPTION
				"optical working temperature."
			::= { topSniOptInfoEntry 9 }

		
		-- 1.3.6.1.4.1.32285.11.2.3.2.3.1.10
		topSniOptInfoWorkingVoltage OBJECT-TYPE
			SYNTAX INTEGER
			UNITS "mV"
			MAX-ACCESS read-only
			STATUS current
			DESCRIPTION
				"optical working voltage."
			::= { topSniOptInfoEntry 10 }

		
		-- 1.3.6.1.4.1.32285.11.2.3.2.3.1.11
		topSniOptInfoBiasCurrent OBJECT-TYPE
			SYNTAX INTEGER
			UNITS "mA"
			MAX-ACCESS read-only
			STATUS current
			DESCRIPTION
				"optical bias current."
			::= { topSniOptInfoEntry 11 }

		
		-- 1.3.6.1.4.1.32285.11.2.3.2.3.1.12
		topSniOptInfoTxPower OBJECT-TYPE
			SYNTAX INTEGER
			UNITS "dBm"
			MAX-ACCESS read-only
			STATUS current
			DESCRIPTION
				"optical tx power."
			::= { topSniOptInfoEntry 12 }

		
		-- 1.3.6.1.4.1.32285.11.2.3.2.3.1.13
		topSniOptInfoRxPower OBJECT-TYPE
			SYNTAX INTEGER
			UNITS "dBm"
			MAX-ACCESS read-only
			STATUS current
			DESCRIPTION
				"optical rx power."
			::= { topSniOptInfoEntry 13 }

		
		-- 1.3.6.1.4.1.32285.11.2.3.2.3.1.14
		topSniOptInfoBitRate OBJECT-TYPE
			SYNTAX INTEGER
			UNITS "Mb/s"
			MAX-ACCESS read-only
			STATUS current
			DESCRIPTION
				"optical nominal bit rate(Mb/s)."
			::= { topSniOptInfoEntry 14 }

		
		-- 1.3.6.1.4.1.32285.11.2.3.2.4
		topSniTrunkManagement OBJECT-IDENTITY
			STATUS current
			DESCRIPTION 
				"A list of topSniTrunkManagement entries."
			::= { topSniObjects 4 }

		
		-- 1.3.6.1.4.1.32285.11.2.3.2.4.1
		topSniTrunkGroupConfigTable OBJECT-TYPE
			SYNTAX SEQUENCE OF TopSniTrunkGroupConfigEntry
			MAX-ACCESS not-accessible
			STATUS current
			DESCRIPTION
				"A list of topSniTrunkGroupConfigTable entries."
			::= { topSniTrunkManagement 1 }

		
		-- 1.3.6.1.4.1.32285.11.2.3.2.4.1.1
		topSniTrunkGroupConfigEntry OBJECT-TYPE
			SYNTAX TopSniTrunkGroupConfigEntry
			MAX-ACCESS not-accessible
			STATUS current
			DESCRIPTION
				"The sniTrunk Group Config Entry Information."
			INDEX { topSniTrunkGroupConfigIndex }
			::= { topSniTrunkGroupConfigTable 1 }

		
		TopSniTrunkGroupConfigEntry ::=
			SEQUENCE { 
				topSniTrunkGroupConfigIndex
					INTEGER,
				topSniTrunkGroupConfigMode
					INTEGER,
				topSniTrunkGroupConfigName
					OCTET STRING,
				topSniTrunkGroupConfigMember
					OCTET STRING,
				topSniTrunkGroupConfigPolicy
					INTEGER,
				topSniTrunkGroupConfigRowstatus
					RowStatus
			 }

		-- 1.3.6.1.4.1.32285.11.2.3.2.4.1.1.1
		topSniTrunkGroupConfigIndex OBJECT-TYPE
			SYNTAX INTEGER (1..32)
			MAX-ACCESS not-accessible
			STATUS current
			DESCRIPTION
				"Trunk Group Config Index."
			::= { topSniTrunkGroupConfigEntry 1 }

		
		-- 1.3.6.1.4.1.32285.11.2.3.2.4.1.1.2
		topSniTrunkGroupConfigMode OBJECT-TYPE
			SYNTAX INTEGER
				{
				manual(0),
				static-lacp(1)
				}
			MAX-ACCESS read-create
			STATUS current
			DESCRIPTION
				"Trunk Group Config Mode."
			DEFVAL { manual }
			::= { topSniTrunkGroupConfigEntry 2 }

		
		-- 1.3.6.1.4.1.32285.11.2.3.2.4.1.1.3
		topSniTrunkGroupConfigName OBJECT-TYPE
			SYNTAX OCTET STRING (SIZE (1..31))
			MAX-ACCESS read-write
			STATUS current
			DESCRIPTION
				"Trunk Group Config Name."
			::= { topSniTrunkGroupConfigEntry 3 }

		
		-- 1.3.6.1.4.1.32285.11.2.3.2.4.1.1.4
		topSniTrunkGroupConfigMember OBJECT-TYPE
			SYNTAX OCTET STRING (SIZE (32))
			MAX-ACCESS read-write
			STATUS current
			DESCRIPTION
				"Trunk Group Config Member.
				 	It is presented by member port list. Each member port is identified
				 	by 4-byte format, same as TC of EponDeviceIndex. The actual length of
				 	this string depends of the number of member ports in the trunk group.
				 	The relationship is:
				 	Length of the string = 4 * (NUM of member ports)
				 	For example, if device 1, port 1/2 and 2/3 is the member ports of the
				 	trunk, then sniTrunkGroupConfigMember is presented as:
				 	01 01 02 00 01 02 03 00."
			::= { topSniTrunkGroupConfigEntry 4 }

		
		-- 1.3.6.1.4.1.32285.11.2.3.2.4.1.1.5
		topSniTrunkGroupConfigPolicy OBJECT-TYPE
			SYNTAX INTEGER
				{
				srcMac(1),
				destMac(2),
				srcMacNDestMac(3),
				srcIp(4),
				destIp(5),
				srcIpNDestIp(6)
				}
			MAX-ACCESS read-write
			STATUS current
			DESCRIPTION
				"Trunk Group Config Policy."
			::= { topSniTrunkGroupConfigEntry 5 }

		
		-- 1.3.6.1.4.1.32285.11.2.3.2.4.1.1.6
		topSniTrunkGroupConfigRowstatus OBJECT-TYPE
			SYNTAX RowStatus
			MAX-ACCESS read-create
			STATUS current
			DESCRIPTION
				"Trunk Group Config Rowstatus."
			::= { topSniTrunkGroupConfigEntry 6 }

		
		-- 1.3.6.1.4.1.32285.11.2.3.2.4.2
		topSniTrunkGroupTable OBJECT-TYPE
			SYNTAX SEQUENCE OF TopSniTrunkGroupEntry
			MAX-ACCESS not-accessible
			STATUS current
			DESCRIPTION
				"a list of sniTrunkGroupConfigTable entries."
			::= { topSniTrunkManagement 2 }

		
		-- 1.3.6.1.4.1.32285.11.2.3.2.4.2.1
		topSniTrunkGroupEntry OBJECT-TYPE
			SYNTAX TopSniTrunkGroupEntry
			MAX-ACCESS not-accessible
			STATUS current
			DESCRIPTION
				"The sniTrunk Group Entry Information."
			INDEX { topSniTrunkGroupIndex }
			::= { topSniTrunkGroupTable 1 }

		
		TopSniTrunkGroupEntry ::=
			SEQUENCE { 
				topSniTrunkGroupIndex
					INTEGER,
				topSniTrunkGroupOperationStatus
					INTEGER,
				topSniTrunkGroupActualSpeed
					INTEGER,
				topSniTrunkGroupAdminStatus
					INTEGER
			 }

		-- 1.3.6.1.4.1.32285.11.2.3.2.4.2.1.1
		topSniTrunkGroupIndex OBJECT-TYPE
			SYNTAX INTEGER (1..32)
			MAX-ACCESS not-accessible
			STATUS current
			DESCRIPTION
				"Trunk Group Index."
			::= { topSniTrunkGroupEntry 1 }

		
		-- 1.3.6.1.4.1.32285.11.2.3.2.4.2.1.2
		topSniTrunkGroupOperationStatus OBJECT-TYPE
			SYNTAX INTEGER
				{
				up(1),
				down(2),
				testing(3)
				}
			MAX-ACCESS read-only
			STATUS current
			DESCRIPTION
				"Trunk Group Operation Status."
			::= { topSniTrunkGroupEntry 2 }

		
		-- 1.3.6.1.4.1.32285.11.2.3.2.4.2.1.3
		topSniTrunkGroupActualSpeed OBJECT-TYPE
			SYNTAX INTEGER
			UNITS "Mbps"
			MAX-ACCESS read-only
			STATUS current
			DESCRIPTION
				"Trunk Group Actual Speed.
				 	The speed is the aggregated rates of all operational UP member
				 	ports of the trunk.
				 	For example, 4 member ports of the trunk, two are UP, each is 1000M
				 	then the SUN is 2000M. As a result, the return of the MIB shall be
				 	2000Mbps."
			::= { topSniTrunkGroupEntry 3 }

		
		-- 1.3.6.1.4.1.32285.11.2.3.2.4.2.1.4
		topSniTrunkGroupAdminStatus OBJECT-TYPE
			SYNTAX INTEGER
				{
				up(1),
				down(2),
				testing(3)
				}
			MAX-ACCESS read-only
			STATUS current
			DESCRIPTION
				"Trunk Group AdminStatus."
			::= { topSniTrunkGroupEntry 4 }

		
		-- 1.3.6.1.4.1.32285.11.2.3.2.4.3
		topSniTrunkLacpSysObjects OBJECT IDENTIFIER ::= { topSniTrunkManagement 3 }
-- A list of topSniTrunkLacpSystemConfigTable entries.
		
		-- 1.3.6.1.4.1.32285.11.2.3.2.4.3.1
		topSniTrunkLacpPriority OBJECT-TYPE
			SYNTAX INTEGER (0..65535)
			MAX-ACCESS read-write
			STATUS current
			DESCRIPTION
				"Lacp system priority"
			DEFVAL { 32768 }
			::= { topSniTrunkLacpSysObjects 1 }

		
		-- 1.3.6.1.4.1.32285.11.2.3.2.4.3.2
		topSniTrunkLacpShortPeriod OBJECT-TYPE
			SYNTAX INTEGER (1..10)
			UNITS "second"
			MAX-ACCESS read-write
			STATUS current
			DESCRIPTION
				"Lacp short Period."
			DEFVAL { 1 }
			::= { topSniTrunkLacpSysObjects 2 }

		
		-- 1.3.6.1.4.1.32285.11.2.3.2.4.3.3
		topSniTrunkLacpLongPeriod OBJECT-TYPE
			SYNTAX INTEGER (20..40)
			UNITS "second"
			MAX-ACCESS read-write
			STATUS current
			DESCRIPTION
				"Lacp Long Period."
			DEFVAL { 30 }
			::= { topSniTrunkLacpSysObjects 3 }

		
		-- 1.3.6.1.4.1.32285.11.2.3.2.4.3.4
		topSniTrunkLacpTimeOutMode OBJECT-TYPE
			SYNTAX INTEGER
				{
				long(0),
				short(1)
				}
			MAX-ACCESS read-write
			STATUS current
			DESCRIPTION
				"Lacp time-out Mode."
			DEFVAL { long }
			::= { topSniTrunkLacpSysObjects 4 }

		
		-- 1.3.6.1.4.1.32285.11.2.3.2.4.4
		topSniTrunkLacpPortTable OBJECT-TYPE
			SYNTAX SEQUENCE OF TopSniTrunkLacpPortEntry
			MAX-ACCESS not-accessible
			STATUS current
			DESCRIPTION
				"Description."
			::= { topSniTrunkManagement 4 }
-- A list of topSniTrunkLacpPortConfigTable entries.
		
		-- 1.3.6.1.4.1.32285.11.2.3.2.4.4.1
		topSniTrunkLacpPortEntry OBJECT-TYPE
			SYNTAX TopSniTrunkLacpPortEntry
			MAX-ACCESS not-accessible
			STATUS current
			DESCRIPTION
				"DesThe sniTrunk Lacp System Config Entry Information."
			INDEX { topSniTrunkLacpPortCardIndex, topSniTrunkLacpPortIndex }
			::= { topSniTrunkLacpPortTable 1 }
-- The sniTrunk Lacp port Config Entry Information
		
		TopSniTrunkLacpPortEntry ::=
			SEQUENCE { 
				topSniTrunkLacpPortCardIndex
					INTEGER,
				topSniTrunkLacpPortIndex
					INTEGER,
				topSniTrunkLacpPortPriority
					INTEGER
			 }

		-- 1.3.6.1.4.1.32285.11.2.3.2.4.4.1.1
		topSniTrunkLacpPortCardIndex OBJECT-TYPE
			SYNTAX INTEGER
			MAX-ACCESS not-accessible
			STATUS current
			DESCRIPTION
				"The Slot Index."
			::= { topSniTrunkLacpPortEntry 1 }

		
		-- 1.3.6.1.4.1.32285.11.2.3.2.4.4.1.2
		topSniTrunkLacpPortIndex OBJECT-TYPE
			SYNTAX INTEGER
			MAX-ACCESS not-accessible
			STATUS current
			DESCRIPTION
				"The Port Index."
			::= { topSniTrunkLacpPortEntry 2 }

		
		-- 1.3.6.1.4.1.32285.11.2.3.2.4.4.1.3
		topSniTrunkLacpPortPriority OBJECT-TYPE
			SYNTAX INTEGER (0..32767)
			MAX-ACCESS read-write
			STATUS current
			DESCRIPTION
				"Lacp Port-priority."
			DEFVAL { 16384 }
			::= { topSniTrunkLacpPortEntry 3 }

		

		-- 1.3.6.1.4.1.32285.11.2.3.3
		topPonPortObjects OBJECT IDENTIFIER ::= { topvisionEponTree 3 }

		
		-- 1.3.6.1.4.1.32285.11.2.3.3.1
		topPonProtectMgmtObjects OBJECT IDENTIFIER ::= { topPonPortObjects 1 }

		-- 1.3.6.1.4.1.32285.11.2.3.3.1.1
		topPonPSGrpTable OBJECT-TYPE
			SYNTAX SEQUENCE OF TopPonPSGrpEntry
			MAX-ACCESS not-accessible
			STATUS current
			DESCRIPTION
				"The pon protect switch table."
			::= { topPonProtectMgmtObjects 1 }

		
		-- 1.3.6.1.4.1.32285.11.2.3.3.1.1.1
		topPonPSGrpEntry OBJECT-TYPE
			SYNTAX TopPonPSGrpEntry
			MAX-ACCESS not-accessible
			STATUS current
			DESCRIPTION
				"The topPonPSGrpEntry information ."
			INDEX { topPonPSGrpIndex }
			::= { topPonPSGrpTable 1 }

		
		TopPonPSGrpEntry ::=
			SEQUENCE { 
				topPonPSGrpIndex
					INTEGER,
				topPonPSGrpAdmin
					INTEGER,
				topPonPSWorkPortItem
					OCTET STRING,
				topPonPSWorkPortStatus
					INTEGER,
				topPonPSStandbyPortItem
					OCTET STRING,
				topPonPSStandbyPortStatus
					INTEGER,
				topPonPSManualSwitch
					INTEGER,
				topPonPSTimes
					INTEGER,
				topPonPSLastSwitchTime
					INTEGER,
				topPonPSReason
					OCTET STRING,
				topPonPSResume
					INTEGER,
				topPonPSRowstatus
					RowStatus
			 }

		-- 1.3.6.1.4.1.32285.11.2.3.3.1.1.1.1
		topPonPSGrpIndex OBJECT-TYPE
			SYNTAX INTEGER (1..32)
			MAX-ACCESS not-accessible
			STATUS current
			DESCRIPTION
				"The index of pon protect switch group ."
			::= { topPonPSGrpEntry 1 }

		
		-- 1.3.6.1.4.1.32285.11.2.3.3.1.1.1.2
		topPonPSGrpAdmin OBJECT-TYPE
			SYNTAX INTEGER
				{
				enable(1),
				disable(2)
				}
			MAX-ACCESS read-write
			STATUS current
			DESCRIPTION
				"The admin config of pon protect switch group ."
			::= { topPonPSGrpEntry 2 }

		
		-- 1.3.6.1.4.1.32285.11.2.3.3.1.1.1.3
		topPonPSWorkPortItem OBJECT-TYPE
			SYNTAX OCTET STRING (SIZE (4))
			MAX-ACCESS read-write
			STATUS current
			DESCRIPTION
				"The work port item of pon protect switch group."
			::= { topPonPSGrpEntry 3 }

		
		-- 1.3.6.1.4.1.32285.11.2.3.3.1.1.1.4
		topPonPSWorkPortStatus OBJECT-TYPE
			SYNTAX INTEGER
				{
				active(1),
				inactive(2)
				}
			MAX-ACCESS read-only
			STATUS current
			DESCRIPTION
				"The work port status of pon protect switch ."
			::= { topPonPSGrpEntry 4 }

		
		-- 1.3.6.1.4.1.32285.11.2.3.3.1.1.1.5
		topPonPSStandbyPortItem OBJECT-TYPE
			SYNTAX OCTET STRING (SIZE (4))
			MAX-ACCESS read-write
			STATUS current
			DESCRIPTION
				"The standby port item of pon protect switch group."
			::= { topPonPSGrpEntry 5 }

		
		-- 1.3.6.1.4.1.32285.11.2.3.3.1.1.1.6
		topPonPSStandbyPortStatus OBJECT-TYPE
			SYNTAX INTEGER
				{
				active(1),
				inactive(2)
				}
			MAX-ACCESS read-only
			STATUS current
			DESCRIPTION
				"The standby port status of pon protect switch group."
			::= { topPonPSGrpEntry 6 }

		
		-- 1.3.6.1.4.1.32285.11.2.3.3.1.1.1.7
		topPonPSManualSwitch OBJECT-TYPE
			SYNTAX INTEGER
				{
				noAction(1),
				switchover(2)
				}
			MAX-ACCESS read-write
			STATUS current
			DESCRIPTION
				"
						noAction(1) - 
						switchover(2) - "
			::= { topPonPSGrpEntry 7 }

		
		-- 1.3.6.1.4.1.32285.11.2.3.3.1.1.1.8
		topPonPSTimes OBJECT-TYPE
			SYNTAX INTEGER
			MAX-ACCESS read-only
			STATUS current
			DESCRIPTION
				"The total times of pon protect switch occured."
			::= { topPonPSGrpEntry 8 }

		
		-- 1.3.6.1.4.1.32285.11.2.3.3.1.1.1.9
		topPonPSLastSwitchTime OBJECT-TYPE
			SYNTAX INTEGER
			MAX-ACCESS read-only
			STATUS current
			DESCRIPTION
				"The last time of pon protect switch occured ."
			::= { topPonPSGrpEntry 9 }

		
		-- 1.3.6.1.4.1.32285.11.2.3.3.1.1.1.10
		topPonPSReason OBJECT-TYPE
			SYNTAX OCTET STRING (SIZE (0..256))
			MAX-ACCESS read-only
			STATUS current
			DESCRIPTION
				"The reason of pon protect switch occur."
			::= { topPonPSGrpEntry 10 }

		
		-- 1.3.6.1.4.1.32285.11.2.3.3.1.1.1.11
		topPonPSResume OBJECT-TYPE
			SYNTAX INTEGER
				{
				enable(1),
				disable(2)
				}
			MAX-ACCESS read-write
			STATUS current
			DESCRIPTION
				"The resume config of pon protect switch."
			::= { topPonPSGrpEntry 11 }

		
		-- 1.3.6.1.4.1.32285.11.2.3.3.1.1.1.12
		topPonPSRowstatus OBJECT-TYPE
			SYNTAX RowStatus
			MAX-ACCESS read-create
			STATUS current
			DESCRIPTION
				"Add/del/set."
			::= { topPonPSGrpEntry 12 }		

		
		-- 1.3.6.1.4.1.32285.11.2.3.3.1.2
		topPonPSPortConfigTable OBJECT-TYPE
			SYNTAX SEQUENCE OF TopPonPSPortConfigEntry
			MAX-ACCESS not-accessible
			STATUS current
			DESCRIPTION
				"Description."
			::= { topPonProtectMgmtObjects 2 }

		
		-- 1.3.6.1.4.1.32285.11.2.3.3.1.2.1
		topPonPSPortConfigEntry OBJECT-TYPE
			SYNTAX TopPonPSPortConfigEntry
			MAX-ACCESS not-accessible
			STATUS current
			DESCRIPTION
				"Description."
			INDEX { topPonPSDeviceIndex, topPonPSCardIndex, topPonPSPortIndex }
			::= { topPonPSPortConfigTable 1 }

		
		TopPonPSPortConfigEntry ::=
			SEQUENCE { 
				topPonPSDeviceIndex
					INTEGER,
				topPonPSCardIndex
					TopEPonSlotIndex,
				topPonPSPortIndex
					TopEPonPonIndex,
				topPonPSDeltaRTT
					INTEGER,
				topPonPSDiscAttemps
					INTEGER,
				topPonPSSyncGate
					INTEGER,
				topPonPSDiscIntervar
					INTEGER,
				topPonPSGpioSwitch
					INTEGER,
				topPonPSGpioFail
					INTEGER,
				topPonPSGpioPS
					INTEGER,
				topPonPSProtectFlags
					INTEGER,
				topPonPSLosSoakTime
					INTEGER,
				topPonPSRttTimeout
					INTEGER
			 }

		-- 1.3.6.1.4.1.32285.11.2.3.3.1.2.1.1
		topPonPSDeviceIndex OBJECT-TYPE
			SYNTAX INTEGER
			MAX-ACCESS not-accessible
			STATUS current
			DESCRIPTION
				"Description."
			::= { topPonPSPortConfigEntry 1 }

		
		-- 1.3.6.1.4.1.32285.11.2.3.3.1.2.1.2
		topPonPSCardIndex OBJECT-TYPE
			SYNTAX TopEPonSlotIndex
			MAX-ACCESS not-accessible
			STATUS current
			DESCRIPTION
				"Description."
			::= { topPonPSPortConfigEntry 2 }

		
		-- 1.3.6.1.4.1.32285.11.2.3.3.1.2.1.3
		topPonPSPortIndex OBJECT-TYPE
			SYNTAX TopEPonPonIndex
			MAX-ACCESS not-accessible
			STATUS current
			DESCRIPTION
				"Description."
			::= { topPonPSPortConfigEntry 3 }

		
		-- 1.3.6.1.4.1.32285.11.2.3.3.1.2.1.4
		topPonPSDeltaRTT OBJECT-TYPE
			SYNTAX INTEGER
			MAX-ACCESS read-write
			STATUS current
			DESCRIPTION
				"Description."
			::= { topPonPSPortConfigEntry 4 }

		
		-- 1.3.6.1.4.1.32285.11.2.3.3.1.2.1.5
		topPonPSDiscAttemps OBJECT-TYPE
			SYNTAX INTEGER
			MAX-ACCESS read-write
			STATUS current
			DESCRIPTION
				"Description."
			::= { topPonPSPortConfigEntry 5 }

		
		-- 1.3.6.1.4.1.32285.11.2.3.3.1.2.1.6
		topPonPSSyncGate OBJECT-TYPE
			SYNTAX INTEGER
			MAX-ACCESS read-write
			STATUS current
			DESCRIPTION
				"Description."
			::= { topPonPSPortConfigEntry 6 }

		
		-- 1.3.6.1.4.1.32285.11.2.3.3.1.2.1.7
		topPonPSDiscIntervar OBJECT-TYPE
			SYNTAX INTEGER
			MAX-ACCESS read-write
			STATUS current
			DESCRIPTION
				"Description."
			::= { topPonPSPortConfigEntry 7 }

		
		-- 1.3.6.1.4.1.32285.11.2.3.3.1.2.1.8
		topPonPSGpioSwitch OBJECT-TYPE
			SYNTAX INTEGER
			MAX-ACCESS read-write
			STATUS current
			DESCRIPTION
				"Description."
			::= { topPonPSPortConfigEntry 8 }

		
		-- 1.3.6.1.4.1.32285.11.2.3.3.1.2.1.9
		topPonPSGpioFail OBJECT-TYPE
			SYNTAX INTEGER
			MAX-ACCESS read-write
			STATUS current
			DESCRIPTION
				"Description."
			::= { topPonPSPortConfigEntry 9 }

		
		-- 1.3.6.1.4.1.32285.11.2.3.3.1.2.1.10
		topPonPSGpioPS OBJECT-TYPE
			SYNTAX INTEGER
			MAX-ACCESS read-write
			STATUS current
			DESCRIPTION
				"Description."
			::= { topPonPSPortConfigEntry 10 }

		
		-- 1.3.6.1.4.1.32285.11.2.3.3.1.2.1.11
		topPonPSProtectFlags OBJECT-TYPE
			SYNTAX INTEGER
			MAX-ACCESS read-write
			STATUS current
			DESCRIPTION
				"Description."
			::= { topPonPSPortConfigEntry 11 }

		
		-- 1.3.6.1.4.1.32285.11.2.3.3.1.2.1.12
		topPonPSLosSoakTime OBJECT-TYPE
			SYNTAX INTEGER
			MAX-ACCESS read-write
			STATUS current
			DESCRIPTION
				"Description."
			::= { topPonPSPortConfigEntry 12 }

		
		-- 1.3.6.1.4.1.32285.11.2.3.3.1.2.1.13
		topPonPSRttTimeout OBJECT-TYPE
			SYNTAX INTEGER
			MAX-ACCESS read-write
			STATUS current
			DESCRIPTION
				"Description."
			::= { topPonPSPortConfigEntry 13 }
		
		-- 1.3.6.1.4.1.32285.11.2.3.3.2
		topAclMgmtObjects OBJECT IDENTIFIER ::= { topPonPortObjects 2 }

		
		-- 1.3.6.1.4.1.32285.11.2.3.3.2.1
		topPortACLListTable OBJECT-TYPE
			SYNTAX SEQUENCE OF TopPortACLListEntry
			MAX-ACCESS not-accessible
			STATUS current
			DESCRIPTION
				"ACL table applies on OLT pon port, OLT SNI, OLT onu ID, ONU UNI.
				for the purpose of ACL and QinQ feature."
			::= { topAclMgmtObjects 1 }

		
		-- 1.3.6.1.4.1.32285.11.2.3.3.2.1.1
		topPortACLListEntry OBJECT-TYPE
			SYNTAX TopPortACLListEntry
			MAX-ACCESS not-accessible
			STATUS current
			DESCRIPTION
				"Port include PON/SNI/UNI."
			INDEX { topAclDeviceIndex, topPortAclListIndex, topAclPortDirection }
			::= { topPortACLListTable 1 }

		
		TopPortACLListEntry ::=
			SEQUENCE { 
				topAclDeviceIndex
					EponDeviceIndex,
				topPortAclListIndex
					INTEGER,
				topAclPortDirection
					INTEGER,
				topAclRowStatus
					RowStatus
			 }

		-- 1.3.6.1.4.1.32285.11.2.3.3.2.1.1.1
		topAclDeviceIndex OBJECT-TYPE
			SYNTAX EponDeviceIndex
			MAX-ACCESS not-accessible
			STATUS current
			DESCRIPTION
				"From MSB on, SLOT index, PON/SNI index, ONU auth index,
				and uni port index.
				For PON/SNI, ONU auth and uni reserved 0."
			::= { topPortACLListEntry 1 }

		
		-- 1.3.6.1.4.1.32285.11.2.3.3.2.1.1.2
		topPortAclListIndex OBJECT-TYPE
			SYNTAX INTEGER
			MAX-ACCESS not-accessible
			STATUS current
			DESCRIPTION
				"ACL RuleList Index"
			::= { topPortACLListEntry 2 }

		
		-- 1.3.6.1.4.1.32285.11.2.3.3.2.1.1.3
		topAclPortDirection OBJECT-TYPE
			SYNTAX INTEGER
				{
				ingress(0),
				egress(1)
				}
			MAX-ACCESS not-accessible
			STATUS current
			DESCRIPTION
				"direction"
			::= { topPortACLListEntry 3 }

		
		-- 1.3.6.1.4.1.32285.11.2.3.3.2.1.1.4
		topAclRowStatus OBJECT-TYPE
			SYNTAX RowStatus
			MAX-ACCESS read-create
			STATUS current
			DESCRIPTION
				"Add/Del/Set"
			::= { topPortACLListEntry 4 }

		
		-- 1.3.6.1.4.1.32285.11.2.3.3.2.2
		topAclListTable OBJECT-TYPE
			SYNTAX SEQUENCE OF TopAclListEntry
			MAX-ACCESS not-accessible
			STATUS current
			DESCRIPTION
				"ACL list table"
			::= { topAclMgmtObjects 2 }

		
		-- 1.3.6.1.4.1.32285.11.2.3.3.2.2.1
		topAclListEntry OBJECT-TYPE
			SYNTAX TopAclListEntry
			MAX-ACCESS not-accessible
			STATUS current
			DESCRIPTION
				"ACL list entry"
			INDEX { topAclListIndex }
			::= { topAclListTable 1 }

		
		TopAclListEntry ::=
			SEQUENCE { 
				topAclListIndex
					INTEGER,
				topAclDescription
					DisplayString,
				topAclRuleNum
					INTEGER,
				topAclRulePriority
					INTEGER,
				topRuleRowStatus
					RowStatus
			 }

		-- 1.3.6.1.4.1.32285.11.2.3.3.2.2.1.1
		topAclListIndex OBJECT-TYPE
			SYNTAX INTEGER
			MAX-ACCESS not-accessible
			STATUS current
			DESCRIPTION
				"ACL List Index"
			::= { topAclListEntry 1 }

		
		-- 1.3.6.1.4.1.32285.11.2.3.3.2.2.1.2
		topAclDescription OBJECT-TYPE
			SYNTAX DisplayString (SIZE (1..63))
			MAX-ACCESS read-create
			STATUS current
			DESCRIPTION
				"ACL Description"
			DEFVAL { "ACL_1" }
			::= { topAclListEntry 2 }

		
		-- 1.3.6.1.4.1.32285.11.2.3.3.2.2.1.3
		topAclRuleNum OBJECT-TYPE
			SYNTAX INTEGER (0..16)
			MAX-ACCESS read-only
			STATUS current
			DESCRIPTION
				"ACL rule quantity."
			::= { topAclListEntry 3 }

		
		-- 1.3.6.1.4.1.32285.11.2.3.3.2.2.1.4
		topAclRulePriority OBJECT-TYPE
			SYNTAX INTEGER (1..16)
			MAX-ACCESS read-create
			STATUS current
			DESCRIPTION
				"priority of ACL list index"
			DEFVAL { 1 }
			::= { topAclListEntry 4 }

		
		-- 1.3.6.1.4.1.32285.11.2.3.3.2.2.1.5
		topRuleRowStatus OBJECT-TYPE
			SYNTAX RowStatus
			MAX-ACCESS read-create
			STATUS current
			DESCRIPTION
				"Add/Del/Set"
			::= { topAclListEntry 5 }

		
		-- 1.3.6.1.4.1.32285.11.2.3.3.2.3
		topAclRuleTable OBJECT-TYPE
			SYNTAX SEQUENCE OF TopAclRuleEntry
			MAX-ACCESS not-accessible
			STATUS current
			DESCRIPTION
				"ACL rule table"
			::= { topAclMgmtObjects 3 }

		
		-- 1.3.6.1.4.1.32285.11.2.3.3.2.3.1
		topAclRuleEntry OBJECT-TYPE
			SYNTAX TopAclRuleEntry
			MAX-ACCESS not-accessible
			STATUS current
			DESCRIPTION
				"ACL rule entry"
			INDEX { topAclRuleListIndex, topAclRuleIndex }
			::= { topAclRuleTable 1 }

		
		TopAclRuleEntry ::=
			SEQUENCE { 
				topAclRuleListIndex
					INTEGER,
				topAclRuleIndex
					INTEGER,
				topMatchedFieldSelection
					BITS,
				topMatchedSrcMac
					MacAddress,
				topMatchedSrcMacMask
					MacAddress,
				topMatchedDstMac
					MacAddress,
				topMatchedDstMacMask
					MacAddress,
				topMatchedStartSVid
					INTEGER,
				topMatchedEndSVid
					INTEGER,
				topMatchedStartCVid
					INTEGER,
				topMatchedEndCVid
					INTEGER,
				topMatchedOuterCos
					INTEGER,
				topMatchedInnerCos
					INTEGER,
				topMatchedOuterTpid
					INTEGER,
				topMatchedInnerTpid
					INTEGER,
				topMatchedEthernetType
					INTEGER,
				topMatchedSrcIP
					IpAddress,
				topMatchedSrcIPMask
					IpAddress,
				topMatchedDstIP
					IpAddress,
				topMatchedDstIPMask
					IpAddress,
				topMatchedL3ProtocolClass
					INTEGER,
				topMatchedIpProtocol
					INTEGER,
				topMatchedDscp
					INTEGER,
				topMatchedTos
					INTEGER,
				topMatchedStartSrcPort
					INTEGER,
				topMatchedEndSrcPort
					INTEGER,
				topMatchedStartDstPort
					INTEGER,
				topMatchedEndDstPort
					INTEGER,
				topAclAction
					BITS,
				topAclActionParameter
					OCTET STRING,
				topAclRuleRowStatus
					RowStatus
			 }

		-- 1.3.6.1.4.1.32285.11.2.3.3.2.3.1.1
		topAclRuleListIndex OBJECT-TYPE
			SYNTAX INTEGER
			MAX-ACCESS not-accessible
			STATUS current
			DESCRIPTION
				"ACL RuleList Index"
			::= { topAclRuleEntry 1 }

		
		-- 1.3.6.1.4.1.32285.11.2.3.3.2.3.1.2
		topAclRuleIndex OBJECT-TYPE
			SYNTAX INTEGER (1..16)
			MAX-ACCESS not-accessible
			STATUS current
			DESCRIPTION
				"ACL Rule Index, also index is rule priority."
			::= { topAclRuleEntry 2 }

		
		-- 1.3.6.1.4.1.32285.11.2.3.3.2.3.1.3
		topMatchedFieldSelection OBJECT-TYPE
			SYNTAX BITS
				{
				srcMac(0),
				dstMac(1),
				outerVid(2),
				innerVid(3),
				outerCos(4),
				innerCos(5),
				outerTpid(6),
				innerTpid(7),
				ethernetType(8),
				srcIp(9),
				dstIp(10),
				ipProtocolClass(11),
				ipProtocolType(12),
				dscp(13),
				tos(14),
				srcPort(15),
				dstPort(16),
				reserved1(17),
				reserved2(18),
				reserved3(19),
				reserved4(20),
				reserved5(21),
				reserved6(22),
				reserved7(23),
				reserved8(24),
				reserved9(25),
				reserved10(26)
				}
			MAX-ACCESS read-create
			STATUS current
			DESCRIPTION
				"match field"
			::= { topAclRuleEntry 3 }

		
		-- 1.3.6.1.4.1.32285.11.2.3.3.2.3.1.4
		topMatchedSrcMac OBJECT-TYPE
			SYNTAX MacAddress
			MAX-ACCESS read-create
			STATUS current
			DESCRIPTION
				"source MAC address"
			::= { topAclRuleEntry 4 }

		
		-- 1.3.6.1.4.1.32285.11.2.3.3.2.3.1.5
		topMatchedSrcMacMask OBJECT-TYPE
			SYNTAX MacAddress
			MAX-ACCESS read-create
			STATUS current
			DESCRIPTION
				"source MAC mask"
			::= { topAclRuleEntry 5 }

		
		-- 1.3.6.1.4.1.32285.11.2.3.3.2.3.1.6
		topMatchedDstMac OBJECT-TYPE
			SYNTAX MacAddress
			MAX-ACCESS read-create
			STATUS current
			DESCRIPTION
				"destination MAC address"
			::= { topAclRuleEntry 6 }

		
		-- 1.3.6.1.4.1.32285.11.2.3.3.2.3.1.7
		topMatchedDstMacMask OBJECT-TYPE
			SYNTAX MacAddress
			MAX-ACCESS read-create
			STATUS current
			DESCRIPTION
				"destination MAC mask"
			::= { topAclRuleEntry 7 }

		
		-- 1.3.6.1.4.1.32285.11.2.3.3.2.3.1.8
		topMatchedStartSVid OBJECT-TYPE
			SYNTAX INTEGER (1..4094)
			MAX-ACCESS read-create
			STATUS current
			DESCRIPTION
				"min value of svlan id range"
			::= { topAclRuleEntry 8 }

		
		-- 1.3.6.1.4.1.32285.11.2.3.3.2.3.1.9
		topMatchedEndSVid OBJECT-TYPE
			SYNTAX INTEGER (1..4094)
			MAX-ACCESS read-create
			STATUS current
			DESCRIPTION
				"max value of svlan id range"
			::= { topAclRuleEntry 9 }

		
		-- 1.3.6.1.4.1.32285.11.2.3.3.2.3.1.10
		topMatchedStartCVid OBJECT-TYPE
			SYNTAX INTEGER (1..4094)
			MAX-ACCESS read-create
			STATUS current
			DESCRIPTION
				"min value of cvlan id range"
			::= { topAclRuleEntry 10 }

		
		-- 1.3.6.1.4.1.32285.11.2.3.3.2.3.1.11
		topMatchedEndCVid OBJECT-TYPE
			SYNTAX INTEGER (1..4094)
			MAX-ACCESS read-create
			STATUS current
			DESCRIPTION
				"max value of cvlan id range"
			::= { topAclRuleEntry 11 }

		
		-- 1.3.6.1.4.1.32285.11.2.3.3.2.3.1.12
		topMatchedOuterCos OBJECT-TYPE
			SYNTAX INTEGER (0..7)
			MAX-ACCESS read-create
			STATUS current
			DESCRIPTION
				"outer cos priority"
			::= { topAclRuleEntry 12 }

		
		-- 1.3.6.1.4.1.32285.11.2.3.3.2.3.1.13
		topMatchedInnerCos OBJECT-TYPE
			SYNTAX INTEGER (0..7)
			MAX-ACCESS read-create
			STATUS current
			DESCRIPTION
				"inner cos priority"
			::= { topAclRuleEntry 13 }

		
		-- 1.3.6.1.4.1.32285.11.2.3.3.2.3.1.14
		topMatchedOuterTpid OBJECT-TYPE
			SYNTAX INTEGER (1..65535)
			MAX-ACCESS read-create
			STATUS current
			DESCRIPTION
				"outer tpid"
			::= { topAclRuleEntry 14 }

		
		-- 1.3.6.1.4.1.32285.11.2.3.3.2.3.1.15
		topMatchedInnerTpid OBJECT-TYPE
			SYNTAX INTEGER (1..65535)
			MAX-ACCESS read-create
			STATUS current
			DESCRIPTION
				"inner tpid"
			::= { topAclRuleEntry 15 }

		
		-- 1.3.6.1.4.1.32285.11.2.3.3.2.3.1.16
		topMatchedEthernetType OBJECT-TYPE
			SYNTAX INTEGER (1..65535)
			MAX-ACCESS read-create
			STATUS current
			DESCRIPTION
				"It is presented in decimal value for heximal EtherType"
			::= { topAclRuleEntry 16 }

		
		-- 1.3.6.1.4.1.32285.11.2.3.3.2.3.1.17
		topMatchedSrcIP OBJECT-TYPE
			SYNTAX IpAddress
			MAX-ACCESS read-create
			STATUS current
			DESCRIPTION
				"Source IP"
			::= { topAclRuleEntry 17 }

		
		-- 1.3.6.1.4.1.32285.11.2.3.3.2.3.1.18
		topMatchedSrcIPMask OBJECT-TYPE
			SYNTAX IpAddress
			MAX-ACCESS read-create
			STATUS current
			DESCRIPTION
				"Source IP Mask"
			::= { topAclRuleEntry 18 }

		
		-- 1.3.6.1.4.1.32285.11.2.3.3.2.3.1.19
		topMatchedDstIP OBJECT-TYPE
			SYNTAX IpAddress
			MAX-ACCESS read-create
			STATUS current
			DESCRIPTION
				"Destination IP"
			::= { topAclRuleEntry 19 }

		
		-- 1.3.6.1.4.1.32285.11.2.3.3.2.3.1.20
		topMatchedDstIPMask OBJECT-TYPE
			SYNTAX IpAddress
			MAX-ACCESS read-create
			STATUS current
			DESCRIPTION
				"Destination IP Mask"
			::= { topAclRuleEntry 20 }

		
		-- 1.3.6.1.4.1.32285.11.2.3.3.2.3.1.21
		topMatchedL3ProtocolClass OBJECT-TYPE
			SYNTAX INTEGER
				{
				nonIp(1),
				nonIpv4(2),
				ipv4(3),
				nonIpv6(4),
				ipv6(5)
				}
			MAX-ACCESS read-create
			STATUS current
			DESCRIPTION
				"ip protocol class, include non-ip,
				non-ipv4,ipv4,non-ipv6,ipv6.
				non-ip: any protocol except for ip.
				nonIpv4: any protocol excpet for ipv4.
				ipv4: ipv4 only.
				ipv6: ipv6 only.
				nonIpv6: any protocol except for ipv6.
				"
			::= { topAclRuleEntry 21 }

		
		-- 1.3.6.1.4.1.32285.11.2.3.3.2.3.1.22
		topMatchedIpProtocol OBJECT-TYPE
			SYNTAX INTEGER (0..255)
			MAX-ACCESS read-create
			STATUS current
			DESCRIPTION
				"IP protocol type, including icmp,igmp, tcp, egp, udp."
			::= { topAclRuleEntry 22 }

		
		-- 1.3.6.1.4.1.32285.11.2.3.3.2.3.1.23
		topMatchedDscp OBJECT-TYPE
			SYNTAX INTEGER (0..63)
			MAX-ACCESS read-create
			STATUS current
			DESCRIPTION
				"dscp"
			::= { topAclRuleEntry 23 }

		
		-- 1.3.6.1.4.1.32285.11.2.3.3.2.3.1.24
		topMatchedTos OBJECT-TYPE
			SYNTAX INTEGER (0..7)
			MAX-ACCESS read-create
			STATUS current
			DESCRIPTION
				"dscp"
			::= { topAclRuleEntry 24 }

		
		-- 1.3.6.1.4.1.32285.11.2.3.3.2.3.1.25
		topMatchedStartSrcPort OBJECT-TYPE
			SYNTAX INTEGER (0..65535)
			MAX-ACCESS read-create
			STATUS current
			DESCRIPTION
				"Min value of L4 source port"
			::= { topAclRuleEntry 25 }

		
		-- 1.3.6.1.4.1.32285.11.2.3.3.2.3.1.26
		topMatchedEndSrcPort OBJECT-TYPE
			SYNTAX INTEGER (0..65535)
			MAX-ACCESS read-create
			STATUS current
			DESCRIPTION
				"Max value of L4 source port"
			::= { topAclRuleEntry 26 }

		
		-- 1.3.6.1.4.1.32285.11.2.3.3.2.3.1.27
		topMatchedStartDstPort OBJECT-TYPE
			SYNTAX INTEGER (0..65535)
			MAX-ACCESS read-create
			STATUS current
			DESCRIPTION
				"Min value of L4 destination port"
			::= { topAclRuleEntry 27 }

		
		-- 1.3.6.1.4.1.32285.11.2.3.3.2.3.1.28
		topMatchedEndDstPort OBJECT-TYPE
			SYNTAX INTEGER (0..65535)
			MAX-ACCESS read-create
			STATUS current
			DESCRIPTION
				"Max value of L4 destination port"
			::= { topAclRuleEntry 28 }

		
		-- 1.3.6.1.4.1.32285.11.2.3.3.2.3.1.29
		topAclAction OBJECT-TYPE
			SYNTAX BITS
				{
				permitDenyvalue(0),
				permitPermitValue(1),
				setIngressRate(2),
				mirror(3),
				setQueue(4),
				markInnerCos(5),
				markDscp(6),
				markTos(7),
				addOuterVlan(8),
				scosMode(9),
				tpidMode(10),
				copyToCpu(11),
				svlanPri(12),
				replaceOuterVlan(13),
				reserved4(14),
				reserved5(15)
				}
			MAX-ACCESS read-create
			STATUS current
			DESCRIPTION
				"2-8 OCTETs:
				note:
				the following coding rule diffrent from ASN.1,
				but BITS will follow ASN.1 still.
                ------------------
				OCTET1:
				BIT0: 1-deny; 0-none;
				BIT1: 1-permit; 0-none,deny and permit cannot be 1 at the same time;
				BIT2: 1-set ingress rate limit; 0-not limited; unit: kbps
				BIT3: 1-mirror to other port; 0-not mirror;
				BIT4: 1-set to some specific queue; 0-default queue;
				BIT5: 1-mark inner cos; 0-keep the current inner cos value
				BIT6: 1-mark DSCP; 0-keep the current DSCP value
				BIT7: 1-mark tos; 0-keep the current TOS value
                -------------------
				OCTET2:
				BIT8: 1-add svlan; 0-keep the current vlan stacking
				BIT9: 0-copy ccos to scos, valid only BIT8=1;
				      1-use a specific cos value from topAclActionParameter,
				        vlaid only BIT8=1.
				BIT10:0-copy tpid from inner tpid, valid only BIT8=1;
				      1-use a specific tpid value from topAclActionParameter,
				        vlaid only BIT8=1.
                BIT11:1-copy data to cpu,0-default.
				    BIT12:1-svlan priority,0-none
				    BIT13:1-replace svlan; 0-keep the current vlan stacking
				    BIT14:reserved 0
				    BIT15:reserved 0
				"
			::= { topAclRuleEntry 29 }

		
		-- 1.3.6.1.4.1.32285.11.2.3.3.2.3.1.30
		topAclActionParameter OBJECT-TYPE
			SYNTAX OCTET STRING (SIZE (18..256))
			MAX-ACCESS read-create
			STATUS current
			DESCRIPTION
				"ACL action parameter description:
				this variable is valid only when topAclAction is not permit/deny.
				from MSB on,
				OCTET1-4(4 bytes): ingress rate limit
				OCTET5-8(4 bytes): format is SLOT-PON/SNI-ONUAUTH-UNI
				    for PON/SNI, OUNAUTH and UNI set to 0x00
				OCTET9(1 byte): queue id
				OCTET10(1 byte): inner CoS
				OCTET11(1 byte): DSCP
				OCTET12(1 byte): TOS
				OCTET13-14(2 byte): SVLAN ID
				OCTET15(1 byte): SCOS, default value is 0
				OCTET16-17(2 byte): outer TPID, defaut value is 0x8100
				OCTET18(1 byte):SVLAN priority 0~7
				Furthermore, for each OCTET, should be filled with 0x00 
				in case the specific field is invalid."
			::= { topAclRuleEntry 30 }

		
		-- 1.3.6.1.4.1.32285.11.2.3.3.2.3.1.31
		topAclRuleRowStatus OBJECT-TYPE
			SYNTAX RowStatus
			MAX-ACCESS read-create
			STATUS current
			DESCRIPTION
				"Add/Del/Set"
			::= { topAclRuleEntry 31 }


		-- 1.3.6.1.4.1.32285.11.2.3.3.3
		topPonOnuAuthModeTable OBJECT-TYPE
			SYNTAX SEQUENCE OF TopPonOnuAuthModeEntry
			MAX-ACCESS not-accessible
			STATUS current
			DESCRIPTION
				"ONU auth policy based on pon port"
			::= { topPonPortObjects 3 }

		
		-- 1.3.6.1.4.1.32285.11.2.3.3.3.1
		topPonOnuAuthModeEntry OBJECT-TYPE
			SYNTAX TopPonOnuAuthModeEntry
			MAX-ACCESS not-accessible
			STATUS current
			DESCRIPTION
				"ONU auth mode"
			INDEX { topPonOnuAuthModeCardIndex, topPonOnuAuthModePonIndex }
			::= { topPonOnuAuthModeTable 1 }

		
		TopPonOnuAuthModeEntry ::=
			SEQUENCE { 
				topPonOnuAuthModeCardIndex
					TopEPonSlotIndex,
				topPonOnuAuthModePonIndex
					TopEPonPonIndex,
				topPonOnuAuthModeMode
					INTEGER
			 }

		-- 1.3.6.1.4.1.32285.11.2.3.3.3.1.1
		topPonOnuAuthModeCardIndex OBJECT-TYPE
			SYNTAX TopEPonSlotIndex
			MAX-ACCESS not-accessible
			STATUS current
			DESCRIPTION
				"slot index"
			::= { topPonOnuAuthModeEntry 1 }

		
		-- 1.3.6.1.4.1.32285.11.2.3.3.3.1.2
		topPonOnuAuthModePonIndex OBJECT-TYPE
			SYNTAX TopEPonPonIndex
			MAX-ACCESS not-accessible
			STATUS current
			DESCRIPTION
				"Pon index"
			::= { topPonOnuAuthModeEntry 2 }

		
		-- 1.3.6.1.4.1.32285.11.2.3.3.3.1.3
		topPonOnuAuthModeMode OBJECT-TYPE
			SYNTAX INTEGER (1..5)
			MAX-ACCESS read-write
			STATUS current
			DESCRIPTION
				"Onu auth policy based on pon port.
				This table will not support rowstatus, it's a static table, created automatically as per epua board.
				TK_AUTO_AUTH = 0x1,
				TK_MAC_AUTH = 0x2,
				TK_MIX_AUTH = 0x3,
				TK_LOID_AUTH= 0x4,
				TK_LOID_PWD_AUTH=0x5"
			DEFVAL { 1 }
			::= { topPonOnuAuthModeEntry 3 }

		
		-- 1.3.6.1.4.1.32285.11.2.3.3.4
		topPonOnuAutoAuthModeTable OBJECT-TYPE
			SYNTAX SEQUENCE OF TopPonOnuAutoAuthModeEntry
			MAX-ACCESS not-accessible
			STATUS current
			DESCRIPTION
				"Onu Auto Auth Mode Table."
			::= { topPonPortObjects 4 }

		
		-- 1.3.6.1.4.1.32285.11.2.3.3.4.1
		topPonOnuAutoAuthModeEntry OBJECT-TYPE
			SYNTAX TopPonOnuAutoAuthModeEntry
			MAX-ACCESS not-accessible
			STATUS current
			DESCRIPTION
				"Onu Auto Auth Mode Entry."
			INDEX { topPonOnuAutoAuthModeCardIndex, topPonOnuAutoAuthModePonIndex }
			::= { topPonOnuAutoAuthModeTable 1 }

		
		TopPonOnuAutoAuthModeEntry ::=
			SEQUENCE { 
				topPonOnuAutoAuthModeCardIndex
					TopEPonSlotIndex,
				topPonOnuAutoAuthModePonIndex
					TopEPonPonIndex,
				topPonOnuAutoAuthEnable
					INTEGER
			 }

		-- 1.3.6.1.4.1.32285.11.2.3.3.4.1.1
		topPonOnuAutoAuthModeCardIndex OBJECT-TYPE
			SYNTAX TopEPonSlotIndex
			MAX-ACCESS not-accessible
			STATUS current
			DESCRIPTION
				"Slot index."
			::= { topPonOnuAutoAuthModeEntry 1 }

		
		-- 1.3.6.1.4.1.32285.11.2.3.3.4.1.2
		topPonOnuAutoAuthModePonIndex OBJECT-TYPE
			SYNTAX TopEPonPonIndex
			MAX-ACCESS not-accessible
			STATUS current
			DESCRIPTION
				"Pon index."
			::= { topPonOnuAutoAuthModeEntry 2 }

		
		-- 1.3.6.1.4.1.32285.11.2.3.3.4.1.3
		topPonOnuAutoAuthEnable OBJECT-TYPE
			SYNTAX INTEGER
				{
				disable(0),
				enable(1)
				}
			MAX-ACCESS read-write
			STATUS current
			DESCRIPTION
				"ONU atuo authentication configuration."
			DEFVAL { 0 }
			::= { topPonOnuAutoAuthModeEntry 3 }

		
		-- 1.3.6.1.4.1.32285.11.2.3.3.5
		topPonOptInfoTable OBJECT-TYPE
			SYNTAX SEQUENCE OF TopPonOptInfoEntry
			MAX-ACCESS not-accessible
			STATUS current
			DESCRIPTION
				"a list of topPonOptInfoTable entries."
			::= { topPonPortObjects 5 }

		
		-- 1.3.6.1.4.1.32285.11.2.3.3.5.1
		topPonOptInfoEntry OBJECT-TYPE
			SYNTAX TopPonOptInfoEntry
			MAX-ACCESS not-accessible
			STATUS current
			DESCRIPTION
				"The topPonOptInfoEntry Information."
			INDEX { topPonOptInfoCardIndex, topPonOptInfoPortIndex }
			::= { topPonOptInfoTable 1 }

		
		TopPonOptInfoEntry ::=
			SEQUENCE { 
				topPonOptInfoCardIndex
					TopEPonSlotIndex,
				topPonOptInfoPortIndex
					TopEPonPonIndex,
				topPonOptInfoIdentifier
					INTEGER,
				topPonOptInfoVendorName
					OCTET STRING,
				topPonOptInfoWaveLength
					INTEGER,
				topPonOptInfoVendorPN
					OCTET STRING,
				topPonOptInfoVendorSN
					OCTET STRING,
				topPonOptInfoDateCode
					OCTET STRING,
				topPonOptInfoWorkingTemp
					INTEGER,
				topPonOptInfoWorkingVoltage
					INTEGER,
				topPonOptInfoBiasCurrent
					INTEGER,
				topPonOptInfoTxPower
					INTEGER,
				topPonOptInfoRxPower
					INTEGER,
				topPonOptInfoBitRate
					INTEGER,
				topPonOptMaxBitRate
					INTEGER,
				topPonOptMinBitRate
					INTEGER,
				topPonOpt10GBiasCurrent
					INTEGER,
				topPonOpt10GTxPwr
					INTEGER
			 }

		-- 1.3.6.1.4.1.32285.11.2.3.3.5.1.1
		topPonOptInfoCardIndex OBJECT-TYPE
			SYNTAX TopEPonSlotIndex
			MAX-ACCESS not-accessible
			STATUS current
			DESCRIPTION
				"slot index."
			::= { topPonOptInfoEntry 1 }

		
		-- 1.3.6.1.4.1.32285.11.2.3.3.5.1.2
		topPonOptInfoPortIndex OBJECT-TYPE
			SYNTAX TopEPonPonIndex
			MAX-ACCESS not-accessible
			STATUS current
			DESCRIPTION
				"port index."
			::= { topPonOptInfoEntry 2 }

		
		-- 1.3.6.1.4.1.32285.11.2.3.3.5.1.3
		topPonOptInfoIdentifier OBJECT-TYPE
			SYNTAX INTEGER
			MAX-ACCESS read-only
			STATUS current
			DESCRIPTION
				"optical Identifier type."
			::= { topPonOptInfoEntry 3 }

		
		-- 1.3.6.1.4.1.32285.11.2.3.3.5.1.4
		topPonOptInfoVendorName OBJECT-TYPE
			SYNTAX OCTET STRING (SIZE (1..16))
			MAX-ACCESS read-only
			STATUS current
			DESCRIPTION
				"optical vendor name."
			::= { topPonOptInfoEntry 4 }

		
		-- 1.3.6.1.4.1.32285.11.2.3.3.5.1.5
		topPonOptInfoWaveLength OBJECT-TYPE
			SYNTAX INTEGER
			MAX-ACCESS read-only
			STATUS current
			DESCRIPTION
				"optical wave length."
			::= { topPonOptInfoEntry 5 }

		
		-- 1.3.6.1.4.1.32285.11.2.3.3.5.1.6
		topPonOptInfoVendorPN OBJECT-TYPE
			SYNTAX OCTET STRING (SIZE (1..16))
			MAX-ACCESS read-only
			STATUS current
			DESCRIPTION
				"optical vendor PN code."
			::= { topPonOptInfoEntry 6 }

		
		-- 1.3.6.1.4.1.32285.11.2.3.3.5.1.7
		topPonOptInfoVendorSN OBJECT-TYPE
			SYNTAX OCTET STRING (SIZE (1..16))
			MAX-ACCESS read-only
			STATUS current
			DESCRIPTION
				"optical vendor SN code."
			::= { topPonOptInfoEntry 7 }

		
		-- 1.3.6.1.4.1.32285.11.2.3.3.5.1.8
		topPonOptInfoDateCode OBJECT-TYPE
			SYNTAX OCTET STRING (SIZE (8))
			MAX-ACCESS read-only
			STATUS current
			DESCRIPTION
				"optical vendor date."
			::= { topPonOptInfoEntry 8 }

		
		-- 1.3.6.1.4.1.32285.11.2.3.3.5.1.9
		topPonOptInfoWorkingTemp OBJECT-TYPE
			SYNTAX INTEGER
			UNITS "C"
			MAX-ACCESS read-only
			STATUS current
			DESCRIPTION
				"optical working temperature."
			::= { topPonOptInfoEntry 9 }

		
		-- 1.3.6.1.4.1.32285.11.2.3.3.5.1.10
		topPonOptInfoWorkingVoltage OBJECT-TYPE
			SYNTAX INTEGER
			UNITS "mV"
			MAX-ACCESS read-only
			STATUS current
			DESCRIPTION
				"optical working voltage."
			::= { topPonOptInfoEntry 10 }

		
		-- 1.3.6.1.4.1.32285.11.2.3.3.5.1.11
		topPonOptInfoBiasCurrent OBJECT-TYPE
			SYNTAX INTEGER
			UNITS "mA"
			MAX-ACCESS read-only
			STATUS current
			DESCRIPTION
				"optical bias current."
			::= { topPonOptInfoEntry 11 }

		
		-- 1.3.6.1.4.1.32285.11.2.3.3.5.1.12
		topPonOptInfoTxPower OBJECT-TYPE
			SYNTAX INTEGER
			UNITS "dBm"
			MAX-ACCESS read-only
			STATUS current
			DESCRIPTION
				"optical tx power."
			::= { topPonOptInfoEntry 12 }

		
		-- 1.3.6.1.4.1.32285.11.2.3.3.5.1.13
		topPonOptInfoRxPower OBJECT-TYPE
			SYNTAX INTEGER
			UNITS "dBm"
			MAX-ACCESS read-only
			STATUS current
			DESCRIPTION
				"optical rx power."
			::= { topPonOptInfoEntry 13 }

		
		-- 1.3.6.1.4.1.32285.11.2.3.3.5.1.14
		topPonOptInfoBitRate OBJECT-TYPE
			SYNTAX INTEGER
			UNITS "Mb/s"
			MAX-ACCESS read-only
			STATUS current
			DESCRIPTION
				"optical nominal bit rate(Mb/s)."
			::= { topPonOptInfoEntry 14 }

		
		-- 1.3.6.1.4.1.32285.11.2.3.3.5.1.15
		topPonOptMaxBitRate OBJECT-TYPE
			SYNTAX INTEGER
			MAX-ACCESS read-only
			STATUS current
			DESCRIPTION
				"Description."
			::= { topPonOptInfoEntry 15 }

		
		-- 1.3.6.1.4.1.32285.11.2.3.3.5.1.16
		topPonOptMinBitRate OBJECT-TYPE
			SYNTAX INTEGER
			MAX-ACCESS read-only
			STATUS current
			DESCRIPTION
				"Description."
			::= { topPonOptInfoEntry 16 }

		
		-- 1.3.6.1.4.1.32285.11.2.3.3.5.1.17
		topPonOpt10GBiasCurrent OBJECT-TYPE
			SYNTAX INTEGER
			MAX-ACCESS read-only
			STATUS current
			DESCRIPTION
				"Description."
			::= { topPonOptInfoEntry 17 }

		
		-- 1.3.6.1.4.1.32285.11.2.3.3.5.1.18
		topPonOpt10GTxPwr OBJECT-TYPE
			SYNTAX INTEGER
			MAX-ACCESS read-only
			STATUS current
			DESCRIPTION
				"Description."
			::= { topPonOptInfoEntry 18 }

		
		-- 1.3.6.1.4.1.32285.11.2.3.3.6
		topPonPortChgObjects OBJECT IDENTIFIER ::= { topPonPortObjects 6 }

		
		-- 1.3.6.1.4.1.32285.11.2.3.3.6.1
		ponPortSrcPonId OBJECT-TYPE
			SYNTAX INTEGER
			MAX-ACCESS read-write
			STATUS current
			DESCRIPTION
				"The source pon instance . The second byte is the slot number, the third byte is the pon port, the highest and the last byte is just reserved."
			::= { topPonPortChgObjects 1 }

		
		-- 1.3.6.1.4.1.32285.11.2.3.3.6.2
		ponPortDstPonId OBJECT-TYPE
			SYNTAX INTEGER
			MAX-ACCESS read-write
			STATUS current
			DESCRIPTION
				"The destination pon instance . The second byte is the slot number, the third byte is the pon port, the highest and the last byte is just reserved."
			::= { topPonPortChgObjects 2 }

		
		-- 1.3.6.1.4.1.32285.11.2.3.3.6.3
		ponPortChgAction OBJECT-TYPE
			SYNTAX INTEGER
			{
				action(1)
			}
			MAX-ACCESS read-write
			STATUS current
			DESCRIPTION
				" 1--action; else--no action."
			::= { topPonPortChgObjects 3 }

		
		-- 1.3.6.1.4.1.32285.11.2.3.3.7
		topPonPortRateLmtTable OBJECT-TYPE
			SYNTAX SEQUENCE OF TopPonPortRateLmtEntry
			MAX-ACCESS not-accessible
			STATUS current
			DESCRIPTION
				"Description."
			::= { topPonPortObjects 7 }

		
		-- 1.3.6.1.4.1.32285.11.2.3.3.7.1
		topPonPortRateLmtEntry OBJECT-TYPE
			SYNTAX TopPonPortRateLmtEntry
			MAX-ACCESS not-accessible
			STATUS current
			DESCRIPTION
				"Description."
			INDEX { ponPortRateLmtCardIndex, ponPortRateLmtPortIndex }
			::= { topPonPortRateLmtTable 1 }

		
		TopPonPortRateLmtEntry ::=
			SEQUENCE { 
				ponPortRateLmtCardIndex
					TopEPonSlotIndex,
				ponPortRateLmtPortIndex
					TopEPonPonIndex,
				ponPortUpRateLmt
					INTEGER,
				ponPortDownRateLmt
					INTEGER
			 }

		-- 1.3.6.1.4.1.32285.11.2.3.3.7.1.1
		ponPortRateLmtCardIndex OBJECT-TYPE
			SYNTAX TopEPonSlotIndex
			MAX-ACCESS not-accessible
			STATUS current
			DESCRIPTION
				"Description."
			::= { topPonPortRateLmtEntry 1 }

		
		-- 1.3.6.1.4.1.32285.11.2.3.3.7.1.2
		ponPortRateLmtPortIndex OBJECT-TYPE
			SYNTAX TopEPonPonIndex
			MAX-ACCESS not-accessible
			STATUS current
			DESCRIPTION
				"Description."
			::= { topPonPortRateLmtEntry 2 }

		
		-- 1.3.6.1.4.1.32285.11.2.3.3.7.1.3
		ponPortUpRateLmt OBJECT-TYPE
			SYNTAX INTEGER (0..10000000)
			MAX-ACCESS read-write
			STATUS current
			DESCRIPTION
				"Description."
			::= { topPonPortRateLmtEntry 3 }

		
		-- 1.3.6.1.4.1.32285.11.2.3.3.7.1.4
		ponPortDownRateLmt OBJECT-TYPE
			SYNTAX INTEGER (0..10000000)
			MAX-ACCESS read-write
			STATUS current
			DESCRIPTION
				"Description."
			::= { topPonPortRateLmtEntry 4 }

		
		-- 1.3.6.1.4.1.32285.11.2.3.3.8
		topPonPortSpeedTable OBJECT-TYPE
			SYNTAX SEQUENCE OF TopPonPortSpeedEntry
			MAX-ACCESS not-accessible
			STATUS current
			DESCRIPTION
				"Description."
			::= { topPonPortObjects 8 }

		
		-- 1.3.6.1.4.1.32285.11.2.3.3.8.1
		topPonPortSpeedEntry OBJECT-TYPE
			SYNTAX TopPonPortSpeedEntry
			MAX-ACCESS not-accessible
			STATUS current
			DESCRIPTION
				"Description."
			INDEX { ponPortSpeedCardIndex, ponPortSpeedPortIndex }
			::= { topPonPortSpeedTable 1 }

		
		TopPonPortSpeedEntry ::=
			SEQUENCE { 
				ponPortSpeedCardIndex
					TopEPonSlotIndex,
				ponPortSpeedPortIndex
					TopEPonPonIndex,
				ponPortSpeedMod
					INTEGER
			 }

		-- 1.3.6.1.4.1.32285.11.2.3.3.8.1.1
		ponPortSpeedCardIndex OBJECT-TYPE
			SYNTAX TopEPonSlotIndex
			MAX-ACCESS not-accessible
			STATUS current
			DESCRIPTION
				"Description."
			::= { topPonPortSpeedEntry 1 }

		
		-- 1.3.6.1.4.1.32285.11.2.3.3.8.1.2
		ponPortSpeedPortIndex OBJECT-TYPE
			SYNTAX TopEPonPonIndex
			MAX-ACCESS not-accessible
			STATUS current
			DESCRIPTION
				"Description."
			::= { topPonPortSpeedEntry 2 }

		
		-- 1.3.6.1.4.1.32285.11.2.3.3.8.1.3
		ponPortSpeedMod OBJECT-TYPE
			SYNTAX INTEGER
				{
				speed-1g(2),
				speed-2g(3),
				speed-10g(4)
				}
			MAX-ACCESS read-write
			STATUS current
			DESCRIPTION
				"Description."
			::= { topPonPortSpeedEntry 3 }

		
		-- 1.3.6.1.4.1.32285.11.2.3.3.9
		topPonPortOpticalObjects OBJECT IDENTIFIER ::= { topPonPortObjects 9 }

		
		-- 1.3.6.1.4.1.32285.11.2.3.3.9.1
		topPonOptAlarmTable OBJECT-TYPE
			SYNTAX SEQUENCE OF TopPonOptAlarmEntry
			MAX-ACCESS not-accessible
			STATUS current
			DESCRIPTION
				"Description."
			::= { topPonPortOpticalObjects 1 }

		
		-- 1.3.6.1.4.1.32285.11.2.3.3.9.1.1
		topPonOptAlarmEntry OBJECT-TYPE
			SYNTAX TopPonOptAlarmEntry
			MAX-ACCESS not-accessible
			STATUS current
			DESCRIPTION
				"Description."
			INDEX { topPonOptCardIndex, topPonOptPonIndex, topPonOptAlarmIndex }
			::= { topPonOptAlarmTable 1 }

		
		TopPonOptAlarmEntry ::=
			SEQUENCE { 
				topPonOptCardIndex
					TopEPonSlotIndex,
				topPonOptPonIndex
					TopEPonPonIndex,
				topPonOptAlarmIndex
					INTEGER,
				topPonOptThresholdValue
					INTEGER,
				topPonOptAlarmState
					INTEGER,
				topPonOptAlarmCount
					INTEGER,
				topPonOptAlarmRowStatus
					RowStatus
			 }

		-- 1.3.6.1.4.1.32285.11.2.3.3.9.1.1.1
		topPonOptCardIndex OBJECT-TYPE
			SYNTAX TopEPonSlotIndex
			MAX-ACCESS not-accessible
			STATUS current
			DESCRIPTION
				"The slot index."
			::= { topPonOptAlarmEntry 1 }

		
		-- 1.3.6.1.4.1.32285.11.2.3.3.9.1.1.2
		topPonOptPonIndex OBJECT-TYPE
			SYNTAX TopEPonPonIndex
			MAX-ACCESS not-accessible
			STATUS current
			DESCRIPTION
				"The pon index."
			::= { topPonOptAlarmEntry 2 }

		
		-- 1.3.6.1.4.1.32285.11.2.3.3.9.1.1.3
		topPonOptAlarmIndex OBJECT-TYPE
			SYNTAX INTEGER
			MAX-ACCESS not-accessible
			STATUS current
			DESCRIPTION
				"The pon optical alarm index."
			::= { topPonOptAlarmEntry 3 }

		
		-- 1.3.6.1.4.1.32285.11.2.3.3.9.1.1.4
		topPonOptThresholdValue OBJECT-TYPE
			SYNTAX INTEGER
			MAX-ACCESS read-write
			STATUS current
			DESCRIPTION
				"The pon optical threshold value."
			::= { topPonOptAlarmEntry 4 }

		
		-- 1.3.6.1.4.1.32285.11.2.3.3.9.1.1.5
		topPonOptAlarmState OBJECT-TYPE
			SYNTAX INTEGER
			MAX-ACCESS read-write
			STATUS current
			DESCRIPTION
				"The pon aptical alarm state:2--disable,1--enable."
			::= { topPonOptAlarmEntry 5 }

		
		-- 1.3.6.1.4.1.32285.11.2.3.3.9.1.1.6
		topPonOptAlarmCount OBJECT-TYPE
			SYNTAX INTEGER
			MAX-ACCESS read-only
			STATUS current
			DESCRIPTION
				"The count of pon optical alarm."
			::= { topPonOptAlarmEntry 6 }

		
		-- 1.3.6.1.4.1.32285.11.2.3.3.9.1.1.7
		topPonOptAlarmRowStatus OBJECT-TYPE
			SYNTAX RowStatus
			MAX-ACCESS read-create
			STATUS current
			DESCRIPTION
				"Add/Del/Set."
			::= { topPonOptAlarmEntry 7 }

		
		-- 1.3.6.1.4.1.32285.11.2.3.3.10
		topPonPortInfoTable OBJECT-TYPE
			SYNTAX SEQUENCE OF TopPonPortInfoEntry
			MAX-ACCESS not-accessible
			STATUS current
			DESCRIPTION
				"Description."
			::= { topPonPortObjects 10 }

		
		-- 1.3.6.1.4.1.32285.11.2.3.3.10.1
		topPonPortInfoEntry OBJECT-TYPE
			SYNTAX TopPonPortInfoEntry
			MAX-ACCESS not-accessible
			STATUS current
			DESCRIPTION
				"Description."
			INDEX { topPonPortCardIndex, topPonPortIndex }
			::= { topPonPortInfoTable 1 }

		
		TopPonPortInfoEntry ::=
			SEQUENCE { 
				topPonPortCardIndex
					TopEPonSlotIndex,
				topPonPortIndex
					TopEPonPonIndex,
				topPonPortName
					OCTET STRING
			 }

		-- 1.3.6.1.4.1.32285.11.2.3.3.10.1.1
		topPonPortCardIndex OBJECT-TYPE
			SYNTAX TopEPonSlotIndex
			MAX-ACCESS not-accessible
			STATUS current
			DESCRIPTION
				"The slot index."
			::= { topPonPortInfoEntry 1 }

		
		-- 1.3.6.1.4.1.32285.11.2.3.3.10.1.2
		topPonPortIndex OBJECT-TYPE
			SYNTAX TopEPonPonIndex
			MAX-ACCESS not-accessible
			STATUS current
			DESCRIPTION
				"The pon index."
			::= { topPonPortInfoEntry 2 }

		
		-- 1.3.6.1.4.1.32285.11.2.3.3.10.1.3
		topPonPortName OBJECT-TYPE
			SYNTAX OCTET STRING (SIZE (1..63))
			MAX-ACCESS read-write
			STATUS current
			DESCRIPTION
				"The pon port-name."
			::= { topPonPortInfoEntry 3 }

		
		-- 1.3.6.1.4.1.32285.11.2.3.3.11
		topPonPortLoopDetectTable OBJECT-TYPE
			SYNTAX SEQUENCE OF TopPonPortLoopDetectEntry
			MAX-ACCESS not-accessible
			STATUS current
			DESCRIPTION
				"Description."
			::= { topPonPortObjects 11 }

		
		-- 1.3.6.1.4.1.32285.11.2.3.3.11.1
		topPonPortLoopDetectEntry OBJECT-TYPE
			SYNTAX TopPonPortLoopDetectEntry
			MAX-ACCESS not-accessible
			STATUS current
			DESCRIPTION
				"Description."
			INDEX { topPonPortLoopDetectCardIndex, topPonPortLoopDetectPortIndex }
			::= { topPonPortLoopDetectTable 1 }

		
		TopPonPortLoopDetectEntry ::=
			SEQUENCE { 
				topPonPortLoopDetectCardIndex
					TopEPonSlotIndex,
				topPonPortLoopDetectPortIndex
					TopEPonPonIndex,
				topPonPortLoopDetectMode
					INTEGER,
				topPonPortLoopDetectStatus
					INTEGER
			 }

		-- 1.3.6.1.4.1.32285.11.2.3.3.11.1.1
		topPonPortLoopDetectCardIndex OBJECT-TYPE
			SYNTAX TopEPonSlotIndex
			MAX-ACCESS not-accessible
			STATUS current
			DESCRIPTION
				"Description."
			::= { topPonPortLoopDetectEntry 1 }

		
		-- 1.3.6.1.4.1.32285.11.2.3.3.11.1.2
		topPonPortLoopDetectPortIndex OBJECT-TYPE
			SYNTAX TopEPonPonIndex
			MAX-ACCESS not-accessible
			STATUS current
			DESCRIPTION
				"Description."
			::= { topPonPortLoopDetectEntry 2 }

		
		-- 1.3.6.1.4.1.32285.11.2.3.3.11.1.3
		topPonPortLoopDetectMode OBJECT-TYPE
			SYNTAX INTEGER
				{				
				enable(1),
				disable(2)
				}
			MAX-ACCESS read-write
			STATUS current
			DESCRIPTION
				"Description."
			DEFVAL { disable }
			::= { topPonPortLoopDetectEntry 3 }

		
		-- 1.3.6.1.4.1.32285.11.2.3.3.11.1.4
		topPonPortLoopDetectStatus OBJECT-TYPE
			SYNTAX INTEGER
				{
				not-detected(0),
				detected(1)
				}
			MAX-ACCESS read-only
			STATUS current
			DESCRIPTION
				"Description."
			::= { topPonPortLoopDetectEntry 4 }

		
		-- 1.3.6.1.4.1.32285.11.2.3.4
		topOnuObjects OBJECT IDENTIFIER ::= { topvisionEponTree 4 }

		
		-- 1.3.6.1.4.1.32285.11.2.3.4.1
		topOnuCapabilityTable OBJECT-TYPE
			SYNTAX SEQUENCE OF TopOnuCapabilityEntry
			MAX-ACCESS not-accessible
			STATUS current
			DESCRIPTION
				"A list of onuCapTable entries. "
			::= { topOnuObjects 1 }

		
		-- 1.3.6.1.4.1.32285.11.2.3.4.1.1
		topOnuCapabilityEntry OBJECT-TYPE
			SYNTAX TopOnuCapabilityEntry
			MAX-ACCESS not-accessible
			STATUS current
			DESCRIPTION
				"The topOnuCapabilityEntry Information"
			INDEX { topOnuCapCardIndex, topOnuCapPonIndex, topOnuCapOnuIndex }
			::= { topOnuCapabilityTable 1 }

		
		TopOnuCapabilityEntry ::=
			SEQUENCE { 
				topOnuCapCardIndex
					TopEPonSlotIndex,
				topOnuCapPonIndex
					TopEPonPonIndex,
				topOnuCapOnuIndex
					TopEPonOnuAuthNum,
				topOnuCapDeregister
					INTEGER,
				topOnuCapMacAddrMaxQuantity
					INTEGER,
				topOnuPonPerfStats15minuteEnable
					INTEGER,
				topOnuPonPerfStats24hourEnable
					INTEGER,
				topOnuTemperatureDetectEnable
					INTEGER,
				topOnuCurrentTemperature
					INTEGER,
				topOnuIsolationEnable
					INTEGER,
                topOnuAction
                	INTEGER,
                topOnuHardwareVersion
                    OCTET STRING,
				topOnuMgmtIp
					IpAddress,
				topOnuNetMask
					IpAddress,
				topOnuGateway
					IpAddress,
                                topOnuExtAttr
                                        OCTET STRING
			 }

		-- 1.3.6.1.4.1.32285.11.2.3.4.1.1.1
		topOnuCapCardIndex OBJECT-TYPE
			SYNTAX TopEPonSlotIndex
			MAX-ACCESS not-accessible
			STATUS current
			DESCRIPTION
				"onu slot Index"
			::= { topOnuCapabilityEntry 1 }

		
		-- 1.3.6.1.4.1.32285.11.2.3.4.1.1.2
		topOnuCapPonIndex OBJECT-TYPE
			SYNTAX TopEPonPonIndex
			MAX-ACCESS not-accessible
			STATUS current
			DESCRIPTION
				"onu pon Index"
			::= { topOnuCapabilityEntry 2 }

		
		-- 1.3.6.1.4.1.32285.11.2.3.4.1.1.3
		topOnuCapOnuIndex OBJECT-TYPE
			SYNTAX TopEPonOnuAuthNum
			MAX-ACCESS not-accessible
			STATUS current
			DESCRIPTION
				"onu auth Index"
			::= { topOnuCapabilityEntry 3 }

		
		-- 1.3.6.1.4.1.32285.11.2.3.4.1.1.4
		topOnuCapDeregister OBJECT-TYPE
			SYNTAX INTEGER
				{
				noOperation(0),
				deregister(1)
				}
			MAX-ACCESS read-write
			STATUS current
			DESCRIPTION
				"deregister ONU"
			DEFVAL { 0 }
			::= { topOnuCapabilityEntry 4 }

		
		-- 1.3.6.1.4.1.32285.11.2.3.4.1.1.5
		topOnuCapMacAddrMaxQuantity OBJECT-TYPE
			SYNTAX INTEGER (0..64)
			MAX-ACCESS read-write
			STATUS current
			DESCRIPTION
				"total mac add capability in ONU
				0:do not limit, max value depend on ONU
				other value: limited to specfic value"
			::= { topOnuCapabilityEntry 5 }

		
		-- 1.3.6.1.4.1.32285.11.2.3.4.1.1.6
		topOnuPonPerfStats15minuteEnable OBJECT-TYPE
			SYNTAX INTEGER
				{
				enable(1),
				disable(2)
				}
			MAX-ACCESS read-write
			STATUS current
			DESCRIPTION
				"disable-2, enable-1"
			DEFVAL { 2 }
			::= { topOnuCapabilityEntry 6 }

		
		-- 1.3.6.1.4.1.32285.11.2.3.4.1.1.7
		topOnuPonPerfStats24hourEnable OBJECT-TYPE
			SYNTAX INTEGER
				{
				enable(1),
				disable(2)
				}
			MAX-ACCESS read-write
			STATUS current
			DESCRIPTION
				"disable-2, enable-1"
			DEFVAL { 2 }
			::= { topOnuCapabilityEntry 7 }

		
		-- 1.3.6.1.4.1.32285.11.2.3.4.1.1.8
		topOnuTemperatureDetectEnable OBJECT-TYPE
			SYNTAX INTEGER
				{
				enable(1),
				disable(2)
				}
			MAX-ACCESS read-write
			STATUS current
			DESCRIPTION
				"disable-2, enable-1"
			DEFVAL { 2 }
			::= { topOnuCapabilityEntry 8 }

		
		-- 1.3.6.1.4.1.32285.11.2.3.4.1.1.9
		topOnuCurrentTemperature OBJECT-TYPE
			SYNTAX INTEGER
			MAX-ACCESS read-only
			STATUS current
			DESCRIPTION
				"when ONU does not support temperature detection,
				fill with the temperature of optical module in PON port."
			::= { topOnuCapabilityEntry 9 }

		
		-- 1.3.6.1.4.1.32285.11.2.3.4.1.1.10
		topOnuIsolationEnable OBJECT-TYPE
			SYNTAX INTEGER
				{
				true(1),
				false(2)
				}
			MAX-ACCESS read-write
			STATUS current
			DESCRIPTION
				"Description."
			::= { topOnuCapabilityEntry 10 }
		
		-- 1.3.6.1.4.1.32285.11.2.3.4.1.1.11
		topOnuAction OBJECT-TYPE
			SYNTAX INTEGER
				{
				active(1),
				commit(2)
				}
			MAX-ACCESS read-write
			STATUS current
			DESCRIPTION
				"ONU action active or commit."
			::= { topOnuCapabilityEntry 11 }
            
        -- 1.3.6.1.4.1.32285.11.2.3.4.1.1.12
        topOnuHardwareVersion OBJECT-TYPE
            SYNTAX OCTET STRING (SIZE(0..8))
            MAX-ACCESS read-only
            STATUS current
            DESCRIPTION
                "ONU hardware version."
            ::= { topOnuCapabilityEntry 12 }
		
        -- 1.3.6.1.4.1.32285.11.2.3.4.1.1.13
		topOnuMgmtIp OBJECT-TYPE
			SYNTAX IpAddress
			MAX-ACCESS read-write
			STATUS current
			DESCRIPTION
				" onu management ip address."
			::= { topOnuCapabilityEntry 13 }
			
        -- 1.3.6.1.4.1.32285.11.2.3.4.1.1.14
		topOnuNetMask OBJECT-TYPE
			SYNTAX IpAddress
			MAX-ACCESS read-write
			STATUS current
			DESCRIPTION
				"  onu management net mask."
			::= { topOnuCapabilityEntry 14 }
		
		-- 1.3.6.1.4.1.32285.11.2.3.4.1.1.15
		topOnuGateway OBJECT-TYPE
			SYNTAX IpAddress
			MAX-ACCESS read-write
			STATUS current
			DESCRIPTION
				"  onu management gateway."
			::= { topOnuCapabilityEntry 15 }

		topOnuExtAttr OBJECT-TYPE
			SYNTAX OCTET STRING (SIZE (16))
			MAX-ACCESS read-only
			STATUS current
			DESCRIPTION
				"OCTET[0] GE port num;
                                 OCTET[1] FE port num(excluding GE);
                                 OCTET[2] VoIp interface;
                                 OCTET[3] TDM interface;
                                 OCTET[4] ADSL2+ interface;
                                 OCTET[5] VDSL2+ interface;
                                 OCTET[6] WLAN interface;
                                 OCTET[7] USB port num;
                                 OCTET[8] CATV RF interface;
                                 OCTET[9~15] reserved 0"
			::= { topOnuCapabilityEntry 16 }
		
		-- 1.3.6.1.4.1.32285.11.2.3.4.2
		topOnuAuthMgmt OBJECT IDENTIFIER ::= { topOnuObjects 2 }

		
		-- 1.3.6.1.4.1.32285.11.2.3.4.2.1
		topOnuAuthLogicSnTable OBJECT-TYPE
			SYNTAX SEQUENCE OF TopOnuAuthLogicSNEntry
			MAX-ACCESS not-accessible
			STATUS current
			DESCRIPTION
				"A list of onuAuthenticationPreConfigTable entries. "
			::= { topOnuAuthMgmt 1 }

		
		-- 1.3.6.1.4.1.32285.11.2.3.4.2.1.1
		topOnuAuthLogicSnEntry OBJECT-TYPE
			SYNTAX TopOnuAuthLogicSNEntry
			MAX-ACCESS not-accessible
			STATUS current
			DESCRIPTION
				"The onuAuthenticationPreConfigEntry Information"
			INDEX { topOnuAuthLogicSnCardIndex, topOnuAuthLogicSnPonIndex, topOnuAuthLogicSnOnuIndex }
			::= { topOnuAuthLogicSnTable 1 }

		
		TopOnuAuthLogicSNEntry ::=
			SEQUENCE { 
				topOnuAuthLogicSnCardIndex
					TopEPonSlotIndex,
				topOnuAuthLogicSnPonIndex
					TopEPonPonIndex,
				topOnuAuthLogicSnOnuIndex
					TopEPonOnuAuthNum,
				topOnuAuthLogicSnMode
					INTEGER,
				topOnuAuthLogicSn
					OCTET STRING,
				topOnuAuthPassword
					OCTET STRING,
				topOnuAuthLogicSnAction
					INTEGER,
				topOnuAuthLogicSnRowStatus
					RowStatus
			 }

		-- 1.3.6.1.4.1.32285.11.2.3.4.2.1.1.1
		topOnuAuthLogicSnCardIndex OBJECT-TYPE
			SYNTAX TopEPonSlotIndex
			MAX-ACCESS not-accessible
			STATUS current
			DESCRIPTION
				"slot Index"
			::= { topOnuAuthLogicSnEntry 1 }

		
		-- 1.3.6.1.4.1.32285.11.2.3.4.2.1.1.2
		topOnuAuthLogicSnPonIndex OBJECT-TYPE
			SYNTAX TopEPonPonIndex
			MAX-ACCESS not-accessible
			STATUS current
			DESCRIPTION
				"pon Index"
			::= { topOnuAuthLogicSnEntry 2 }

		
		-- 1.3.6.1.4.1.32285.11.2.3.4.2.1.1.3
		topOnuAuthLogicSnOnuIndex OBJECT-TYPE
			SYNTAX TopEPonOnuAuthNum
			MAX-ACCESS not-accessible
			STATUS current
			DESCRIPTION
				"onu logical ID"
			::= { topOnuAuthLogicSnEntry 3 }

		
		-- 1.3.6.1.4.1.32285.11.2.3.4.2.1.1.4
		topOnuAuthLogicSnMode OBJECT-TYPE
			SYNTAX INTEGER
				{
				logicSnAndPassword(1),
				logicSnOnly(2),
				passwordOnly(3)
				}
			MAX-ACCESS read-only
			STATUS current
			DESCRIPTION
				"1-logic sn+password,
				2-logic sn only
				3-password only"
			DEFVAL { 1 }
			::= { topOnuAuthLogicSnEntry 4 }

		
		-- 1.3.6.1.4.1.32285.11.2.3.4.2.1.1.5
		topOnuAuthLogicSn OBJECT-TYPE
			SYNTAX OCTET STRING (SIZE (1..24))
			MAX-ACCESS read-create
			STATUS current
			DESCRIPTION
				"logic sn"
			::= { topOnuAuthLogicSnEntry 5 }

		
		-- 1.3.6.1.4.1.32285.11.2.3.4.2.1.1.6
		topOnuAuthPassword OBJECT-TYPE
			SYNTAX OCTET STRING (SIZE (0..12))
			MAX-ACCESS read-create
			STATUS current
			DESCRIPTION
				"password"
			::= { topOnuAuthLogicSnEntry 6 }

		
		-- 1.3.6.1.4.1.32285.11.2.3.4.2.1.1.7
		topOnuAuthLogicSnAction OBJECT-TYPE
			SYNTAX INTEGER
				{
				accept(1),
				reject(2)
				}
			MAX-ACCESS read-create
			STATUS current
			DESCRIPTION
				"Authen Action
				This is optional in function"
			DEFVAL { 1 }
			::= { topOnuAuthLogicSnEntry 7 }

		
		-- 1.3.6.1.4.1.32285.11.2.3.4.2.1.1.8
		topOnuAuthLogicSnRowStatus OBJECT-TYPE
			SYNTAX RowStatus
			MAX-ACCESS read-create
			STATUS current
			DESCRIPTION
				"authen Row Status"
			::= { topOnuAuthLogicSnEntry 8 }


		-- 1.3.6.1.4.1.32285.11.2.3.4.2.2
		topOnuAuthBlockExtTable OBJECT-TYPE
			SYNTAX SEQUENCE OF TopOnuAuthBlockExtEntry
			MAX-ACCESS not-accessible
			STATUS current
			DESCRIPTION
				"A list of topOnuAuthBlockExtTable entries. "
			::= { topOnuAuthMgmt 2 }

		
		-- 1.3.6.1.4.1.32285.11.2.3.4.2.2.1
		topOnuAuthBlockExtEntry OBJECT-TYPE
			SYNTAX TopOnuAuthBlockExtEntry
			MAX-ACCESS not-accessible
			STATUS current
			DESCRIPTION
				"unauthorized onu information.
				Index depends on onuAuthenBlockOnuId, defined in onuAuthenticationBlockTable of NSCRTV MIB.
				This information will be read only, not support row-status operation.
				In case of implementation ONU authentication, just config onu in advance."
			INDEX { topOnuAuthBlockExtOnuId }
			::= { topOnuAuthBlockExtTable 1 }

		
		TopOnuAuthBlockExtEntry ::=
			SEQUENCE { 
				topOnuAuthBlockExtOnuId
					EponDeviceIndex,
				topOnuAuthBlockedExtLogicSn
					OCTET STRING,
				topOnuAuthBlockedExtPwd
					OCTET STRING
			 }

		-- 1.3.6.1.4.1.32285.11.2.3.4.2.2.1.1
		topOnuAuthBlockExtOnuId OBJECT-TYPE
			SYNTAX EponDeviceIndex
			MAX-ACCESS not-accessible
			STATUS current
			DESCRIPTION
				"ONU Id"
			::= { topOnuAuthBlockExtEntry 1 }

		
		-- 1.3.6.1.4.1.32285.11.2.3.4.2.2.1.2
		topOnuAuthBlockedExtLogicSn OBJECT-TYPE
			SYNTAX OCTET STRING (SIZE (0..24))
			MAX-ACCESS read-only
			STATUS current
			DESCRIPTION
				"logic sn"
			::= { topOnuAuthBlockExtEntry 2 }

		
		-- 1.3.6.1.4.1.32285.11.2.3.4.2.2.1.3
		topOnuAuthBlockedExtPwd OBJECT-TYPE
			SYNTAX OCTET STRING (SIZE (0..12))
			MAX-ACCESS read-only
			STATUS current
			DESCRIPTION
				"password"
			::= { topOnuAuthBlockExtEntry 3 }

		
		-- 1.3.6.1.4.1.32285.11.2.3.4.2.3
		topOnuProductTable OBJECT-TYPE
			SYNTAX SEQUENCE OF TopOnuProductEntry
			MAX-ACCESS not-accessible
			STATUS current
			DESCRIPTION
				"ONU pre auth product table."
			::= { topOnuAuthMgmt 3 }

		
		-- 1.3.6.1.4.1.32285.11.2.3.4.2.3.1
		topOnuProductEntry OBJECT-TYPE
			SYNTAX TopOnuProductEntry
			MAX-ACCESS not-accessible
			STATUS current
			DESCRIPTION
				"ONU pre auth product table entry."
			INDEX { topOnuProductCardIndex, topOnuProductPonIndex, topOnuProductOnuIndex }
			::= { topOnuProductTable 1 }

		
		TopOnuProductEntry ::=
			SEQUENCE { 
				topOnuProductCardIndex
					TopEPonSlotIndex,
				topOnuProductPonIndex
					TopEPonPonIndex,
				topOnuProductOnuIndex
					TopEPonOnuAuthNum,
				topOnuProductType
					INTEGER,
	            topOnuActiveStatus
					INTEGER				
			 }

		-- 1.3.6.1.4.1.32285.11.2.3.4.2.3.1.1
		topOnuProductCardIndex OBJECT-TYPE
			SYNTAX TopEPonSlotIndex
			MAX-ACCESS not-accessible
			STATUS current
			DESCRIPTION
				"Slot index."
			::= { topOnuProductEntry 1 }

		
		-- 1.3.6.1.4.1.32285.11.2.3.4.2.3.1.2
		topOnuProductPonIndex OBJECT-TYPE
			SYNTAX TopEPonPonIndex
			MAX-ACCESS not-accessible
			STATUS current
			DESCRIPTION
				"pon port index."
			::= { topOnuProductEntry 2 }

		
		-- 1.3.6.1.4.1.32285.11.2.3.4.2.3.1.3
		topOnuProductOnuIndex OBJECT-TYPE
			SYNTAX TopEPonOnuAuthNum
			MAX-ACCESS not-accessible
			STATUS current
			DESCRIPTION
				"onu id index."
			::= { topOnuProductEntry 3 }

		
		-- 1.3.6.1.4.1.32285.11.2.3.4.2.3.1.4
		topOnuProductType OBJECT-TYPE
			SYNTAX INTEGER
			MAX-ACCESS read-write
			STATUS current
			DESCRIPTION
				"Onu product name,Set the product like this:
                PN8621: 33 (0x21)
                PN8622: 34 (0x22)
                PN8623: 35 (0x23)
                PN8624: 36 (0x24)
                PN8625: 37 (0x25)
                .....
                if you want to set onu type 'none', you should set 0"
			::= { topOnuProductEntry 4 }

		
		-- 1.3.6.1.4.1.32285.11.2.3.4.2.3.1.5
		topOnuActiveStatus OBJECT-TYPE
			SYNTAX INTEGER
				{
				active(1),
				deactive(2)
				}
			MAX-ACCESS read-write
			STATUS current
			DESCRIPTION
				"1--active,2--deactive"
			::= { topOnuProductEntry 5 }

		

		-- 1.3.6.1.4.1.32285.11.2.3.4.3
		topOnuRstpMgmtObjects OBJECT IDENTIFIER ::= { topOnuObjects 3 }

		
		-- 1.3.6.1.4.1.32285.11.2.3.4.3.1
		topOnuRstpConfigTable OBJECT-TYPE
			SYNTAX SEQUENCE OF TopOnuRstpConfigEntry
			MAX-ACCESS not-accessible
			STATUS current
			DESCRIPTION
				"ONU RSTP config table"
			::= { topOnuRstpMgmtObjects 1 }

		
		-- 1.3.6.1.4.1.32285.11.2.3.4.3.1.1
		topOnuRstpConfigEntry OBJECT-TYPE
			SYNTAX TopOnuRstpConfigEntry
			MAX-ACCESS not-accessible
			STATUS current
			DESCRIPTION
				"The onuInfoEntry Information"
			INDEX { topOnuRstpCardIndex, topOnuRstpPonIndex, topOnuRstpOnuIndex }
			::= { topOnuRstpConfigTable 1 }

		
		TopOnuRstpConfigEntry ::=
			SEQUENCE { 
				topOnuRstpCardIndex
					TopEPonSlotIndex,
				topOnuRstpPonIndex
					TopEPonPonIndex,
				topOnuRstpOnuIndex
					TopEPonOnuAuthNum,
				topOnuRstpBridgeMode
					INTEGER
			 }

		-- 1.3.6.1.4.1.32285.11.2.3.4.3.1.1.1
		topOnuRstpCardIndex OBJECT-TYPE
			SYNTAX TopEPonSlotIndex
			MAX-ACCESS not-accessible
			STATUS current
			DESCRIPTION
				"slot Index"
			::= { topOnuRstpConfigEntry 1 }

		
		-- 1.3.6.1.4.1.32285.11.2.3.4.3.1.1.2
		topOnuRstpPonIndex OBJECT-TYPE
			SYNTAX TopEPonPonIndex
			MAX-ACCESS not-accessible
			STATUS current
			DESCRIPTION
				"pon Index"
			::= { topOnuRstpConfigEntry 2 }

		
		-- 1.3.6.1.4.1.32285.11.2.3.4.3.1.1.3
		topOnuRstpOnuIndex OBJECT-TYPE
			SYNTAX TopEPonOnuAuthNum
			MAX-ACCESS not-accessible
			STATUS current
			DESCRIPTION
				"ONU auth Index"
			::= { topOnuRstpConfigEntry 3 }

		
		-- 1.3.6.1.4.1.32285.11.2.3.4.3.1.1.4
		topOnuRstpBridgeMode OBJECT-TYPE
			SYNTAX INTEGER
				{
				enable(1),
				disable(2),
				passThrough(3)
				}
			MAX-ACCESS read-write
			STATUS current
			DESCRIPTION
				"onu rstp mode"
			DEFVAL { 2 }
			::= { topOnuRstpConfigEntry 4 }

		
		-- 1.3.6.1.4.1.32285.11.2.3.4.4
		topOnuVoipMgmtObjects OBJECT IDENTIFIER ::= { topOnuObjects 4 }

		
		-- 1.3.6.1.4.1.32285.11.2.3.4.4.1
		topOnuVoipConfigTable OBJECT-TYPE
			SYNTAX SEQUENCE OF TopOnuVoipConfigEntry
			MAX-ACCESS not-accessible
			STATUS current
			DESCRIPTION
				"ONU RSTP config table"
			::= { topOnuVoipMgmtObjects 1 }

		
		-- 1.3.6.1.4.1.32285.11.2.3.4.4.1.1
		topOnuVoipConfigEntry OBJECT-TYPE
			SYNTAX TopOnuVoipConfigEntry
			MAX-ACCESS not-accessible
			STATUS current
			DESCRIPTION
				"The onuInfoEntry Information"
			INDEX { topOnuVoipCardIndex, topOnuVoipPonIndex, topOnuVoipOnuIndex }
			::= { topOnuVoipConfigTable 1 }

		
		TopOnuVoipConfigEntry ::=
			SEQUENCE { 
				topOnuVoipCardIndex
					TopEPonSlotIndex,
				topOnuVoipPonIndex
					TopEPonPonIndex,
				topOnuVoipOnuIndex
					TopEPonOnuAuthNum,
				topOnuVoipEnable
					INTEGER
			 }

		-- 1.3.6.1.4.1.32285.11.2.3.4.4.1.1.1
		topOnuVoipCardIndex OBJECT-TYPE
			SYNTAX TopEPonSlotIndex
			MAX-ACCESS not-accessible
			STATUS current
			DESCRIPTION
				"slot Index"
			::= { topOnuVoipConfigEntry 1 }

		
		-- 1.3.6.1.4.1.32285.11.2.3.4.4.1.1.2
		topOnuVoipPonIndex OBJECT-TYPE
			SYNTAX TopEPonPonIndex
			MAX-ACCESS not-accessible
			STATUS current
			DESCRIPTION
				"pon Index"
			::= { topOnuVoipConfigEntry 2 }

		
		-- 1.3.6.1.4.1.32285.11.2.3.4.4.1.1.3
		topOnuVoipOnuIndex OBJECT-TYPE
			SYNTAX TopEPonOnuAuthNum
			MAX-ACCESS not-accessible
			STATUS current
			DESCRIPTION
				"ONU auth Index"
			::= { topOnuVoipConfigEntry 3 }

		
		-- 1.3.6.1.4.1.32285.11.2.3.4.4.1.1.4
		topOnuVoipEnable OBJECT-TYPE
			SYNTAX INTEGER
				{
				enable(1),
				disable(2)
				}
			MAX-ACCESS read-write
			STATUS current
			DESCRIPTION
				"ONU VoIP config, not supported at present"
			DEFVAL { 2 }
			::= { topOnuVoipConfigEntry 4 }

		
		-- 1.3.6.1.4.1.32285.11.2.3.4.5
		topOnuCatvMgmtObjects OBJECT IDENTIFIER ::= { topOnuObjects 5 }

		
		-- 1.3.6.1.4.1.32285.11.2.3.4.5.1
		topOnuCatvConfigTable OBJECT-TYPE
			SYNTAX SEQUENCE OF TopOnuCatvConfigEntry
			MAX-ACCESS not-accessible
			STATUS current
			DESCRIPTION
				"ONU RSTP config table"
			::= { topOnuCatvMgmtObjects 1 }

		
		-- 1.3.6.1.4.1.32285.11.2.3.4.5.1.1
		topOnuCatvConfigEntry OBJECT-TYPE
			SYNTAX TopOnuCatvConfigEntry
			MAX-ACCESS not-accessible
			STATUS current
			DESCRIPTION
				"The onuInfoEntry Information"
			INDEX { topOnuCatvCardIndex, topOnuCatvPonIndex, topOnuCatvOnuIndex }
			::= { topOnuCatvConfigTable 1 }

		
		TopOnuCatvConfigEntry ::=
			SEQUENCE { 
				topOnuCatvCardIndex
					TopEPonSlotIndex,
				topOnuCatvPonIndex
					TopEPonPonIndex,
				topOnuCatvOnuIndex
					TopEPonOnuAuthNum,
				topOnuCatvEnable
					INTEGER
			 }

		-- 1.3.6.1.4.1.32285.11.2.3.4.5.1.1.1
		topOnuCatvCardIndex OBJECT-TYPE
			SYNTAX TopEPonSlotIndex
			MAX-ACCESS not-accessible
			STATUS current
			DESCRIPTION
				"slot Index"
			::= { topOnuCatvConfigEntry 1 }

		
		-- 1.3.6.1.4.1.32285.11.2.3.4.5.1.1.2
		topOnuCatvPonIndex OBJECT-TYPE
			SYNTAX TopEPonPonIndex
			MAX-ACCESS not-accessible
			STATUS current
			DESCRIPTION
				"pon Index"
			::= { topOnuCatvConfigEntry 2 }

		
		-- 1.3.6.1.4.1.32285.11.2.3.4.5.1.1.3
		topOnuCatvOnuIndex OBJECT-TYPE
			SYNTAX TopEPonOnuAuthNum
			MAX-ACCESS not-accessible
			STATUS current
			DESCRIPTION
				"ONU auth Index"
			::= { topOnuCatvConfigEntry 3 }

		
		-- 1.3.6.1.4.1.32285.11.2.3.4.5.1.1.4
		topOnuCatvEnable OBJECT-TYPE
			SYNTAX INTEGER
				{
				enable(1),
				disable(2)
				}
			MAX-ACCESS read-write
			STATUS current
			DESCRIPTION
				"ONU VoIP config, not supported at present"
			DEFVAL { 2 }
			::= { topOnuCatvConfigEntry 4 }

		
		-- 1.3.6.1.4.1.32285.11.2.3.4.6
		topOnuUpgradeMgmtObjects OBJECT IDENTIFIER ::= { topOnuObjects 6 }

		
		-- 1.3.6.1.4.1.32285.11.2.3.4.6.1
		topOnuUpgradeTable OBJECT-TYPE
			SYNTAX SEQUENCE OF TopOnuUpgradeEntry
			MAX-ACCESS not-accessible
			STATUS current
			DESCRIPTION
				"ONU batch upgrading table"
			::= { topOnuUpgradeMgmtObjects 1 }

		
		-- 1.3.6.1.4.1.32285.11.2.3.4.6.1.1
		topOnuUpgradeEntry OBJECT-TYPE
			SYNTAX TopOnuUpgradeEntry
			MAX-ACCESS not-accessible
			STATUS current
			DESCRIPTION
				"The onu batch upgrading entry"
			INDEX { topOnuUpgradeTransactionIndex }
			::= { topOnuUpgradeTable 1 }

		
		TopOnuUpgradeEntry ::=
			SEQUENCE { 
				topOnuUpgradeTransactionIndex
					INTEGER,
				topOnuUpgradeSlotNum
					TopEPonSlotIndex,
				topOnuUpgradeOnuType
					INTEGER,
        topOnuUpgradeHwVersion
          OCTET STRING,
				topOnuUpgradeFileName
					OCTET STRING,
				topOnuUpgradeFileType
					INTEGER,
				topOnuUpgradeMode
					INTEGER,
				topOnuUpgradeOnuList
					OCTET STRING,
				topOnuUpgradeOperAction
					INTEGER,
				topOnuUpgradeStatus
					OCTET STRING,
				topOnuUpgradeRowStatus
					RowStatus,
				topOnuUpgradeOption
					INTEGER
			 }

		-- 1.3.6.1.4.1.32285.11.2.3.4.6.1.1.1
		topOnuUpgradeTransactionIndex OBJECT-TYPE
			SYNTAX INTEGER
			MAX-ACCESS not-accessible
			STATUS current
			DESCRIPTION
				"The ID of Transaction its belongs to.
				Support max 100 records,
				otherwise delete previous transactions firstly"
			::= { topOnuUpgradeEntry 1 }

		
		-- 1.3.6.1.4.1.32285.11.2.3.4.6.1.1.2
		topOnuUpgradeSlotNum OBJECT-TYPE
			SYNTAX TopEPonSlotIndex
			MAX-ACCESS read-create
			STATUS current
			DESCRIPTION
				"This object makes sense in two cases. 
				One is to provide number of slot which will download its bootrom/app 
				files from the SCU ramdisk into its own Flash memory. 
				The other is to provide number of slot which the OLT/ONUs who will 
				download their firmware files from the SCU ramdisk into their own Flash memory 
				reside on."
			::= { topOnuUpgradeEntry 2 }

		
		-- 1.3.6.1.4.1.32285.11.2.3.4.6.1.1.3
		topOnuUpgradeOnuType OBJECT-TYPE
			SYNTAX INTEGER
			MAX-ACCESS read-create
			STATUS current
			DESCRIPTION
				"An integer value to identify the Onu Type to be upgraded,
				as per product plan."
			::= { topOnuUpgradeEntry 3 }

		
		-- 1.3.6.1.4.1.32285.11.2.3.4.6.1.1.4
		topOnuUpgradeHwVersion OBJECT-TYPE
			SYNTAX OCTET STRING (SIZE (0..8))
			MAX-ACCESS read-write
			STATUS current
			DESCRIPTION
				"Description."
			::= { topOnuUpgradeEntry 4 }

		
		-- 1.3.6.1.4.1.32285.11.2.3.4.6.1.1.5
		topOnuUpgradeFileName OBJECT-TYPE
			SYNTAX OCTET STRING (SIZE (1..63))
			MAX-ACCESS read-create
			STATUS current
			DESCRIPTION
				"This is the name of the source file name, including file path."
			::= { topOnuUpgradeEntry 5 }

		
		-- 1.3.6.1.4.1.32285.11.2.3.4.6.1.1.6
		topOnuUpgradeFileType OBJECT-TYPE
			SYNTAX INTEGER
				{
				onuBoot(9),
				onuConfig(10),
				onuFirmware(11),
				onuApp(12),
				onuCombinedPkg(13)
				}
			MAX-ACCESS read-create
			STATUS current
			DESCRIPTION
				"This object indicates the file type of operation to be performed.   		 
				Selecting boot(9)/config(10)/firmware(11)/app(12)/onuCombinedPkg(12)
				will perform an upgrade operation to ONU chipset(s).
				For onuCombinedPkg(13), OLT will check package header so as to
				decided whether spliting package into multi sub-package or not,
				then sending them to ONU. If OLT can not anlyzer the package head,
				it will send them to ONU directly as one package."
			DEFVAL { 13 }
			::= { topOnuUpgradeEntry 6 }

		
		-- 1.3.6.1.4.1.32285.11.2.3.4.6.1.1.7
		topOnuUpgradeMode OBJECT-TYPE
			SYNTAX INTEGER
				{
				tk(1),
				pmc(2),
				ctc(4), 
				baseline(16),
				extend(32),
				an(64)
				}
			MAX-ACCESS read-create
			STATUS current
			DESCRIPTION
				"The Quantity of Onus to be upgraded.
				At present, ctc mode supported only,
				other value reserved for future extension.
				"
			DEFVAL { 4 }
			::= { topOnuUpgradeEntry 7 }

		
		-- 1.3.6.1.4.1.32285.11.2.3.4.6.1.1.8
		topOnuUpgradeOnuList OBJECT-TYPE
			SYNTAX OCTET STRING (SIZE (256))
			MAX-ACCESS read-create
			STATUS current
			DESCRIPTION
				"The first 128 bit (as 16 bytes) indicate those ONUs under PON index 1,
				the second 128 bit indicate those ONUs under PON index 2,
				So the max ONU quantity is 2048/128=16 PONs under one slot.
				In case some ONUs do not exist, just filled with 0x00.
				"
			::= { topOnuUpgradeEntry 8 }

		
		-- 1.3.6.1.4.1.32285.11.2.3.4.6.1.1.9
		topOnuUpgradeOperAction OBJECT-TYPE
			SYNTAX INTEGER
				{
				none(0),
				upgrade(1)
				}
			MAX-ACCESS read-create
			STATUS current
			DESCRIPTION
				"This is the action to be taken to start the upgrade operation."
			::= { topOnuUpgradeEntry 9 }

		
		-- 1.3.6.1.4.1.32285.11.2.3.4.6.1.1.10
		topOnuUpgradeStatus OBJECT-TYPE
			SYNTAX OCTET STRING (SIZE (2048))
			MAX-ACCESS read-create
			STATUS current
			DESCRIPTION
				"This variable is the result of the upgrade operation.
				1.Each OCTET represent the upgrading status of one ONU.
				From left to right, the first OCTET indicate the result of PON 1 ONU 1,
				then PON 1 ONU 2, and so on.
				the 2048 octet indicate the result of PON 16 ONU 128.
				2.In one OCTET,	idle(1), inProgress(2), success(3), failure(4),
				other values are reserved and meaningless.
				"
			::= { topOnuUpgradeEntry 10 }

		-- 1.3.6.1.4.1.32285.11.2.3.4.6.1.1.11
		topOnuUpgradeRowStatus OBJECT-TYPE
			SYNTAX RowStatus
			MAX-ACCESS read-create
			STATUS current
			DESCRIPTION
				"add/del/set"
			::= { topOnuUpgradeEntry 11 }
		
		-- 1.3.6.1.4.1.32285.11.2.3.4.6.1.1.12
		topOnuUpgradeOption OBJECT-TYPE
			SYNTAX INTEGER
				{
				none(0),
				auto-activate(1),
				auto-activatecommit(2),
				reset(3)
				}
			MAX-ACCESS read-write
			STATUS current
			DESCRIPTION
				"Description."
			::= { topOnuUpgradeEntry 12 }

		
		-- 1.3.6.1.4.1.32285.11.2.3.4.7
		topOnuAutoUpgardeMgmtObjects OBJECT IDENTIFIER ::= { topOnuObjects 7 }

		
		-- 1.3.6.1.4.1.32285.11.2.3.4.7.1
		topOnuAutoUpgProfileTable OBJECT-TYPE
			SYNTAX SEQUENCE OF TopOnuAutoUpgProfileEntry
			MAX-ACCESS not-accessible
			STATUS current
			DESCRIPTION
				"ONU atuo upgrade profile table"
			::= { topOnuAutoUpgardeMgmtObjects 1 }

		
		-- 1.3.6.1.4.1.32285.11.2.3.4.7.1.1
		topOnuAutoUpgProfileEntry OBJECT-TYPE
			SYNTAX TopOnuAutoUpgProfileEntry
			MAX-ACCESS not-accessible
			STATUS current
			DESCRIPTION
				"ONU atuo upgrade profile entry"
			INDEX { topOnuAutoUpgProfileId }
			::= { topOnuAutoUpgProfileTable 1 }

		
		TopOnuAutoUpgProfileEntry ::=
			SEQUENCE { 
				topOnuAutoUpgProfileId
					INTEGER,
				topOnuAutoUpgProfileName
					OCTET STRING,
				topOnuAutoUpgProfileOnuType
					INTEGER,
				topOnuAutoUpgProfileHwVersion
					OCTET STRING,
				topOnuAutoUpgProfileMode
					INTEGER,
				topOnuAutoUpgProfileNewVersion
					OCTET STRING,
				topOnuAutoUpgProfileUpgTime
					DateAndTime,
				topOnuAutoUpgProfileFile1
					OCTET STRING,
				topOnuAutoUpgProfileFile2
					OCTET STRING,
				topOnuAutoUpgProfileFile3
					OCTET STRING,
				topOnuAutoUpgProfileFile4
					OCTET STRING,
				topOnuAutoUpgProfileFile5
					OCTET STRING,
				topOnuAutoUpgProfilePri
					INTEGER,
				topOnuAutoUpgProfileBindStatus
					INTEGER,
				topOnuAutoUpgProfileRowStatus
					RowStatus
			 }

		-- 1.3.6.1.4.1.32285.11.2.3.4.7.1.1.1
		topOnuAutoUpgProfileId OBJECT-TYPE
			SYNTAX INTEGER (1..20)
			MAX-ACCESS not-accessible
			STATUS current
			DESCRIPTION
				"The profile ID."
			::= { topOnuAutoUpgProfileEntry 1 }

		
		-- 1.3.6.1.4.1.32285.11.2.3.4.7.1.1.2
		topOnuAutoUpgProfileName OBJECT-TYPE
			SYNTAX OCTET STRING (SIZE (1..31))
			MAX-ACCESS read-write
			STATUS current
			DESCRIPTION
				"The profile name."
			::= { topOnuAutoUpgProfileEntry 2 }

		
		-- 1.3.6.1.4.1.32285.11.2.3.4.7.1.1.3
		topOnuAutoUpgProfileOnuType OBJECT-TYPE
			SYNTAX INTEGER
			MAX-ACCESS read-write
			STATUS current
			DESCRIPTION
				"Onu product name,Set the product like this:
					ANY		: 0  (0x00)
				 	PN8621: 33 (0x21)
				 	PN8622: 34 (0x22)
				 	PN8623: 35 (0x23)
				 	PN8624: 36 (0x24)
				 	PN8625: 37 (0x25)"
			::= { topOnuAutoUpgProfileEntry 3 }

		
		-- 1.3.6.1.4.1.32285.11.2.3.4.7.1.1.4
		topOnuAutoUpgProfileHwVersion OBJECT-TYPE
			SYNTAX OCTET STRING (SIZE (0..8))
			MAX-ACCESS read-write
			STATUS current
			DESCRIPTION
				"Hardware version, if do not need hardware version, please set NULL(empty string)"
			::= { topOnuAutoUpgProfileEntry 4 }

		
		-- 1.3.6.1.4.1.32285.11.2.3.4.7.1.1.5
		topOnuAutoUpgProfileMode OBJECT-TYPE
			SYNTAX INTEGER
				{
				tk(1),
				pmc(2),
				ctc(4),
				baseline(16),
				extend(32),
				an(64) 
				}
			MAX-ACCESS read-write
			STATUS current
			DESCRIPTION
				"default ctc."
			::= { topOnuAutoUpgProfileEntry 5 }

		
		-- 1.3.6.1.4.1.32285.11.2.3.4.7.1.1.6
		topOnuAutoUpgProfileNewVersion OBJECT-TYPE
			SYNTAX OCTET STRING (SIZE (1..31))
			MAX-ACCESS read-write
			STATUS current
			DESCRIPTION
				"New software version for onu in this profile."
			::= { topOnuAutoUpgProfileEntry 6 }

		
		-- 1.3.6.1.4.1.32285.11.2.3.4.7.1.1.7
		topOnuAutoUpgProfileUpgTime OBJECT-TYPE
			SYNTAX DateAndTime
			MAX-ACCESS read-write
			STATUS current
			DESCRIPTION
				"If you set this node, at that time, this profile will auto start.
                if Do not set, set NULL"
			::= { topOnuAutoUpgProfileEntry 7 }

		
		-- 1.3.6.1.4.1.32285.11.2.3.4.7.1.1.8
		topOnuAutoUpgProfileFile1 OBJECT-TYPE
			SYNTAX OCTET STRING (SIZE (0..127))
			MAX-ACCESS read-write
			STATUS current
			DESCRIPTION
				"Onu upgrade file name, support relative path and absolute path,
                if the head character of this string, will be treated as absolute path,
                or will be treated as relative path. Default directory of relative path is 
                '/tffs0/onuapp'"
			::= { topOnuAutoUpgProfileEntry 8 }

		
		-- 1.3.6.1.4.1.32285.11.2.3.4.7.1.1.9
		topOnuAutoUpgProfileFile2 OBJECT-TYPE
			SYNTAX OCTET STRING (SIZE (0..127))
			MAX-ACCESS read-write
			STATUS current
			DESCRIPTION
				"The second upgrade file."
			::= { topOnuAutoUpgProfileEntry 9 }

		
		-- 1.3.6.1.4.1.32285.11.2.3.4.7.1.1.10
		topOnuAutoUpgProfileFile3 OBJECT-TYPE
			SYNTAX OCTET STRING (SIZE (0..127))
			MAX-ACCESS read-write
			STATUS current
			DESCRIPTION
				"The third upgrade file."
			::= { topOnuAutoUpgProfileEntry 10 }

		
		-- 1.3.6.1.4.1.32285.11.2.3.4.7.1.1.11
		topOnuAutoUpgProfileFile4 OBJECT-TYPE
			SYNTAX OCTET STRING (SIZE (0..127))
			MAX-ACCESS read-write
			STATUS current
			DESCRIPTION
				"The fourth upgrade file."
			::= { topOnuAutoUpgProfileEntry 11 }

		
		-- 1.3.6.1.4.1.32285.11.2.3.4.7.1.1.12
		topOnuAutoUpgProfileFile5 OBJECT-TYPE
			SYNTAX OCTET STRING (SIZE (0..127))
			MAX-ACCESS read-write
			STATUS current
			DESCRIPTION
				"The fifth upgrade file."
			::= { topOnuAutoUpgProfileEntry 12 }

		
		-- 1.3.6.1.4.1.32285.11.2.3.4.7.1.1.13
		topOnuAutoUpgProfilePri OBJECT-TYPE
			SYNTAX INTEGER (0..15)
			MAX-ACCESS read-write
			STATUS current
			DESCRIPTION
				"Profile priority, Use for profile match ONU."
			::= { topOnuAutoUpgProfileEntry 13 }

		
		-- 1.3.6.1.4.1.32285.11.2.3.4.7.1.1.14
		topOnuAutoUpgProfileBindStatus OBJECT-TYPE
			SYNTAX INTEGER
				{
				no-bind(0),
				bind(1)
				}
			MAX-ACCESS read-only
			STATUS current
			DESCRIPTION
				"This profile bind status, If this profile has already bind to pon,
                It will return bind(1)."
			::= { topOnuAutoUpgProfileEntry 14 }

		
		-- 1.3.6.1.4.1.32285.11.2.3.4.7.1.1.15
		topOnuAutoUpgProfileRowStatus OBJECT-TYPE
			SYNTAX RowStatus
			MAX-ACCESS read-create
			STATUS current
			DESCRIPTION
				"add/del/set"
			::= { topOnuAutoUpgProfileEntry 15 }

		
		-- 1.3.6.1.4.1.32285.11.2.3.4.7.2
		topOnuAutoUpgInstallTable OBJECT-TYPE
			SYNTAX SEQUENCE OF TopOnuAutoUpgInstallEntry
			MAX-ACCESS not-accessible
			STATUS current
			DESCRIPTION
				"Onu auto upgrade install to pon port table."
			::= { topOnuAutoUpgardeMgmtObjects 2 }

		
		-- 1.3.6.1.4.1.32285.11.2.3.4.7.2.1
		topOnuAutoUpgInstallEntry OBJECT-TYPE
			SYNTAX TopOnuAutoUpgInstallEntry
			MAX-ACCESS not-accessible
			STATUS current
			DESCRIPTION
				"Onu auto upgrade install to pon port table entry."
			INDEX { topOnuAutoUpgInstallSlotId, topOnuAutoUpgInstallPonId, topOnuAutoUpgInstallOnuId, topOnuAutoUpgInstallProfile }
			::= { topOnuAutoUpgInstallTable 1 }

		
		TopOnuAutoUpgInstallEntry ::=
			SEQUENCE { 
				topOnuAutoUpgInstallSlotId
					TopEPonSlotIndex,
				topOnuAutoUpgInstallPonId
					TopEPonPonIndex,
				topOnuAutoUpgInstallOnuId
					TopEPonOnuAuthNum,
				topOnuAutoUpgInstallProfile
					INTEGER,
				topOnuAutoUpgInstallStatus
					INTEGER,
				topOnuAutoUpgInstallAction
					INTEGER,
				topOnuAutoUpgInstallRowStatus
					RowStatus
			 }

		-- 1.3.6.1.4.1.32285.11.2.3.4.7.2.1.1
		topOnuAutoUpgInstallSlotId OBJECT-TYPE
			SYNTAX TopEPonSlotIndex
			MAX-ACCESS not-accessible
			STATUS current
			DESCRIPTION
				"Epon slot id."
			::= { topOnuAutoUpgInstallEntry 1 }

		
		-- 1.3.6.1.4.1.32285.11.2.3.4.7.2.1.2
		topOnuAutoUpgInstallPonId OBJECT-TYPE
			SYNTAX TopEPonPonIndex
			MAX-ACCESS not-accessible
			STATUS current
			DESCRIPTION
				"Epon pon id."
			::= { topOnuAutoUpgInstallEntry 2 }

		
		-- 1.3.6.1.4.1.32285.11.2.3.4.7.2.1.3
		topOnuAutoUpgInstallOnuId OBJECT-TYPE
			SYNTAX TopEPonOnuAuthNum
			MAX-ACCESS not-accessible
			STATUS current
			DESCRIPTION
				"Onu id."
			::= { topOnuAutoUpgInstallEntry 3 }

		
		-- 1.3.6.1.4.1.32285.11.2.3.4.7.2.1.4
		topOnuAutoUpgInstallProfile OBJECT-TYPE
			SYNTAX INTEGER (1..20)
			MAX-ACCESS not-accessible
			STATUS current
			DESCRIPTION
				"Profile id."
			::= { topOnuAutoUpgInstallEntry 4 }

		
		-- 1.3.6.1.4.1.32285.11.2.3.4.7.2.1.5
		topOnuAutoUpgInstallStatus OBJECT-TYPE
			SYNTAX INTEGER
				{
				idle(0),
				upgrading(1)
				}
			MAX-ACCESS read-only
			STATUS current
			DESCRIPTION
				"If the profile is using to upgrade, will return upgrading(1), 
                or return 0."
			::= { topOnuAutoUpgInstallEntry 5 }

		
		-- 1.3.6.1.4.1.32285.11.2.3.4.7.2.1.6
		topOnuAutoUpgInstallAction OBJECT-TYPE
			SYNTAX INTEGER
				{
				invalid(0),
				restart(1)
				}
			MAX-ACCESS read-write
			STATUS current
			DESCRIPTION
				"Restart onu auto upgrade, If Restart upgrade in whole OLT, slot should setted 0,
                If Restart upgrade in whole pon slot, pon should be setted 0."
			::= { topOnuAutoUpgInstallEntry 6 }

		
		-- 1.3.6.1.4.1.32285.11.2.3.4.7.2.1.7
		topOnuAutoUpgInstallRowStatus OBJECT-TYPE
			SYNTAX RowStatus
			MAX-ACCESS read-create
			STATUS current
			DESCRIPTION
				"add/del/set."
			::= { topOnuAutoUpgInstallEntry 7 }

		
		-- 1.3.6.1.4.1.32285.11.2.3.4.7.3
		topOnuAutoUpgRecordTable OBJECT-TYPE
			SYNTAX SEQUENCE OF TopOnuAutoUpgRecordEntry
			MAX-ACCESS not-accessible
			STATUS current
			DESCRIPTION
				"ONU auto upgrade record table, upgrading record will be stay in this table."
			::= { topOnuAutoUpgardeMgmtObjects 3 }

		
		-- 1.3.6.1.4.1.32285.11.2.3.4.7.3.1
		topOnuAutoUpgRecordEntry OBJECT-TYPE
			SYNTAX TopOnuAutoUpgRecordEntry
			MAX-ACCESS not-accessible
			STATUS current
			DESCRIPTION
				"ONU auto upgrade record table entry."
			INDEX { topOnuAutoUpgRecordSlotId, topOnuAutoUpgRecordIndex }
			::= { topOnuAutoUpgRecordTable 1 }

		
		TopOnuAutoUpgRecordEntry ::=
			SEQUENCE { 
				topOnuAutoUpgRecordSlotId
					TopEPonSlotIndex,
				topOnuAutoUpgRecordIndex
					INTEGER,
				topOnuAutoUpgRecordProfileId
					INTEGER,
				topOnuAutoUpgRecordStartTime
					DateAndTime,
				topOnuAutoUpgRecordAction
					INTEGER,
				topOnuAutoUpgRecordOnuStatus
					OCTET STRING
			 }

		-- 1.3.6.1.4.1.32285.11.2.3.4.7.3.1.1
		topOnuAutoUpgRecordSlotId OBJECT-TYPE
			SYNTAX TopEPonSlotIndex
			MAX-ACCESS not-accessible
			STATUS current
			DESCRIPTION
				"Slot id."
			::= { topOnuAutoUpgRecordEntry 1 }

		
		-- 1.3.6.1.4.1.32285.11.2.3.4.7.3.1.2
		topOnuAutoUpgRecordIndex OBJECT-TYPE
			SYNTAX INTEGER
			MAX-ACCESS not-accessible
			STATUS current
			DESCRIPTION
				"Upgrade record index."
			::= { topOnuAutoUpgRecordEntry 2 }

		
		-- 1.3.6.1.4.1.32285.11.2.3.4.7.3.1.3
		topOnuAutoUpgRecordProfileId OBJECT-TYPE
			SYNTAX INTEGER (1..20)
			MAX-ACCESS read-only
			STATUS current
			DESCRIPTION
				"Profile id which is being used."
			::= { topOnuAutoUpgRecordEntry 3 }

		
		-- 1.3.6.1.4.1.32285.11.2.3.4.7.3.1.4
		topOnuAutoUpgRecordStartTime OBJECT-TYPE
			SYNTAX DateAndTime
			MAX-ACCESS read-only
			STATUS current
			DESCRIPTION
				"This upgard start time."
			::= { topOnuAutoUpgRecordEntry 4 }

		
		-- 1.3.6.1.4.1.32285.11.2.3.4.7.3.1.5
		topOnuAutoUpgRecordAction OBJECT-TYPE
			SYNTAX INTEGER
				{
				invalide(0),
				cancel(1)
				}
			MAX-ACCESS read-write
			STATUS current
			DESCRIPTION
				"When upgrading, you can cancel the task."
			::= { topOnuAutoUpgRecordEntry 5 }

		
		-- 1.3.6.1.4.1.32285.11.2.3.4.7.3.1.6
		topOnuAutoUpgRecordOnuStatus OBJECT-TYPE
			SYNTAX OCTET STRING (SIZE (2048))
			MAX-ACCESS read-only
			STATUS current
			DESCRIPTION
				"onu upgrade status"
			::= { topOnuAutoUpgRecordEntry 6 }

		
		-- 1.3.6.1.4.1.32285.11.2.3.4.8
		topOnuModifyTable OBJECT-TYPE
			SYNTAX SEQUENCE OF TopOnuModifyEntry
			MAX-ACCESS not-accessible
			STATUS current
			DESCRIPTION
				"ONU replace table"
			::= { topOnuObjects 8 }

		
		-- 1.3.6.1.4.1.32285.11.2.3.4.8.1
		topOnuModifyEntry OBJECT-TYPE
			SYNTAX TopOnuModifyEntry
			MAX-ACCESS not-accessible
			STATUS current
			DESCRIPTION
				"ONU replace entry.
				supported mode:MAC only, sn only, password only,sn+password,
				other mode will not be supported at present."
			INDEX { topOnuModifyCardIndex, topOnuModifyPonIndex, topOnuModifyOnuIndex }
			::= { topOnuModifyTable 1 }

		
		TopOnuModifyEntry ::=
			SEQUENCE { 
				topOnuModifyCardIndex
					TopEPonSlotIndex,
				topOnuModifyPonIndex
					TopEPonPonIndex,
				topOnuModifyOnuIndex
					TopEPonOnuAuthNum,
				topOnuModifyMacAddress
					MacAddress,
				topOnuModifyLogicSn
					OCTET STRING,
				topOnuModifyPwd
					OCTET STRING
			 }

		-- 1.3.6.1.4.1.32285.11.2.3.4.8.1.1
		topOnuModifyCardIndex OBJECT-TYPE
			SYNTAX TopEPonSlotIndex
			MAX-ACCESS not-accessible
			STATUS current
			DESCRIPTION
				"onu slot Index"
			::= { topOnuModifyEntry 1 }

		
		-- 1.3.6.1.4.1.32285.11.2.3.4.8.1.2
		topOnuModifyPonIndex OBJECT-TYPE
			SYNTAX TopEPonPonIndex
			MAX-ACCESS not-accessible
			STATUS current
			DESCRIPTION
				"onu pon Index"
			::= { topOnuModifyEntry 2 }

		
		-- 1.3.6.1.4.1.32285.11.2.3.4.8.1.3
		topOnuModifyOnuIndex OBJECT-TYPE
			SYNTAX TopEPonOnuAuthNum
			MAX-ACCESS not-accessible
			STATUS current
			DESCRIPTION
				"onu auth Index"
			::= { topOnuModifyEntry 3 }

		
		-- 1.3.6.1.4.1.32285.11.2.3.4.8.1.4
		topOnuModifyMacAddress OBJECT-TYPE
			SYNTAX MacAddress
			MAX-ACCESS read-write
			STATUS current
			DESCRIPTION
				"Mac Address.
				Filling six bytes with 0x00, means invalid this member."
			::= { topOnuModifyEntry 4 }

		
		-- 1.3.6.1.4.1.32285.11.2.3.4.8.1.5
		topOnuModifyLogicSn OBJECT-TYPE
			SYNTAX OCTET STRING (SIZE (0..24))
			MAX-ACCESS read-write
			STATUS current
			DESCRIPTION
				"logic sn."
			::= { topOnuModifyEntry 5 }

		
		-- 1.3.6.1.4.1.32285.11.2.3.4.8.1.6
		topOnuModifyPwd OBJECT-TYPE
			SYNTAX OCTET STRING (SIZE (0..12))
			MAX-ACCESS read-write
			STATUS current
			DESCRIPTION
				"password"
			::= { topOnuModifyEntry 6 }

		
		-- 1.3.6.1.4.1.32285.11.2.3.4.9
		topOnuMacMgmtObjects OBJECT IDENTIFIER ::= { topOnuObjects 9 }
		-- 1.3.6.1.4.1.32285.11.2.3.4.9.1
		topOnuMacMgmtTable OBJECT-TYPE
			SYNTAX SEQUENCE OF TopOnuMacMgmtEntry
			MAX-ACCESS not-accessible
			STATUS current
			DESCRIPTION
				"Description."
			::= { topOnuMacMgmtObjects 1 }

		
		-- 1.3.6.1.4.1.32285.11.2.3.4.9.1.1
		topOnuMacMgmtEntry OBJECT-TYPE
			SYNTAX TopOnuMacMgmtEntry
			MAX-ACCESS not-accessible
			STATUS current
			DESCRIPTION
				"Description."
			INDEX { topOnuMacMgmtInstIndex }
			::= { topOnuMacMgmtTable 1 }

		
		TopOnuMacMgmtEntry ::=
			SEQUENCE { 
				topOnuMacMgmtInstIndex
					INTEGER,
				topOnuMacList
					OCTET STRING,
				topOnuMacMark
					INTEGER,
				topOnuMacRowStatus
					RowStatus
			 }

		-- 1.3.6.1.4.1.32285.11.2.3.4.9.1.1.1
		topOnuMacMgmtInstIndex OBJECT-TYPE
			SYNTAX INTEGER
			MAX-ACCESS not-accessible
			STATUS current
			DESCRIPTION
				"Onu index . The highest byte is the slot number, the second byte is the pon port, 
				the third byte is the onu number, the last byte is just reserved."
			::= { topOnuMacMgmtEntry 1 }

		
		-- 1.3.6.1.4.1.32285.11.2.3.4.9.1.1.2
		topOnuMacList OBJECT-TYPE
			SYNTAX OCTET STRING (SIZE (0..384))
			MAX-ACCESS read-write
			STATUS current
			DESCRIPTION
				"List of onu mac. a mac needs 6 bytes. 
				The max number of mac is 64, so the max length of macList is 384.
				The length of macList if from 0 to 384, when is as 0, means to clear all macList."
			::= { topOnuMacMgmtEntry 2 }

		
		-- 1.3.6.1.4.1.32285.11.2.3.4.9.1.1.3
		topOnuMacMark OBJECT-TYPE
			SYNTAX INTEGER
				{
				filter(1),
				bind(2)
				}
			MAX-ACCESS read-write
			STATUS current
			DESCRIPTION
				"Onu mac mark attribute.
				When unset, you can read an invalid value of 0."
			::= { topOnuMacMgmtEntry 3 }
		-- 1.3.6.1.4.1.32285.11.2.3.4.9.1.1.4
		topOnuMacRowStatus OBJECT-TYPE
			SYNTAX RowStatus
			MAX-ACCESS read-create
			STATUS current
			DESCRIPTION
				"create/delete/set"
			::= { topOnuMacMgmtEntry 4 }

		
		-- 1.3.6.1.4.1.32285.11.2.3.4.10
		topOnuComObject OBJECT IDENTIFIER ::= { topOnuObjects 10 }

		
		-- 1.3.6.1.4.1.32285.11.2.3.4.10.1
		topOnuComParamObject OBJECT IDENTIFIER ::= { topOnuComObject 1 }

		
		-- 1.3.6.1.4.1.32285.11.2.3.4.10.1.1
		topOnuComVlan OBJECT-TYPE
			SYNTAX INTEGER
			MAX-ACCESS read-write
			STATUS current
			DESCRIPTION
				"Description."
			::= { topOnuComParamObject 1 }

		
		-- 1.3.6.1.4.1.32285.11.2.3.4.10.2
		topOnuComInfoTable OBJECT-TYPE
			SYNTAX SEQUENCE OF TopOnuComInfoEntry
			MAX-ACCESS not-accessible
			STATUS current
			DESCRIPTION
				"Description."
			::= { topOnuComObject 2 }

		
		-- 1.3.6.1.4.1.32285.11.2.3.4.10.2.1
		topOnuComInfoEntry OBJECT-TYPE
			SYNTAX TopOnuComInfoEntry
			MAX-ACCESS not-accessible
			STATUS current
			DESCRIPTION
				"Description."
			INDEX { topOnuComInfoCardIndex, topOnuComInfoPonIndex, topOnuComInfoOnuIndex, topOnuComInfoComIndex }
			::= { topOnuComInfoTable 1 }

		
		TopOnuComInfoEntry ::=
			SEQUENCE { 
				topOnuComInfoCardIndex
					INTEGER,
				topOnuComInfoPonIndex
					INTEGER,
				topOnuComInfoOnuIndex
					INTEGER,
				topOnuComInfoComIndex
					INTEGER,
				topOnuComInfoComDesc
					OCTET STRING,
				topOnuComInfoComType
					INTEGER,
				topOnuComInfoBuad
					INTEGER,
				topOnuComInfoDataBits
					INTEGER,
				topOnuComInfoStartBits
					INTEGER,
				topOnuComInfoStopBits
					INTEGER,
				topOnuComInfoParityType
					INTEGER,
				topOnuComInfoMainRemoteIp
					IpAddress,
				topOnuComInfoMainRemotePort
					INTEGER,
				topOnuComInfoBackRemoteIp
					IpAddress,
				topOnuComInfoBackRemotePort
					INTEGER,
				topOnuComInfoSrvType
					INTEGER,
				topOnuComInfoSrvPort
					INTEGER,
				topOnuComInfoClientNum
					INTEGER
			 }

		-- 1.3.6.1.4.1.32285.11.2.3.4.10.2.1.1
		topOnuComInfoCardIndex OBJECT-TYPE
			SYNTAX INTEGER
			MAX-ACCESS not-accessible
			STATUS current
			DESCRIPTION
				"Description."
			::= { topOnuComInfoEntry 1 }

		
		-- 1.3.6.1.4.1.32285.11.2.3.4.10.2.1.2
		topOnuComInfoPonIndex OBJECT-TYPE
			SYNTAX INTEGER
			MAX-ACCESS not-accessible
			STATUS current
			DESCRIPTION
				"Description."
			::= { topOnuComInfoEntry 2 }

		
		-- 1.3.6.1.4.1.32285.11.2.3.4.10.2.1.3
		topOnuComInfoOnuIndex OBJECT-TYPE
			SYNTAX INTEGER
			MAX-ACCESS not-accessible
			STATUS current
			DESCRIPTION
				"Description."
			::= { topOnuComInfoEntry 3 }

		
		-- 1.3.6.1.4.1.32285.11.2.3.4.10.2.1.4
		topOnuComInfoComIndex OBJECT-TYPE
			SYNTAX INTEGER
			MAX-ACCESS not-accessible
			STATUS current
			DESCRIPTION
				"Description."
			::= { topOnuComInfoEntry 4 }

		
		-- 1.3.6.1.4.1.32285.11.2.3.4.10.2.1.5
		topOnuComInfoComDesc OBJECT-TYPE
			SYNTAX OCTET STRING (SIZE (0..63))
			MAX-ACCESS read-write
			STATUS current
			DESCRIPTION
				"Description."
			::= { topOnuComInfoEntry 5 }

		
		-- 1.3.6.1.4.1.32285.11.2.3.4.10.2.1.6
		topOnuComInfoComType OBJECT-TYPE
			SYNTAX INTEGER
				{
				rs-232(1),
				rs-485(2)
				}
			MAX-ACCESS read-write
			STATUS current
			DESCRIPTION
				"Description."
			::= { topOnuComInfoEntry 6 }

		
		-- 1.3.6.1.4.1.32285.11.2.3.4.10.2.1.7
		topOnuComInfoBuad OBJECT-TYPE
			SYNTAX INTEGER
				{
				b110(1),
				b300(2),
				b600(3),
				b1200(4),
				b2400(5),
				b4800(6),
				b9600(7),
				b14400(8),
				b19200(9),
				b38400(10),
				b57600(11),
				b115200(12)
				}
			MAX-ACCESS read-write
			STATUS current
			DESCRIPTION
				"Description."
			::= { topOnuComInfoEntry 7 }

		
		-- 1.3.6.1.4.1.32285.11.2.3.4.10.2.1.8
		topOnuComInfoDataBits OBJECT-TYPE
			SYNTAX INTEGER
			MAX-ACCESS read-write
			STATUS current
			DESCRIPTION
				"Description."
			::= { topOnuComInfoEntry 8 }

		
		-- 1.3.6.1.4.1.32285.11.2.3.4.10.2.1.9
		topOnuComInfoStartBits OBJECT-TYPE
			SYNTAX INTEGER
			MAX-ACCESS read-write
			STATUS current
			DESCRIPTION
				"Description."
			::= { topOnuComInfoEntry 9 }

		
		-- 1.3.6.1.4.1.32285.11.2.3.4.10.2.1.10
		topOnuComInfoStopBits OBJECT-TYPE
			SYNTAX INTEGER
			MAX-ACCESS read-write
			STATUS current
			DESCRIPTION
				"Description."
			::= { topOnuComInfoEntry 10 }

		
		-- 1.3.6.1.4.1.32285.11.2.3.4.10.2.1.11
		topOnuComInfoParityType OBJECT-TYPE
			SYNTAX INTEGER
				{
				none(1),
				even(2),
				odd(3),
				space(4),
				mark(5)
				}
			MAX-ACCESS read-write
			STATUS current
			DESCRIPTION
				"Description."
			::= { topOnuComInfoEntry 11 }

		
		-- 1.3.6.1.4.1.32285.11.2.3.4.10.2.1.12
		topOnuComInfoMainRemoteIp OBJECT-TYPE
			SYNTAX IpAddress
			MAX-ACCESS read-write
			STATUS current
			DESCRIPTION
				"Description."
			::= { topOnuComInfoEntry 12 }

		
		-- 1.3.6.1.4.1.32285.11.2.3.4.10.2.1.13
		topOnuComInfoMainRemotePort OBJECT-TYPE
			SYNTAX INTEGER (1025..65535)
			MAX-ACCESS read-write
			STATUS current
			DESCRIPTION
				"Description."
			::= { topOnuComInfoEntry 13 }

		
		-- 1.3.6.1.4.1.32285.11.2.3.4.10.2.1.14
		topOnuComInfoBackRemoteIp OBJECT-TYPE
			SYNTAX IpAddress
			MAX-ACCESS read-write
			STATUS current
			DESCRIPTION
				"Description."
			::= { topOnuComInfoEntry 14 }

		
		-- 1.3.6.1.4.1.32285.11.2.3.4.10.2.1.15
		topOnuComInfoBackRemotePort OBJECT-TYPE
			SYNTAX INTEGER (1025..65535)
			MAX-ACCESS read-write
			STATUS current
			DESCRIPTION
				"Description."
			::= { topOnuComInfoEntry 15 }

		
		-- 1.3.6.1.4.1.32285.11.2.3.4.10.2.1.16
		topOnuComInfoSrvType OBJECT-TYPE
			SYNTAX INTEGER
				{
				none(0),
				tcp-server(1),
				tcp-client(2),
				udp(3)
				}
			MAX-ACCESS read-write
			STATUS current
			DESCRIPTION
				"Description."
			::= { topOnuComInfoEntry 16 }

		
		-- 1.3.6.1.4.1.32285.11.2.3.4.10.2.1.17
		topOnuComInfoSrvPort OBJECT-TYPE
			SYNTAX INTEGER (1025..65535)
			MAX-ACCESS read-write
			STATUS current
			DESCRIPTION
				"Description."
			::= { topOnuComInfoEntry 17 }

		
		-- 1.3.6.1.4.1.32285.11.2.3.4.10.2.1.18
		topOnuComInfoClientNum OBJECT-TYPE
			SYNTAX INTEGER (0..10)
			MAX-ACCESS read-write
			STATUS current
			DESCRIPTION
				"Description."
			::= { topOnuComInfoEntry 18 }

		
		-- 1.3.6.1.4.1.32285.11.2.3.4.10.3
		topOnuComStatisticTable OBJECT-TYPE
			SYNTAX SEQUENCE OF TopOnuComStatisticEntry
			MAX-ACCESS not-accessible
			STATUS current
			DESCRIPTION
				"Description."
			::= { topOnuComObject 3 }

		
		-- 1.3.6.1.4.1.32285.11.2.3.4.10.3.1
		topOnuComStatisticEntry OBJECT-TYPE
			SYNTAX TopOnuComStatisticEntry
			MAX-ACCESS not-accessible
			STATUS current
			DESCRIPTION
				"Description."
			INDEX { topOnuComStatisCardIdx, topOnuComStatisPonIdx, topOnuComStatisOnuIdx, topOnuComStatisComIdx }
			::= { topOnuComStatisticTable 1 }

		
		TopOnuComStatisticEntry ::=
			SEQUENCE { 
				topOnuComStatisCardIdx
					INTEGER,
				topOnuComStatisPonIdx
					INTEGER,
				topOnuComStatisOnuIdx
					INTEGER,
				topOnuComStatisComIdx
					INTEGER,
				topOnuComStatisCts
					Counter64,
				topOnuComStatisDsr
					Counter64,
				topOnuComStatisRng
					Counter64,
				topOnuComStatisDcd
					Counter64,
				topOnuComStatisRxBytes
					Counter64,
				topOnuComStatisTxBytes
					Counter64,
				topOnuComStatisFrames
					Counter64,
				topOnuComStatisOverRun
					Counter64,
				topOnuComStatisParityErr
					Counter64,
				topOnuComStatisBrk
					Counter64,
				topOnuComStatisBufOverRun
					Counter64,
				topOnuComStatisRxDrops
					Counter64,
				topOnuComStatisTxDrops
					Counter64,
				topOnuComStatisRecvFromNet
					Counter64,
				topOnuComStatisSendToNet
					Counter64,
				topOnuComStatisClear
					INTEGER
			 }

		-- 1.3.6.1.4.1.32285.11.2.3.4.10.3.1.1
		topOnuComStatisCardIdx OBJECT-TYPE
			SYNTAX INTEGER
			MAX-ACCESS not-accessible
			STATUS current
			DESCRIPTION
				"Description."
			::= { topOnuComStatisticEntry 1 }

		
		-- 1.3.6.1.4.1.32285.11.2.3.4.10.3.1.2
		topOnuComStatisPonIdx OBJECT-TYPE
			SYNTAX INTEGER
			MAX-ACCESS not-accessible
			STATUS current
			DESCRIPTION
				"Description."
			::= { topOnuComStatisticEntry 2 }

		
		-- 1.3.6.1.4.1.32285.11.2.3.4.10.3.1.3
		topOnuComStatisOnuIdx OBJECT-TYPE
			SYNTAX INTEGER
			MAX-ACCESS not-accessible
			STATUS current
			DESCRIPTION
				"Description."
			::= { topOnuComStatisticEntry 3 }

		
		-- 1.3.6.1.4.1.32285.11.2.3.4.10.3.1.4
		topOnuComStatisComIdx OBJECT-TYPE
			SYNTAX INTEGER
			MAX-ACCESS not-accessible
			STATUS current
			DESCRIPTION
				"Description."
			::= { topOnuComStatisticEntry 4 }

		
		-- 1.3.6.1.4.1.32285.11.2.3.4.10.3.1.5
		topOnuComStatisCts OBJECT-TYPE
			SYNTAX Counter64
			MAX-ACCESS read-only
			STATUS current
			DESCRIPTION
				"Description."
			::= { topOnuComStatisticEntry 5 }

		
		-- 1.3.6.1.4.1.32285.11.2.3.4.10.3.1.6
		topOnuComStatisDsr OBJECT-TYPE
			SYNTAX Counter64
			MAX-ACCESS read-only
			STATUS current
			DESCRIPTION
				"Description."
			::= { topOnuComStatisticEntry 6 }

		
		-- 1.3.6.1.4.1.32285.11.2.3.4.10.3.1.7
		topOnuComStatisRng OBJECT-TYPE
			SYNTAX Counter64
			MAX-ACCESS read-only
			STATUS current
			DESCRIPTION
				"Description."
			::= { topOnuComStatisticEntry 7 }

		
		-- 1.3.6.1.4.1.32285.11.2.3.4.10.3.1.8
		topOnuComStatisDcd OBJECT-TYPE
			SYNTAX Counter64
			MAX-ACCESS read-only
			STATUS current
			DESCRIPTION
				"Description."
			::= { topOnuComStatisticEntry 8 }

		
		-- 1.3.6.1.4.1.32285.11.2.3.4.10.3.1.9
		topOnuComStatisRxBytes OBJECT-TYPE
			SYNTAX Counter64
			MAX-ACCESS read-only
			STATUS current
			DESCRIPTION
				"Description."
			::= { topOnuComStatisticEntry 9 }

		
		-- 1.3.6.1.4.1.32285.11.2.3.4.10.3.1.10
		topOnuComStatisTxBytes OBJECT-TYPE
			SYNTAX Counter64
			MAX-ACCESS read-only
			STATUS current
			DESCRIPTION
				"Description."
			::= { topOnuComStatisticEntry 10 }

		
		-- 1.3.6.1.4.1.32285.11.2.3.4.10.3.1.11
		topOnuComStatisFrames OBJECT-TYPE
			SYNTAX Counter64
			MAX-ACCESS read-only
			STATUS current
			DESCRIPTION
				"Description."
			::= { topOnuComStatisticEntry 11 }

		
		-- 1.3.6.1.4.1.32285.11.2.3.4.10.3.1.12
		topOnuComStatisOverRun OBJECT-TYPE
			SYNTAX Counter64
			MAX-ACCESS read-only
			STATUS current
			DESCRIPTION
				"Description."
			::= { topOnuComStatisticEntry 12 }

		
		-- 1.3.6.1.4.1.32285.11.2.3.4.10.3.1.13
		topOnuComStatisParityErr OBJECT-TYPE
			SYNTAX Counter64
			MAX-ACCESS read-only
			STATUS current
			DESCRIPTION
				"Description."
			::= { topOnuComStatisticEntry 13 }

		
		-- 1.3.6.1.4.1.32285.11.2.3.4.10.3.1.14
		topOnuComStatisBrk OBJECT-TYPE
			SYNTAX Counter64
			MAX-ACCESS read-only
			STATUS current
			DESCRIPTION
				"Description."
			::= { topOnuComStatisticEntry 14 }

		
		-- 1.3.6.1.4.1.32285.11.2.3.4.10.3.1.15
		topOnuComStatisBufOverRun OBJECT-TYPE
			SYNTAX Counter64
			MAX-ACCESS read-only
			STATUS current
			DESCRIPTION
				"Description."
			::= { topOnuComStatisticEntry 15 }

		
		-- 1.3.6.1.4.1.32285.11.2.3.4.10.3.1.16
		topOnuComStatisRxDrops OBJECT-TYPE
			SYNTAX Counter64
			MAX-ACCESS read-only
			STATUS current
			DESCRIPTION
				"Description."
			::= { topOnuComStatisticEntry 16 }

		
		-- 1.3.6.1.4.1.32285.11.2.3.4.10.3.1.17
		topOnuComStatisTxDrops OBJECT-TYPE
			SYNTAX Counter64
			MAX-ACCESS read-only
			STATUS current
			DESCRIPTION
				"Description."
			::= { topOnuComStatisticEntry 17 }

		
		-- 1.3.6.1.4.1.32285.11.2.3.4.10.3.1.18
		topOnuComStatisRecvFromNet OBJECT-TYPE
			SYNTAX Counter64
			MAX-ACCESS read-only
			STATUS current
			DESCRIPTION
				"Description."
			::= { topOnuComStatisticEntry 18 }

		
		-- 1.3.6.1.4.1.32285.11.2.3.4.10.3.1.19
		topOnuComStatisSendToNet OBJECT-TYPE
			SYNTAX Counter64
			MAX-ACCESS read-only
			STATUS current
			DESCRIPTION
				"Description."
			::= { topOnuComStatisticEntry 19 }

		
		-- 1.3.6.1.4.1.32285.11.2.3.4.10.3.1.20
		topOnuComStatisClear OBJECT-TYPE
			SYNTAX INTEGER { clear(1) }
			MAX-ACCESS read-write
			STATUS current
			DESCRIPTION
				"Description."
			::= { topOnuComStatisticEntry 20 }

		
		-- 1.3.6.1.4.1.32285.11.2.3.4.11
		topOnuManageParameterObject OBJECT IDENTIFIER ::= { topOnuObjects 11 }

		
		-- 1.3.6.1.4.1.32285.11.2.3.4.11.1
		topOnuGlobalParameterTable OBJECT-TYPE
			SYNTAX SEQUENCE OF TopOnuGlobalParameterEntry
			MAX-ACCESS not-accessible
			STATUS current
			DESCRIPTION
				"Onu manage parameter."
			::= { topOnuManageParameterObject 1 }

		
		-- 1.3.6.1.4.1.32285.11.2.3.4.11.1.1
		topOnuGlobalParameterEntry OBJECT-TYPE
			SYNTAX TopOnuGlobalParameterEntry
			MAX-ACCESS not-accessible
			STATUS current
			DESCRIPTION
				"Onu manage parameter."
			INDEX { topOnuGlobalParamCardIndex, topOnuGlobalParamPonIndex, topOnuGlobalParamOnuIndex }
			::= { topOnuGlobalParameterTable 1 }

		
		TopOnuGlobalParameterEntry ::=
			SEQUENCE { 
				topOnuGlobalParamCardIndex
					TopEPonSlotIndex,
				topOnuGlobalParamPonIndex
					TopEPonPonIndex,
				topOnuGlobalParamOnuIndex
					TopEPonOnuAuthNum,
				topOnuManageIpAddr
					IpAddress,
				topOnuManageIpMask
					IpAddress,
				topOnuManageGateWay
					IpAddress,
				topOnuManageCvlan
					INTEGER,
				topOnuManageSvlan
					INTEGER,
				topOnuManagePriority
					INTEGER,
				topOnuGlobalParamRowStatus
					RowStatus
			 }

		-- 1.3.6.1.4.1.32285.11.2.3.4.11.1.1.1
		topOnuGlobalParamCardIndex OBJECT-TYPE
			SYNTAX TopEPonSlotIndex
			MAX-ACCESS not-accessible
			STATUS current
			DESCRIPTION
				"Epon slot id."
			::= { topOnuGlobalParameterEntry 1 }

		
		-- 1.3.6.1.4.1.32285.11.2.3.4.11.1.1.2
		topOnuGlobalParamPonIndex OBJECT-TYPE
			SYNTAX TopEPonPonIndex
			MAX-ACCESS not-accessible
			STATUS current
			DESCRIPTION
				"Epon pon id."
			::= { topOnuGlobalParameterEntry 2 }

		
		-- 1.3.6.1.4.1.32285.11.2.3.4.11.1.1.3
		topOnuGlobalParamOnuIndex OBJECT-TYPE
			SYNTAX TopEPonOnuAuthNum
			MAX-ACCESS not-accessible
			STATUS current
			DESCRIPTION
				"Epon onu id."
			::= { topOnuGlobalParameterEntry 3 }

		
		-- 1.3.6.1.4.1.32285.11.2.3.4.11.1.1.4
		topOnuManageIpAddr OBJECT-TYPE
			SYNTAX IpAddress
			MAX-ACCESS read-write
			STATUS current
			DESCRIPTION
				"Ip address."
			::= { topOnuGlobalParameterEntry 4 }

		
		-- 1.3.6.1.4.1.32285.11.2.3.4.11.1.1.5
		topOnuManageIpMask OBJECT-TYPE
			SYNTAX IpAddress
			MAX-ACCESS read-write
			STATUS current
			DESCRIPTION
				"Ip mask."
			::= { topOnuGlobalParameterEntry 5 }

		
		-- 1.3.6.1.4.1.32285.11.2.3.4.11.1.1.6
		topOnuManageGateWay OBJECT-TYPE
			SYNTAX IpAddress
			MAX-ACCESS read-write
			STATUS current
			DESCRIPTION
				"Gateway."
			::= { topOnuGlobalParameterEntry 6 }

		
		-- 1.3.6.1.4.1.32285.11.2.3.4.11.1.1.7
		topOnuManageCvlan OBJECT-TYPE
			SYNTAX INTEGER (0..4094)
			MAX-ACCESS read-write
			STATUS current
			DESCRIPTION
				"Cvlan."
			::= { topOnuGlobalParameterEntry 7 }

		
		-- 1.3.6.1.4.1.32285.11.2.3.4.11.1.1.8
		topOnuManageSvlan OBJECT-TYPE
			SYNTAX INTEGER (0..4094)
			MAX-ACCESS read-write
			STATUS current
			DESCRIPTION
				"Svlan, 0--svlan does't exsit."
			::= { topOnuGlobalParameterEntry 8 }

		
		-- 1.3.6.1.4.1.32285.11.2.3.4.11.1.1.9
		topOnuManagePriority OBJECT-TYPE
			SYNTAX INTEGER (0..7)
			MAX-ACCESS read-write
			STATUS current
			DESCRIPTION
				"Priority."
			::= { topOnuGlobalParameterEntry 9 }

		
		-- 1.3.6.1.4.1.32285.11.2.3.4.11.1.1.10
		topOnuGlobalParamRowStatus OBJECT-TYPE
			SYNTAX RowStatus
			MAX-ACCESS read-create
			STATUS current
			DESCRIPTION
				"Row status."
			::= { topOnuGlobalParameterEntry 10 }

		
		-- 1.3.6.1.4.1.32285.11.2.3.4.11.2
		topOnuSnmpProfileTable OBJECT-TYPE
			SYNTAX SEQUENCE OF TopOnuSnmpProfileEntry
			MAX-ACCESS not-accessible
			STATUS current
			DESCRIPTION
				"Snmp profile table."
			::= { topOnuManageParameterObject 2 }

		
		-- 1.3.6.1.4.1.32285.11.2.3.4.11.2.1
		topOnuSnmpProfileEntry OBJECT-TYPE
			SYNTAX TopOnuSnmpProfileEntry
			MAX-ACCESS not-accessible
			STATUS current
			DESCRIPTION
				"Snmp profile entry."
			INDEX { topOnuSnmpProfileIdx }
			::= { topOnuSnmpProfileTable 1 }

		
		TopOnuSnmpProfileEntry ::=
			SEQUENCE { 
				topOnuSnmpProfileIdx
					INTEGER,
				topOnuSnmpProfileName
					OCTET STRING,
				topOnuSnmpVersion
					INTEGER,
				topOnuSnmpTrapHostIp
					IpAddress,
				topOnuSnmpTrapPort
					INTEGER,
				topOnuSnmpPort
					INTEGER,
				topOnuSnmpSecurityName
					OCTET STRING,
				topOnuSnmpReadCommunity
					OCTET STRING,
				topOnuSnmpWriteCommunity
					OCTET STRING,
				topSnmpProfileRefCount
					INTEGER,
				topSnmpProfileRowStatus
					RowStatus
			 }

		-- 1.3.6.1.4.1.32285.11.2.3.4.11.2.1.1
		topOnuSnmpProfileIdx OBJECT-TYPE
			SYNTAX INTEGER (1..64)
			MAX-ACCESS not-accessible
			STATUS current
			DESCRIPTION
				"Profile id."
			::= { topOnuSnmpProfileEntry 1 }

		
		-- 1.3.6.1.4.1.32285.11.2.3.4.11.2.1.2
		topOnuSnmpProfileName OBJECT-TYPE
			SYNTAX OCTET STRING (SIZE (1..31))
			MAX-ACCESS read-write
			STATUS current
			DESCRIPTION
				"Profile name."
			::= { topOnuSnmpProfileEntry 2 }

		
		-- 1.3.6.1.4.1.32285.11.2.3.4.11.2.1.3
		topOnuSnmpVersion OBJECT-TYPE
			SYNTAX INTEGER (1..2)
			MAX-ACCESS read-write
			STATUS current
			DESCRIPTION
				"Snmp version."
			::= { topOnuSnmpProfileEntry 3 }

		
		-- 1.3.6.1.4.1.32285.11.2.3.4.11.2.1.4
		topOnuSnmpTrapHostIp OBJECT-TYPE
			SYNTAX IpAddress
			MAX-ACCESS read-write
			STATUS current
			DESCRIPTION
				"Trap host ip."
			::= { topOnuSnmpProfileEntry 4 }

		
		-- 1.3.6.1.4.1.32285.11.2.3.4.11.2.1.5
		topOnuSnmpTrapPort OBJECT-TYPE
			SYNTAX INTEGER (162 | 1025..65535)
			MAX-ACCESS read-write
			STATUS current
			DESCRIPTION
				"Trap port."
			::= { topOnuSnmpProfileEntry 5 }

		
		-- 1.3.6.1.4.1.32285.11.2.3.4.11.2.1.6
		topOnuSnmpPort OBJECT-TYPE
			SYNTAX INTEGER (161 | 1025..65535)
			MAX-ACCESS read-write
			STATUS current
			DESCRIPTION
				"Snmp port."
			::= { topOnuSnmpProfileEntry 6 }

		
		-- 1.3.6.1.4.1.32285.11.2.3.4.11.2.1.7
		topOnuSnmpSecurityName OBJECT-TYPE
			SYNTAX OCTET STRING (SIZE (1..31))
			MAX-ACCESS read-write
			STATUS current
			DESCRIPTION
				"Secutity name,in snmp v1 or v2c, it just equals trap community."
			::= { topOnuSnmpProfileEntry 7 }

		
		-- 1.3.6.1.4.1.32285.11.2.3.4.11.2.1.8
		topOnuSnmpReadCommunity OBJECT-TYPE
			SYNTAX OCTET STRING (SIZE (1..31))
			MAX-ACCESS read-write
			STATUS current
			DESCRIPTION
				"Read community."
			::= { topOnuSnmpProfileEntry 8 }

		
		-- 1.3.6.1.4.1.32285.11.2.3.4.11.2.1.9
		topOnuSnmpWriteCommunity OBJECT-TYPE
			SYNTAX OCTET STRING (SIZE (1..31))
			MAX-ACCESS read-write
			STATUS current
			DESCRIPTION
				"Write community."
			::= { topOnuSnmpProfileEntry 9 }

		
		-- 1.3.6.1.4.1.32285.11.2.3.4.11.2.1.10
		topSnmpProfileRefCount OBJECT-TYPE
			SYNTAX INTEGER
			MAX-ACCESS read-only
			STATUS current
			DESCRIPTION
				"Profile refcount."
			::= { topOnuSnmpProfileEntry 10 }

		
		-- 1.3.6.1.4.1.32285.11.2.3.4.11.2.1.11
		topSnmpProfileRowStatus OBJECT-TYPE
			SYNTAX RowStatus
			MAX-ACCESS read-create
			STATUS current
			DESCRIPTION
				"Row status."
			::= { topOnuSnmpProfileEntry 11 }

		
		-- 1.3.6.1.4.1.32285.11.2.3.4.11.3
		topOnuSnmpProfileBindTable OBJECT-TYPE
			SYNTAX SEQUENCE OF TopOnuSnmpProfileBindEntry
			MAX-ACCESS not-accessible
			STATUS current
			DESCRIPTION
				"Profile bind table."
			::= { topOnuManageParameterObject 3 }

		
		-- 1.3.6.1.4.1.32285.11.2.3.4.11.3.1
		topOnuSnmpProfileBindEntry OBJECT-TYPE
			SYNTAX TopOnuSnmpProfileBindEntry
			MAX-ACCESS not-accessible
			STATUS current
			DESCRIPTION
				"Profile bind entry."
			INDEX { topOnuSnmpCardIndex, topOnuSnmpPonIndex, topOnuSnmpOnuIndex }
			::= { topOnuSnmpProfileBindTable 1 }

		
		TopOnuSnmpProfileBindEntry ::=
			SEQUENCE { 
				topOnuSnmpCardIndex
					TopEPonSlotIndex,
				topOnuSnmpPonIndex
					TopEPonPonIndex,
				topOnuSnmpOnuIndex
					TopEPonOnuAuthNum,
				topOnuSnmpBindProfileIdx
					INTEGER,
				topOnuSnmpBindProfileRowStatus
					RowStatus
			 }

		-- 1.3.6.1.4.1.32285.11.2.3.4.11.3.1.1
		topOnuSnmpCardIndex OBJECT-TYPE
			SYNTAX TopEPonSlotIndex
			MAX-ACCESS not-accessible
			STATUS current
			DESCRIPTION
				"Epon slot id."
			::= { topOnuSnmpProfileBindEntry 1 }

		
		-- 1.3.6.1.4.1.32285.11.2.3.4.11.3.1.2
		topOnuSnmpPonIndex OBJECT-TYPE
			SYNTAX TopEPonPonIndex
			MAX-ACCESS not-accessible
			STATUS current
			DESCRIPTION
				"Epon pon id."
			::= { topOnuSnmpProfileBindEntry 2 }

		
		-- 1.3.6.1.4.1.32285.11.2.3.4.11.3.1.3
		topOnuSnmpOnuIndex OBJECT-TYPE
			SYNTAX TopEPonOnuAuthNum
			MAX-ACCESS not-accessible
			STATUS current
			DESCRIPTION
				"Epon onu id."
			::= { topOnuSnmpProfileBindEntry 3 }

		
		-- 1.3.6.1.4.1.32285.11.2.3.4.11.3.1.4
		topOnuSnmpBindProfileIdx OBJECT-TYPE
			SYNTAX INTEGER (1..64)
			MAX-ACCESS read-write
			STATUS current
			DESCRIPTION
				"Profile id."
			::= { topOnuSnmpProfileBindEntry 4 }

		
		-- 1.3.6.1.4.1.32285.11.2.3.4.11.3.1.5
		topOnuSnmpBindProfileRowStatus OBJECT-TYPE
			SYNTAX RowStatus
			MAX-ACCESS read-create
			STATUS current
			DESCRIPTION
				"Row status."
			::= { topOnuSnmpProfileBindEntry 5 }

		
		-- 1.3.6.1.4.1.32285.11.2.3.4.12
		topOnuOpticalObjects OBJECT IDENTIFIER ::= { topOnuObjects 12 }

		
		-- 1.3.6.1.4.1.32285.11.2.3.4.12.1
		topOnuOptAlarmTable OBJECT-TYPE
			SYNTAX SEQUENCE OF TopOnuOptAlarmEntry
			MAX-ACCESS not-accessible
			STATUS current
			DESCRIPTION
				"Description."
			::= { topOnuOpticalObjects 1 }

		
		-- 1.3.6.1.4.1.32285.11.2.3.4.12.1.1
		topOnuOptAlarmEntry OBJECT-TYPE
			SYNTAX TopOnuOptAlarmEntry
			MAX-ACCESS not-accessible
			STATUS current
			DESCRIPTION
				"Description."
			INDEX { topOnuOptCardIndex, topOnuOptPonIndex, topOnuOptOnuIndex, topOnuOptAlarmIndex }
			::= { topOnuOptAlarmTable 1 }

		
		TopOnuOptAlarmEntry ::=
			SEQUENCE { 
				topOnuOptCardIndex
					TopEPonSlotIndex,
				topOnuOptPonIndex
					TopEPonPonIndex,
				topOnuOptOnuIndex
					TopEPonOnuAuthNum,
				topOnuOptAlarmIndex
					INTEGER,
				topOnuOptThresholdValue
					INTEGER,
				topOnuOptAlarmState
					INTEGER,
				topOnuOptAlarmCount
					INTEGER,
				topOnuOptAlarmRowStatus
					RowStatus
			 }

		-- 1.3.6.1.4.1.32285.11.2.3.4.12.1.1.1
		topOnuOptCardIndex OBJECT-TYPE
			SYNTAX TopEPonSlotIndex
			MAX-ACCESS not-accessible
			STATUS current
			DESCRIPTION
				"The slot index."
			::= { topOnuOptAlarmEntry 1 }

		
		-- 1.3.6.1.4.1.32285.11.2.3.4.12.1.1.2
		topOnuOptPonIndex OBJECT-TYPE
			SYNTAX TopEPonPonIndex
			MAX-ACCESS not-accessible
			STATUS current
			DESCRIPTION
				"The pon index."
			::= { topOnuOptAlarmEntry 2 }

		
		-- 1.3.6.1.4.1.32285.11.2.3.4.12.1.1.3
		topOnuOptOnuIndex OBJECT-TYPE
			SYNTAX TopEPonOnuAuthNum
			MAX-ACCESS not-accessible
			STATUS current
			DESCRIPTION
				"The onu index."
			::= { topOnuOptAlarmEntry 3 }

		
		-- 1.3.6.1.4.1.32285.11.2.3.4.12.1.1.4
		topOnuOptAlarmIndex OBJECT-TYPE
			SYNTAX INTEGER
			MAX-ACCESS not-accessible
			STATUS current
			DESCRIPTION
				"The onu optical alarm index."
			::= { topOnuOptAlarmEntry 4 }

		
		-- 1.3.6.1.4.1.32285.11.2.3.4.12.1.1.5
		topOnuOptThresholdValue OBJECT-TYPE
			SYNTAX INTEGER
			MAX-ACCESS read-write
			STATUS current
			DESCRIPTION
				"The onu optical threshold value."
			::= { topOnuOptAlarmEntry 5 }

		
		-- 1.3.6.1.4.1.32285.11.2.3.4.12.1.1.6
		topOnuOptAlarmState OBJECT-TYPE
			SYNTAX INTEGER
			MAX-ACCESS read-write
			STATUS current
			DESCRIPTION
				"The onu aptical alarm state:2--disable,1--enable."
			::= { topOnuOptAlarmEntry 6 }

		
		-- 1.3.6.1.4.1.32285.11.2.3.4.12.1.1.7
		topOnuOptAlarmCount OBJECT-TYPE
			SYNTAX INTEGER
			MAX-ACCESS read-only
			STATUS current
			DESCRIPTION
				"The count of onu optical alarm."
			::= { topOnuOptAlarmEntry 7 }

		
		-- 1.3.6.1.4.1.32285.11.2.3.4.12.1.1.8
		topOnuOptAlarmRowStatus OBJECT-TYPE
			SYNTAX RowStatus
			MAX-ACCESS read-create
			STATUS current
			DESCRIPTION
				"Add/Del/Set."
			::= { topOnuOptAlarmEntry 8 }

		
		-- 1.3.6.1.4.1.32285.11.2.3.4.12.2
		topOnuPonOpticalTransmissionTable OBJECT-TYPE
			SYNTAX SEQUENCE OF TopOnuPonOpticalTransmissionEntry
			MAX-ACCESS not-accessible
			STATUS current
			DESCRIPTION
				"Description."
			::= { topOnuOpticalObjects 2 }

		
		-- 1.3.6.1.4.1.32285.11.2.3.4.12.2.1
		topOnuPonOpticalTransmissionEntry OBJECT-TYPE
			SYNTAX TopOnuPonOpticalTransmissionEntry
			MAX-ACCESS not-accessible
			STATUS current
			DESCRIPTION
				"Description."
			INDEX { topOnuPonOpticalTransmissionDeviceIndex, topOnuPonOpticalTransmissionCardIndex, topOnuPonOpticalTransmissionPortIndex }
			::= { topOnuPonOpticalTransmissionTable 1 }

		
		TopOnuPonOpticalTransmissionEntry ::=
			SEQUENCE { 
				topOnuPonOpticalTransmissionDeviceIndex
					INTEGER,
				topOnuPonOpticalTransmissionCardIndex
					INTEGER,
				topOnuPonOpticalTransmissionPortIndex
					INTEGER,
				topOnuReceivedOpticalPower
					INTEGER,
				topOnuTramsmittedOpticalPower
					INTEGER,
				topOnuBiasCurrent
					INTEGER,
				topOnuWorkingVoltage
					INTEGER,
				topOnuWorkingTemperature
					INTEGER,
				topOltReceivedOpticalPower
					INTEGER
			 }


		-- 1.3.6.1.4.1.32285.11.2.3.4.12.2.1.1
		topOnuPonOpticalTransmissionDeviceIndex OBJECT-TYPE
			SYNTAX INTEGER
			MAX-ACCESS not-accessible
			STATUS current
			DESCRIPTION
				"Description."
			::= { topOnuPonOpticalTransmissionEntry 1 }

		
		-- 1.3.6.1.4.1.32285.11.2.3.4.12.2.1.2
		topOnuPonOpticalTransmissionCardIndex OBJECT-TYPE
			SYNTAX INTEGER
			MAX-ACCESS not-accessible
			STATUS current
			DESCRIPTION
				"Description."
			::= { topOnuPonOpticalTransmissionEntry 2 }

		
		-- 1.3.6.1.4.1.32285.11.2.3.4.12.2.1.3
		topOnuPonOpticalTransmissionPortIndex OBJECT-TYPE
			SYNTAX INTEGER
			MAX-ACCESS not-accessible
			STATUS current
			DESCRIPTION
				"Description."
			::= { topOnuPonOpticalTransmissionEntry 3 }

		
		-- 1.3.6.1.4.1.32285.11.2.3.4.12.2.1.4
		topOnuReceivedOpticalPower OBJECT-TYPE
			SYNTAX INTEGER
			UNITS "centi-dBm"
			MAX-ACCESS read-only
			STATUS current
			DESCRIPTION
				"received Optical Power"
			::= { topOnuPonOpticalTransmissionEntry 4 }

		
		-- 1.3.6.1.4.1.32285.11.2.3.4.12.2.1.5
		topOnuTramsmittedOpticalPower OBJECT-TYPE
			SYNTAX INTEGER
			UNITS "centi-dBm"
			MAX-ACCESS read-only
			STATUS current
			DESCRIPTION
				"tramsmitted Optical Power"
			::= { topOnuPonOpticalTransmissionEntry 5 }

		
		-- 1.3.6.1.4.1.32285.11.2.3.4.12.2.1.6
		topOnuBiasCurrent OBJECT-TYPE
			SYNTAX INTEGER
			UNITS "centi-mA"
			MAX-ACCESS read-only
			STATUS current
			DESCRIPTION
				"biasCurrent"
			::= { topOnuPonOpticalTransmissionEntry 6 }

		
		-- 1.3.6.1.4.1.32285.11.2.3.4.12.2.1.7
		topOnuWorkingVoltage OBJECT-TYPE
			SYNTAX INTEGER
			UNITS "centi-mV"
			MAX-ACCESS read-only
			STATUS current
			DESCRIPTION
				"onuworking Voltage"
			::= { topOnuPonOpticalTransmissionEntry 7 }

		
		-- 1.3.6.1.4.1.32285.11.2.3.4.12.2.1.8
		topOnuWorkingTemperature OBJECT-TYPE
			SYNTAX INTEGER
			UNITS "Centi-degree centigrade"
			MAX-ACCESS read-only
			STATUS current
			DESCRIPTION
				"working Temperature"
			::= { topOnuPonOpticalTransmissionEntry 8 }

		
		-- 1.3.6.1.4.1.32285.11.2.3.4.12.2.1.9
		topOltReceivedOpticalPower OBJECT-TYPE
			SYNTAX INTEGER
			UNITS "Centi-dBm"
			MAX-ACCESS read-only
			STATUS current
			DESCRIPTION
				"Olt received Optical Power"
			::= { topOnuPonOpticalTransmissionEntry 9 }

		
		-- 1.3.6.1.4.1.32285.11.2.3.4.13
		topOnuFilterObjects OBJECT IDENTIFIER ::= { topOnuObjects 13 }

		
		-- 1.3.6.1.4.1.32285.11.2.3.4.13.1
		topOnuFrameFilterTable OBJECT-TYPE
			SYNTAX SEQUENCE OF TopOnuFrameFilterEntry
			MAX-ACCESS not-accessible
			STATUS current
			DESCRIPTION
				"Description."
			::= { topOnuFilterObjects 1 }

		
		-- 1.3.6.1.4.1.32285.11.2.3.4.13.1.1
		topOnuFrameFilterEntry OBJECT-TYPE
			SYNTAX TopOnuFrameFilterEntry
			MAX-ACCESS not-accessible
			STATUS current
			DESCRIPTION
				"Description."
			INDEX { topOnuFrameFilterCardIndex, topOnuFrameFilterPonIndex, topOnuFrameFilterOnuIndex }
			::= { topOnuFrameFilterTable 1 }

		
		TopOnuFrameFilterEntry ::=
			SEQUENCE { 
				topOnuFrameFilterCardIndex
					TopEPonSlotIndex,
				topOnuFrameFilterPonIndex
					TopEPonPonIndex,
				topOnuFrameFilterOnuIndex
					TopEPonOnuAuthNum,
				topOnuFrameFilterEntryNum
					INTEGER,
				topOnuFrameFilterEntryData
					OCTET STRING
			 }

		-- 1.3.6.1.4.1.32285.11.2.3.4.13.1.1.1
		topOnuFrameFilterCardIndex OBJECT-TYPE
			SYNTAX TopEPonSlotIndex
			MAX-ACCESS not-accessible
			STATUS current
			DESCRIPTION
				"The slot index."
			::= { topOnuFrameFilterEntry 1 }

		
		-- 1.3.6.1.4.1.32285.11.2.3.4.13.1.1.2
		topOnuFrameFilterPonIndex OBJECT-TYPE
			SYNTAX TopEPonPonIndex
			MAX-ACCESS not-accessible
			STATUS current
			DESCRIPTION
				"The pon port index."
			::= { topOnuFrameFilterEntry 2 }

		
		-- 1.3.6.1.4.1.32285.11.2.3.4.13.1.1.3
		topOnuFrameFilterOnuIndex OBJECT-TYPE
			SYNTAX TopEPonOnuAuthNum
			MAX-ACCESS not-accessible
			STATUS current
			DESCRIPTION
				"The onu index."
			::= { topOnuFrameFilterEntry 3 }

		
		-- 1.3.6.1.4.1.32285.11.2.3.4.13.1.1.4
		topOnuFrameFilterEntryNum OBJECT-TYPE
			SYNTAX INTEGER (0..16)
			MAX-ACCESS read-write
			STATUS current
			DESCRIPTION
				"The number of frame filter."
			::= { topOnuFrameFilterEntry 4 }

		
		-- 1.3.6.1.4.1.32285.11.2.3.4.13.1.1.5
		topOnuFrameFilterEntryData OBJECT-TYPE
			SYNTAX OCTET STRING (SIZE (128))
			MAX-ACCESS read-write
			STATUS current
			DESCRIPTION
				"The data of frame filter."
			::= { topOnuFrameFilterEntry 5 }

		
		-- 1.3.6.1.4.1.32285.11.2.3.4.14
		topOnuInfoObjects OBJECT IDENTIFIER ::= { topOnuObjects 14 }

		
		-- 1.3.6.1.4.1.32285.11.2.3.4.14.1
		topOnuVersionTable OBJECT-TYPE
			SYNTAX SEQUENCE OF TopOnuVersionEntry
			MAX-ACCESS not-accessible
			STATUS current
			DESCRIPTION
				"Description."
			::= { topOnuInfoObjects 1 }

		
		-- 1.3.6.1.4.1.32285.11.2.3.4.14.1.1
		topOnuVersionEntry OBJECT-TYPE
			SYNTAX TopOnuVersionEntry
			MAX-ACCESS not-accessible
			STATUS current
			DESCRIPTION
				"Description."
			INDEX { topOnuVerCardIndex, topOnuVerPonIndex, topOnuVerOnuIndex }
			::= { topOnuVersionTable 1 }

		
		TopOnuVersionEntry ::=
			SEQUENCE { 
				topOnuVerCardIndex
					TopEPonSlotIndex,
				topOnuVerPonIndex
					TopEPonPonIndex,
				topOnuVerOnuIndex
					TopEPonOnuAuthNum,
				topOnuVendorId
					INTEGER,
				topOnuModel
					INTEGER,
				topOnuMacAddress
					MacAddress,
				topOnuSoftwareVersion
					OCTET STRING,
				topOnuVerHardwareVersion
					OCTET STRING,
				topOnuFirmwareVersion
					OCTET STRING,
				topOnuChipVenderId
					INTEGER,
				topOnuChipModel
					INTEGER,
				topOnuChipRevision
					INTEGER,
				topOnuChipVersion
					INTEGER,
				topOnuTimeSinceLastDeregister
				    Counter32,
				topOnuReasonOfLastDeregister
				    INTEGER
			 }

		-- 1.3.6.1.4.1.32285.11.2.3.4.14.1.1.1
		topOnuVerCardIndex OBJECT-TYPE
			SYNTAX TopEPonSlotIndex
			MAX-ACCESS not-accessible
			STATUS current
			DESCRIPTION
				"Description."
			::= { topOnuVersionEntry 1 }

		
		-- 1.3.6.1.4.1.32285.11.2.3.4.14.1.1.2
		topOnuVerPonIndex OBJECT-TYPE
			SYNTAX TopEPonPonIndex
			MAX-ACCESS not-accessible
			STATUS current
			DESCRIPTION
				"Description."
			::= { topOnuVersionEntry 2 }

		
		-- 1.3.6.1.4.1.32285.11.2.3.4.14.1.1.3
		topOnuVerOnuIndex OBJECT-TYPE
			SYNTAX TopEPonOnuAuthNum
			MAX-ACCESS not-accessible
			STATUS current
			DESCRIPTION
				"Description."
			::= { topOnuVersionEntry 3 }

		
		-- 1.3.6.1.4.1.32285.11.2.3.4.14.1.1.4
		topOnuVendorId OBJECT-TYPE
			SYNTAX INTEGER
			MAX-ACCESS read-only
			STATUS current
			DESCRIPTION
				"Description."
			::= { topOnuVersionEntry 4 }

		
		-- 1.3.6.1.4.1.32285.11.2.3.4.14.1.1.5
		topOnuModel OBJECT-TYPE
			SYNTAX INTEGER
			MAX-ACCESS read-only
			STATUS current
			DESCRIPTION
				"Description."
			::= { topOnuVersionEntry 5 }

		
		-- 1.3.6.1.4.1.32285.11.2.3.4.14.1.1.6
		topOnuMacAddress OBJECT-TYPE
			SYNTAX MacAddress
			MAX-ACCESS read-only
			STATUS current
			DESCRIPTION
				"Description."
			::= { topOnuVersionEntry 6 }

		
		-- 1.3.6.1.4.1.32285.11.2.3.4.14.1.1.7
		topOnuSoftwareVersion OBJECT-TYPE
			SYNTAX OCTET STRING (SIZE (16))
			MAX-ACCESS read-only
			STATUS current
			DESCRIPTION
				"Description."
			::= { topOnuVersionEntry 7 }

		
		-- 1.3.6.1.4.1.32285.11.2.3.4.14.1.1.8
		topOnuVerHardwareVersion OBJECT-TYPE
			SYNTAX OCTET STRING (SIZE (8))
			MAX-ACCESS read-only
			STATUS current
			DESCRIPTION
				"Description."
			::= { topOnuVersionEntry 8 }

		
		-- 1.3.6.1.4.1.32285.11.2.3.4.14.1.1.9
		topOnuFirmwareVersion OBJECT-TYPE
			SYNTAX OCTET STRING (SIZE (64))
			MAX-ACCESS read-only
			STATUS current
			DESCRIPTION
				"Description."
			::= { topOnuVersionEntry 9 }

		
		-- 1.3.6.1.4.1.32285.11.2.3.4.14.1.1.10
		topOnuChipVenderId OBJECT-TYPE
			SYNTAX INTEGER
			MAX-ACCESS read-only
			STATUS current
			DESCRIPTION
				"Description."
			::= { topOnuVersionEntry 10 }

		
		-- 1.3.6.1.4.1.32285.11.2.3.4.14.1.1.11
		topOnuChipModel OBJECT-TYPE
			SYNTAX INTEGER
			MAX-ACCESS read-only
			STATUS current
			DESCRIPTION
				"Description."
			::= { topOnuVersionEntry 11 }

		
		-- 1.3.6.1.4.1.32285.11.2.3.4.14.1.1.12
		topOnuChipRevision OBJECT-TYPE
			SYNTAX INTEGER
			MAX-ACCESS read-only
			STATUS current
			DESCRIPTION
				"Description."
			::= { topOnuVersionEntry 12 }

		
		-- 1.3.6.1.4.1.32285.11.2.3.4.14.1.1.13
		topOnuChipVersion OBJECT-TYPE
			SYNTAX INTEGER
			MAX-ACCESS read-only
			STATUS current
			DESCRIPTION
				"Description."
			::= { topOnuVersionEntry 13 }
			
		-- 1.3.6.1.4.1.32285.11.2.3.4.14.1.1.14
		topOnuTimeSinceLastDeregister OBJECT-TYPE
			SYNTAX Counter32
			UNITS "seconds"
			MAX-ACCESS read-only
			STATUS current
			DESCRIPTION
				"Onu last deregister time."
			DEFVAL { 0 }
			::= { topOnuVersionEntry 14 }
			
		-- 1.3.6.1.4.1.32285.11.2.3.4.14.1.1.15
		topOnuReasonOfLastDeregister OBJECT-TYPE
			SYNTAX INTEGER
				{
				none(0),
				poweroff(1),
				fiberbreak(2),
				other(3)
				}
			MAX-ACCESS read-only
			STATUS current
			DESCRIPTION
				"Onu last deregister reason.
				 0: none, meaningless
                                 1: power off
                                 2: fiber break
				 3: other
				"
			DEFVAL { 0 }
			::= { topOnuVersionEntry 15 }		
		
		-- 1.3.6.1.4.1.32285.11.2.3.4.15
		topOnuGlobalCfgObjects OBJECT IDENTIFIER ::= { topOnuObjects 15 }

		
		-- 1.3.6.1.4.1.32285.11.2.3.4.15.1
		topOnuGlobalBind OBJECT-TYPE
			SYNTAX INTEGER
				{
				enable(1),
				disable(2)
				}
			MAX-ACCESS read-write
			STATUS current
			DESCRIPTION
				"Description."
			::= { topOnuGlobalCfgObjects 1 }


		-- 1.3.6.1.4.1.32285.11.2.3.4.15.2
		topOnuGlobalCfgMgmtTable OBJECT-TYPE
			SYNTAX SEQUENCE OF TopOnuGlobalCfgMgmtEntry
			MAX-ACCESS not-accessible
			STATUS current
			DESCRIPTION
				"Description."
			::= { topOnuGlobalCfgObjects 2 }


		-- 1.3.6.1.4.1.32285.11.2.3.4.15.2.1
		topOnuGlobalCfgMgmtEntry OBJECT-TYPE
			SYNTAX TopOnuGlobalCfgMgmtEntry
			MAX-ACCESS not-accessible
			STATUS current
			DESCRIPTION
				"Description."
			INDEX { topOnuGlobalCfgMgmtItemIndex }
			::= { topOnuGlobalCfgMgmtTable 1 }


		TopOnuGlobalCfgMgmtEntry ::=
			SEQUENCE { 
				topOnuGlobalCfgMgmtItemIndex
					INTEGER,
				topOnuGlobalCfgMgmtValue
					BITS
			 }


		-- 1.3.6.1.4.1.32285.11.2.3.4.15.2.1.1
		topOnuGlobalCfgMgmtItemIndex OBJECT-TYPE
			SYNTAX INTEGER
				{
				wan(1),
				wlan(2),
				catv(3)
				}
			MAX-ACCESS not-accessible
			STATUS current
			DESCRIPTION
				"1-wan, 2-wlan,3-catv"
			::= { topOnuGlobalCfgMgmtEntry 1 }
		

		-- 1.3.6.1.4.1.32285.11.2.3.4.15.2.2
		topOnuGlobalCfgMgmtValue OBJECT-TYPE
			SYNTAX BITS
				{
				oam(0),
				tr069(1)
				}
			MAX-ACCESS read-write
			STATUS current
			DESCRIPTION
				"bit0: 1-enable olt oam/omci management; 0-disable olt oam/omci management;
				 bit1: 1-enable tr069 management; 0-disable tr069 management; this feature not supported"
			::= { topOnuGlobalCfgMgmtEntry 2 }


		-- 1.3.6.1.4.1.32285.11.2.3.4.16
		topOnuSrvProfileObjects OBJECT IDENTIFIER ::= { topOnuObjects 16 }

		
		-- 1.3.6.1.4.1.32285.11.2.3.4.16.1
		topOnuSrvProfileTable OBJECT-TYPE
			SYNTAX SEQUENCE OF TopOnuSrvProfileEntry
			MAX-ACCESS not-accessible
			STATUS current
			DESCRIPTION
				"Description."
			::= { topOnuSrvProfileObjects 1 }

		
		-- 1.3.6.1.4.1.32285.11.2.3.4.16.1.1
		topOnuSrvProfileEntry OBJECT-TYPE
			SYNTAX TopOnuSrvProfileEntry
			MAX-ACCESS not-accessible
			STATUS current
			DESCRIPTION
				"Description."
			INDEX { topOnuSrvProfileIndex }
			::= { topOnuSrvProfileTable 1 }

		
		TopOnuSrvProfileEntry ::=
			SEQUENCE { 
				topOnuSrvProfileIndex
					INTEGER,
				topOnuSrvProfileName
					OCTET STRING,
				topOnuSrvProfileIgmpMode
					INTEGER,
				topOnuSrvProfileIgmpFastLeave
					INTEGER,
				topOnuSrvProfileBindCapSet
					INTEGER,
				topOnuSrvProfileRefCnt
					INTEGER,
				topOnuSrvProfileRowstatus
					RowStatus
			 }

		-- 1.3.6.1.4.1.32285.11.2.3.4.16.1.1.1
		topOnuSrvProfileIndex OBJECT-TYPE
			SYNTAX INTEGER (1..256)
			MAX-ACCESS not-accessible
			STATUS current
			DESCRIPTION
				"OnuSrvProfile id.<1-256>"
			::= { topOnuSrvProfileEntry 1 }

		
		-- 1.3.6.1.4.1.32285.11.2.3.4.16.1.1.2
		topOnuSrvProfileName OBJECT-TYPE
			SYNTAX OCTET STRING (SIZE (1..31))
			MAX-ACCESS read-write
			STATUS current
			DESCRIPTION
				"OnuSrvProfile Description."
			::= { topOnuSrvProfileEntry 2 }

		
		-- 1.3.6.1.4.1.32285.11.2.3.4.16.1.1.3
		topOnuSrvProfileIgmpMode OBJECT-TYPE
			SYNTAX INTEGER
				{
				unset(0),
				ctc(1),
				snooping(2),
				disable(3)
				}
			MAX-ACCESS read-write
			STATUS current
			DESCRIPTION
				"igmp mode, depend on igmpMode."
			DEFVAL { unset }
			::= { topOnuSrvProfileEntry 3 }

		
		-- 1.3.6.1.4.1.32285.11.2.3.4.16.1.1.4
		topOnuSrvProfileIgmpFastLeave OBJECT-TYPE
			SYNTAX INTEGER
				{
				unset(0),
				enable(1),
				disable(2)
				}
			MAX-ACCESS read-write
			STATUS current
			DESCRIPTION
				"Description."
			DEFVAL { unset }
			::= { topOnuSrvProfileEntry 4 }

		
		-- 1.3.6.1.4.1.32285.11.2.3.4.16.1.1.5
		topOnuSrvProfileBindCapSet OBJECT-TYPE
			SYNTAX INTEGER (0..256)
			MAX-ACCESS read-write
			STATUS current
			DESCRIPTION
				"0 means unbind."
			::= { topOnuSrvProfileEntry 5 }

		
		-- 1.3.6.1.4.1.32285.11.2.3.4.16.1.1.6
		topOnuSrvProfileRefCnt OBJECT-TYPE
			SYNTAX INTEGER
			MAX-ACCESS read-only
			STATUS current
			DESCRIPTION
				"Description."
			::= { topOnuSrvProfileEntry 6 }

		
		-- 1.3.6.1.4.1.32285.11.2.3.4.16.1.1.7
		topOnuSrvProfileRowstatus OBJECT-TYPE
			SYNTAX RowStatus
			MAX-ACCESS read-create
			STATUS current
			DESCRIPTION
				"Description."
			::= { topOnuSrvProfileEntry 7 }

		
		-- 1.3.6.1.4.1.32285.11.2.3.4.16.2
		topOnuSrvProfilePortCfgTable OBJECT-TYPE
			SYNTAX SEQUENCE OF TopOnuSrvProfilePortCfgEntry
			MAX-ACCESS not-accessible
			STATUS current
			DESCRIPTION
				"Description."
			::= { topOnuSrvProfileObjects 2 }

		
		-- 1.3.6.1.4.1.32285.11.2.3.4.16.2.1
		topOnuSrvProfilePortCfgEntry OBJECT-TYPE
			SYNTAX TopOnuSrvProfilePortCfgEntry
			MAX-ACCESS not-accessible
			STATUS current
			DESCRIPTION
				"Description."
			INDEX { topOnuSrvProfileCfgIndex, topOnuSrvProfilePortId }
			::= { topOnuSrvProfilePortCfgTable 1 }

		
		TopOnuSrvProfilePortCfgEntry ::=
			SEQUENCE { 
				topOnuSrvProfileCfgIndex
					INTEGER,
				topOnuSrvProfilePortId
					INTEGER,
				topOnuSrvProfileBindVlanProfile
					INTEGER,
				topOnuSrvProfileVlanPvid
					INTEGER,
				topOnuSrvProfilePortRowstatus
					RowStatus,
				topOnuSrvProfileVlanPvidPri
				    INTEGER
			 }

		-- 1.3.6.1.4.1.32285.11.2.3.4.16.2.1.1
		topOnuSrvProfileCfgIndex OBJECT-TYPE
			SYNTAX INTEGER (1..256)
			MAX-ACCESS not-accessible
			STATUS current
			DESCRIPTION
				"OnuSrvProfile id."
			::= { topOnuSrvProfilePortCfgEntry 1 }

		
		-- 1.3.6.1.4.1.32285.11.2.3.4.16.2.1.2
		topOnuSrvProfilePortId OBJECT-TYPE
			SYNTAX INTEGER (1..24)
			MAX-ACCESS not-accessible
			STATUS current
			DESCRIPTION
				"port ID.<1-24>"
			::= { topOnuSrvProfilePortCfgEntry 2 }

		
		-- 1.3.6.1.4.1.32285.11.2.3.4.16.2.1.3
		topOnuSrvProfileBindVlanProfile OBJECT-TYPE
			SYNTAX INTEGER (0..4094)
			MAX-ACCESS read-write
			STATUS current
			DESCRIPTION
				"vlan-profile id, 0 means unbind."
			DEFVAL { 0 }
			::= { topOnuSrvProfilePortCfgEntry 3 }

		
		-- 1.3.6.1.4.1.32285.11.2.3.4.16.2.1.4
		topOnuSrvProfileVlanPvid OBJECT-TYPE
			SYNTAX INTEGER (0..4094)
			MAX-ACCESS read-write
			STATUS current
			DESCRIPTION
				"0 means no configurate."
			DEFVAL { 0 }
			::= { topOnuSrvProfilePortCfgEntry 4 }

		
		-- 1.3.6.1.4.1.32285.11.2.3.4.16.2.1.5
		topOnuSrvProfilePortRowstatus OBJECT-TYPE
			SYNTAX RowStatus
			MAX-ACCESS read-create
			STATUS current
			DESCRIPTION
				"Description."
			::= { topOnuSrvProfilePortCfgEntry 5 }
			
		-- 1.3.6.1.4.1.32285.11.2.3.4.16.2.1.6
		topOnuSrvProfileVlanPvidPri OBJECT-TYPE
			SYNTAX INTEGER (0..7)
			MAX-ACCESS read-write
			STATUS current
			DESCRIPTION
				"vlan priority."
			DEFVAL { 0 }
			::= { topOnuSrvProfilePortCfgEntry 6 }
		
		-- 1.3.6.1.4.1.32285.11.2.3.4.16.3
		topOnuSrvProfilePortIgmpTable OBJECT-TYPE
			SYNTAX SEQUENCE OF TopOnuSrvProfilePortIgmpEntry
			MAX-ACCESS not-accessible
			STATUS current
			DESCRIPTION
				"Description."
			::= { topOnuSrvProfileObjects 3 }

		
		-- 1.3.6.1.4.1.32285.11.2.3.4.16.3.1
		topOnuSrvProfilePortIgmpEntry OBJECT-TYPE
			SYNTAX TopOnuSrvProfilePortIgmpEntry
			MAX-ACCESS not-accessible
			STATUS current
			DESCRIPTION
				"Description."
			INDEX { topOnuSrvProfileIgmpIndex, topOnuSrvProfilePortIgmpId }
			::= { topOnuSrvProfilePortIgmpTable 1 }

		
		TopOnuSrvProfilePortIgmpEntry ::=
			SEQUENCE { 
				topOnuSrvProfileIgmpIndex
					INTEGER,
				topOnuSrvProfilePortIgmpId
					INTEGER,
				topOnuSrvProfileIgmpMaxGroup
					INTEGER,
				topOnuSrvProfileIgmpVlanMode
					INTEGER,
				topOnuSrvProfilePortIgmpTransIdx
					INTEGER,
				topOnuSrvProfilePortIgmpVlanList
					OCTET STRING,
				topOnuSrvProfilePortIgmpRowstatus
					RowStatus
			 }

		-- 1.3.6.1.4.1.32285.11.2.3.4.16.3.1.1
		topOnuSrvProfileIgmpIndex OBJECT-TYPE
			SYNTAX INTEGER (1..256)
			MAX-ACCESS not-accessible
			STATUS current
			DESCRIPTION
				"OnuSrvProfile id."
			::= { topOnuSrvProfilePortIgmpEntry 1 }

		
		-- 1.3.6.1.4.1.32285.11.2.3.4.16.3.1.2
		topOnuSrvProfilePortIgmpId OBJECT-TYPE
			SYNTAX INTEGER (1..24)
			MAX-ACCESS not-accessible
			STATUS current
			DESCRIPTION
				"port ID.<1-24>"
			::= { topOnuSrvProfilePortIgmpEntry 2 }

		
		-- 1.3.6.1.4.1.32285.11.2.3.4.16.3.1.3
		topOnuSrvProfileIgmpMaxGroup OBJECT-TYPE
			SYNTAX INTEGER (-1..64)
			MAX-ACCESS read-write
			STATUS current
			DESCRIPTION
				"0: do not limit other value: use specific value"
			DEFVAL { -1 }
			::= { topOnuSrvProfilePortIgmpEntry 3 }

		
		-- 1.3.6.1.4.1.32285.11.2.3.4.16.3.1.4
		topOnuSrvProfileIgmpVlanMode OBJECT-TYPE
			SYNTAX INTEGER
				{
				unset(0),
				strip(1),
				translation(2),
				kepp(3)
				}
			MAX-ACCESS read-write
			STATUS current
			DESCRIPTION
				"Description."
			DEFVAL { unset }
			::= { topOnuSrvProfilePortIgmpEntry 4 }

		
		-- 1.3.6.1.4.1.32285.11.2.3.4.16.3.1.5
		topOnuSrvProfilePortIgmpTransIdx OBJECT-TYPE
			SYNTAX INTEGER (1..64)
			MAX-ACCESS read-write
			STATUS obsolete
			DESCRIPTION
				"vlan translation map index.Valid only when topMcUniVlanMode is translation(2)."
			::= { topOnuSrvProfilePortIgmpEntry 5 }

		

		-- 1.3.6.1.4.1.32285.11.2.3.4.16.3.1.6
		topOnuSrvProfilePortIgmpVlanList OBJECT-TYPE
			SYNTAX OCTET STRING (SIZE (64))
			MAX-ACCESS read-write
			STATUS current
			DESCRIPTION
				"Port allows max 32 multicast vlans.Every two octets compose an integer, which represent an vlan id.
				"
			::= { topOnuSrvProfilePortIgmpEntry 6 }

		
        	-- 1.3.6.1.4.1.32285.11.2.3.4.16.3.1.7
		topOnuSrvProfilePortIgmpRowstatus OBJECT-TYPE
			SYNTAX RowStatus
			MAX-ACCESS read-create
			STATUS current
			DESCRIPTION
				"Description."
			::= { topOnuSrvProfilePortIgmpEntry 7 }

		
		-- 1.3.6.1.4.1.32285.11.2.3.4.16.4
		topOnuSrvProfileIgmpVlanTransTable OBJECT-TYPE
			SYNTAX SEQUENCE OF TopOnuSrvProfileIgmpVlanTransEntry
			MAX-ACCESS not-accessible
			STATUS current
			DESCRIPTION
				"Description."
			::= { topOnuSrvProfileObjects 4 }

		
		-- 1.3.6.1.4.1.32285.11.2.3.4.16.4.1
		topOnuSrvProfileIgmpVlanTransEntry OBJECT-TYPE
			SYNTAX TopOnuSrvProfileIgmpVlanTransEntry
			MAX-ACCESS not-accessible
			STATUS current
			DESCRIPTION
				"Description."
			INDEX { topOnuSrvProfileIgmpProfIndex, topOnuSrvProfileIgmpPortId, topOnuSrvProfileIgmpVlanTransIndex }
			::= { topOnuSrvProfileIgmpVlanTransTable 1 }

		
		TopOnuSrvProfileIgmpVlanTransEntry ::=
			SEQUENCE { 
				topOnuSrvProfileIgmpProfIndex
					INTEGER,
				topOnuSrvProfileIgmpPortId
					INTEGER,
				topOnuSrvProfileIgmpVlanTransIndex
					INTEGER,
				topOnuSrvProfileIgmpVlanTransOldVlan
					INTEGER,
				topOnuSrvProfileIgmpVlanTransNewVlan
					INTEGER,
				topOnuSrvProfileIgmpVlanTransRowstatus
					RowStatus
			 }

		-- 1.3.6.1.4.1.32285.11.2.3.4.16.4.1.1
		topOnuSrvProfileIgmpProfIndex OBJECT-TYPE
			SYNTAX INTEGER (1..256)
			MAX-ACCESS not-accessible
			STATUS current
			DESCRIPTION
				"Description."
			::= { topOnuSrvProfileIgmpVlanTransEntry 1 }

		
		-- 1.3.6.1.4.1.32285.11.2.3.4.16.4.1.2
		topOnuSrvProfileIgmpPortId OBJECT-TYPE
			SYNTAX INTEGER (1..24)
			MAX-ACCESS not-accessible
			STATUS current
			DESCRIPTION
				"Description."
			::= { topOnuSrvProfileIgmpVlanTransEntry 2 }

		
		-- 1.3.6.1.4.1.32285.11.2.3.4.16.4.1.3
		topOnuSrvProfileIgmpVlanTransIndex OBJECT-TYPE
			SYNTAX INTEGER (1..8)
			MAX-ACCESS not-accessible
			STATUS current
			DESCRIPTION
				"Description."
			::= { topOnuSrvProfileIgmpVlanTransEntry 3 }

		
		-- 1.3.6.1.4.1.32285.11.2.3.4.16.4.1.4
		topOnuSrvProfileIgmpVlanTransOldVlan OBJECT-TYPE
			SYNTAX INTEGER (1..4094)
			MAX-ACCESS read-write
			STATUS current
			DESCRIPTION
				"Description."
			::= { topOnuSrvProfileIgmpVlanTransEntry 4 }

		
		-- 1.3.6.1.4.1.32285.11.2.3.4.16.4.1.5
		topOnuSrvProfileIgmpVlanTransNewVlan OBJECT-TYPE
			SYNTAX INTEGER (1..4094)
			MAX-ACCESS read-write
			STATUS current
			DESCRIPTION
				"Description."
			::= { topOnuSrvProfileIgmpVlanTransEntry 5 }

		
		-- 1.3.6.1.4.1.32285.11.2.3.4.16.4.1.6
		topOnuSrvProfileIgmpVlanTransRowstatus OBJECT-TYPE
			SYNTAX RowStatus
			MAX-ACCESS read-create
			STATUS current
			DESCRIPTION
				"Description."
			::= { topOnuSrvProfileIgmpVlanTransEntry 6 }

		
		-- 1.3.6.1.4.1.32285.11.2.3.4.17
		topOnuCapabilitySetTable OBJECT-TYPE
			SYNTAX SEQUENCE OF TopOnuCapabilitySetEntry
			MAX-ACCESS not-accessible
			STATUS current
			DESCRIPTION
				"The table just supports creat/delect,not modify."
			::= { topOnuObjects 17 }

		
		-- 1.3.6.1.4.1.32285.11.2.3.4.17.1
		topOnuCapabilitySetEntry OBJECT-TYPE
			SYNTAX TopOnuCapabilitySetEntry
			MAX-ACCESS not-accessible
			STATUS current
			DESCRIPTION
				"Description."
			INDEX { topOnuCapSetIdIndex }
			::= { topOnuCapabilitySetTable 1 }

		
		TopOnuCapabilitySetEntry ::=
			SEQUENCE { 
				topOnuCapSetIdIndex
					INTEGER,
				topOnuCapSetGePortNum
					INTEGER,
				topOnuCapSetFePortNum
					INTEGER,
				topOnuCapSetPotsPortNum
					INTEGER,
				topOnuCapSetE1PortNum
					INTEGER,
				topOnuCapSetWlanPortNum
					INTEGER,
				topOnuCapSetCatvPortNum
					INTEGER,
				topOnuCapSetUartPortNum
					INTEGER,
				topOnuCapSetRowstatus
					RowStatus
			 }

		-- 1.3.6.1.4.1.32285.11.2.3.4.17.1.1
		topOnuCapSetIdIndex OBJECT-TYPE
			SYNTAX INTEGER (1..256)
			MAX-ACCESS not-accessible
			STATUS current
			DESCRIPTION
				"CapabilitySetId<1-32> is system default, no support creat/delect."
			::= { topOnuCapabilitySetEntry 1 }

		
		-- 1.3.6.1.4.1.32285.11.2.3.4.17.1.2
		topOnuCapSetGePortNum OBJECT-TYPE
			SYNTAX INTEGER (0..24)
			MAX-ACCESS read-create
			STATUS current
			DESCRIPTION
				"Description."
			::= { topOnuCapabilitySetEntry 2 }

		
		-- 1.3.6.1.4.1.32285.11.2.3.4.17.1.3
		topOnuCapSetFePortNum OBJECT-TYPE
			SYNTAX INTEGER (0..24)
			MAX-ACCESS read-create
			STATUS current
			DESCRIPTION
				"Description."
			::= { topOnuCapabilitySetEntry 3 }

		
		-- 1.3.6.1.4.1.32285.11.2.3.4.17.1.4
		topOnuCapSetPotsPortNum OBJECT-TYPE
			SYNTAX INTEGER (0..24)
			MAX-ACCESS read-create
			STATUS current
			DESCRIPTION
				"Description."
			::= { topOnuCapabilitySetEntry 4 }

		
		-- 1.3.6.1.4.1.32285.11.2.3.4.17.1.5
		topOnuCapSetE1PortNum OBJECT-TYPE
			SYNTAX INTEGER (0..24)
			MAX-ACCESS read-create
			STATUS current
			DESCRIPTION
				"Description."
			::= { topOnuCapabilitySetEntry 5 }

		
		-- 1.3.6.1.4.1.32285.11.2.3.4.17.1.6
		topOnuCapSetWlanPortNum OBJECT-TYPE
			SYNTAX INTEGER (0..24)
			MAX-ACCESS read-create
			STATUS current
			DESCRIPTION
				"Description."
			::= { topOnuCapabilitySetEntry 6 }

		
		-- 1.3.6.1.4.1.32285.11.2.3.4.17.1.7
		topOnuCapSetCatvPortNum OBJECT-TYPE
			SYNTAX INTEGER (0..24)
			MAX-ACCESS read-create
			STATUS current
			DESCRIPTION
				"Description."
			::= { topOnuCapabilitySetEntry 7 }

		
		-- 1.3.6.1.4.1.32285.11.2.3.4.17.1.8
		topOnuCapSetUartPortNum OBJECT-TYPE
			SYNTAX INTEGER (0..24)
			MAX-ACCESS read-create
			STATUS current
			DESCRIPTION
				"Description."
			::= { topOnuCapabilitySetEntry 8 }

		
		-- 1.3.6.1.4.1.32285.11.2.3.4.17.1.9
		topOnuCapSetRowstatus OBJECT-TYPE
			SYNTAX RowStatus
			MAX-ACCESS read-create
			STATUS current
			DESCRIPTION
				"Description."
			::= { topOnuCapabilitySetEntry 9 }

		-- 1.3.6.1.4.1.32285.11.2.3.4.18
		topOnuQueueSetThrObjects OBJECT IDENTIFIER ::= { topOnuObjects 18 }

		
		-- 1.3.6.1.4.1.32285.11.2.3.4.18.1
		topOnuQueueSetThrTable OBJECT-TYPE
			SYNTAX SEQUENCE OF TopOnuQueueSetThrEntry
			MAX-ACCESS not-accessible
			STATUS current
			DESCRIPTION
				"Onu queue set threshold table."
			::= { topOnuQueueSetThrObjects 1 }

		
		-- 1.3.6.1.4.1.32285.11.2.3.4.18.1.1
		topOnuQueueSetThrEntry OBJECT-TYPE
			SYNTAX TopOnuQueueSetThrEntry
			MAX-ACCESS not-accessible
			STATUS current
			DESCRIPTION
				"Description."
			INDEX { topOnuQueueSetThrCardIndex, topOnuQueueSetThrPonIndex, topOnuQueueSetThrOnuIndex, topOnuQueueSetThrIndex }
			::= { topOnuQueueSetThrTable 1 }

		
				TopOnuQueueSetThrEntry ::=
			SEQUENCE { 
				topOnuQueueSetThrCardIndex
					INTEGER,
				topOnuQueueSetThrPonIndex
					INTEGER,
				topOnuQueueSetThrOnuIndex
					INTEGER,
				topOnuQueueSetThrIndex
					INTEGER,
				topOnuQueueSetThrQueueList
					OCTET STRING,
				topOnuQueueSetThrRowStatus
					RowStatus
			 }


		-- 1.3.6.1.4.1.32285.11.2.3.4.18.1.1.1
		topOnuQueueSetThrCardIndex OBJECT-TYPE
			SYNTAX INTEGER
			MAX-ACCESS not-accessible
			STATUS current
			DESCRIPTION
				"slot."
			::= { topOnuQueueSetThrEntry 1 }

		
		-- 1.3.6.1.4.1.32285.11.2.3.4.18.1.1.2
		topOnuQueueSetThrPonIndex OBJECT-TYPE
			SYNTAX INTEGER
			MAX-ACCESS not-accessible
			STATUS current
			DESCRIPTION
				"Port."
			::= { topOnuQueueSetThrEntry 2 }

		
		-- 1.3.6.1.4.1.32285.11.2.3.4.18.1.1.3
		topOnuQueueSetThrOnuIndex OBJECT-TYPE
			SYNTAX INTEGER
			MAX-ACCESS not-accessible
			STATUS current
			DESCRIPTION
				"Onu."
			::= { topOnuQueueSetThrEntry 3 }

		
		-- 1.3.6.1.4.1.32285.11.2.3.4.18.1.1.4
		topOnuQueueSetThrIndex OBJECT-TYPE
			SYNTAX INTEGER (1..3)
			MAX-ACCESS not-accessible
			STATUS current
			DESCRIPTION
				"Queue set index(1 to 3)."
			::= { topOnuQueueSetThrEntry 4 }

		
		-- 1.3.6.1.4.1.32285.11.2.3.4.18.1.1.5
			topOnuQueueSetThrQueueList OBJECT-TYPE
			SYNTAX OCTET STRING (SIZE (1..384))
			MAX-ACCESS read-write
			STATUS current
			DESCRIPTION
				"Onu queue set threshold,every 6 bytes as a group,the first two bytes is queue number,and the last four bytes is queue threshold(0-0xffff)."
			::= { topOnuQueueSetThrEntry 5 }


		
		-- 1.3.6.1.4.1.32285.11.2.3.4.18.1.1.6
		topOnuQueueSetThrRowStatus OBJECT-TYPE
			SYNTAX RowStatus
			MAX-ACCESS read-create
			STATUS current
			DESCRIPTION
				"Rowstatus."
			::= { topOnuQueueSetThrEntry 6 }

		

		-- 1.3.6.1.4.1.32285.11.2.3.5
		topUniObjects OBJECT IDENTIFIER ::= { topvisionEponTree 5 }

		
		-- 1.3.6.1.4.1.32285.11.2.3.5.1
		topUniAttrTable OBJECT-TYPE
			SYNTAX SEQUENCE OF TopUniAttrEntry
			MAX-ACCESS not-accessible
			STATUS current
			DESCRIPTION
				"A list of topUniAttrTable entries."
			::= { topUniObjects 1 }

		
		-- 1.3.6.1.4.1.32285.11.2.3.5.1.1
		topUniAttrEntry OBJECT-TYPE
			SYNTAX TopUniAttrEntry
			MAX-ACCESS not-accessible
			STATUS current
			DESCRIPTION
				"The topUniAttrEntry Information"
			INDEX { topUniAttrCardIndex, topUniAttrPonIndex, topUniAttrOnuIndex, topUniAttrPortIndex }
			::= { topUniAttrTable 1 }

		
		TopUniAttrEntry ::=
			SEQUENCE { 
				topUniAttrCardIndex
					TopEPonSlotIndex,
				topUniAttrPonIndex
					TopEPonPonIndex,
				topUniAttrOnuIndex
					TopEPonOnuAuthNum,
				topUniAttrPortIndex
					TopEPonUniPortIndex,
				topUniAttrFlowCtrl
					INTEGER,
				topUniDSLoopBackEnable
					INTEGER,
				topUniUSUtgPri
					INTEGER,
				topUniAttrPerfStats15minuteEnable
					INTEGER,
				topUniAttrPerfStats24hourEnable
					INTEGER,
				topUniAttrLastChangeTime
					TimeTicks,
				topUniAttrIsolationEnable
					INTEGER,
				topUniAttrMacAddrLearnMaxNum
					INTEGER,
				topUniAttrAutoNegotiationAdvertisedTechAbility
					BITS,
				topUniAttrMacAddrClearByPort
					INTEGER,
        topUniAttrMacAge
					INTEGER,
				topUniLoopDetectEnable
					INTEGER,
				topUniName
					OCTET STRING
			 }

		-- 1.3.6.1.4.1.32285.11.2.3.5.1.1.1
		topUniAttrCardIndex OBJECT-TYPE
			SYNTAX TopEPonSlotIndex
			MAX-ACCESS not-accessible
			STATUS current
			DESCRIPTION
				"Card Index
				The value of this cardIndex depends on onuType.
				fixed(1) - set to 0, to indicate slot num is meaningless.
				chassisBased(2) - MUST NOT be zero
				"
			::= { topUniAttrEntry 1 }

		
		-- 1.3.6.1.4.1.32285.11.2.3.5.1.1.2
		topUniAttrPonIndex OBJECT-TYPE
			SYNTAX TopEPonPonIndex
			MAX-ACCESS not-accessible
			STATUS current
			DESCRIPTION
				"Pon index"
			::= { topUniAttrEntry 2 }

		
		-- 1.3.6.1.4.1.32285.11.2.3.5.1.1.3
		topUniAttrOnuIndex OBJECT-TYPE
			SYNTAX TopEPonOnuAuthNum
			MAX-ACCESS not-accessible
			STATUS current
			DESCRIPTION
				"Pon index"
			::= { topUniAttrEntry 3 }

		
		-- 1.3.6.1.4.1.32285.11.2.3.5.1.1.4
		topUniAttrPortIndex OBJECT-TYPE
			SYNTAX TopEPonUniPortIndex
			MAX-ACCESS not-accessible
			STATUS current
			DESCRIPTION
				"Port Index"
			::= { topUniAttrEntry 4 }

		
		-- 1.3.6.1.4.1.32285.11.2.3.5.1.1.5
		topUniAttrFlowCtrl OBJECT-TYPE
			SYNTAX INTEGER
				{
				enable(1),
				disable(2)
				}
			MAX-ACCESS read-write
			STATUS current
			DESCRIPTION
				"Port Index"
			DEFVAL { 2 }
			::= { topUniAttrEntry 5 }

		
		-- 1.3.6.1.4.1.32285.11.2.3.5.1.1.6
		topUniDSLoopBackEnable OBJECT-TYPE
			SYNTAX INTEGER
				{
				enable(1),
				disable(2)
				}
			MAX-ACCESS read-write
			STATUS current
			DESCRIPTION
				"Set the loopBack enable mode of uni port Downstream."
			::= { topUniAttrEntry 6 }
		-- 1.3.6.1.4.1.32285.11.2.3.5.1.1.7
		topUniUSUtgPri OBJECT-TYPE
			SYNTAX INTEGER
				{
				pri0(0),
				pri1(1),
				pri2(2),
				pri3(3),
				pri4(4),
				pri5(5),
				pri6(6),
				pri7(7),
				nopri(255)
				}
			MAX-ACCESS read-write
			STATUS current
			DESCRIPTION
				"Set the priority of uni port upStream , 
				when priority's value is equal as 255,means no priority set,
				 pri0 is the highest priority and pri7 is the lowest priority ."
			::= { topUniAttrEntry 7 }
		-- 1.3.6.1.4.1.32285.11.2.3.5.1.1.8
		topUniAttrPerfStats15minuteEnable OBJECT-TYPE
			SYNTAX INTEGER
				{
				true(1),
				false(2)
				}
			MAX-ACCESS read-write
			STATUS current
			DESCRIPTION
				"Description."
			DEFVAL { 2 }
			::= { topUniAttrEntry 8 }

		
		-- 1.3.6.1.4.1.32285.11.2.3.5.1.1.9
		topUniAttrPerfStats24hourEnable OBJECT-TYPE
			SYNTAX INTEGER
				{
				true(1),
				false(2)
				}
			MAX-ACCESS read-write
			STATUS current
			DESCRIPTION
				"Description."
			DEFVAL { 2 }
			::= { topUniAttrEntry 9 }

		
		-- 1.3.6.1.4.1.32285.11.2.3.5.1.1.10
		topUniAttrLastChangeTime OBJECT-TYPE
			SYNTAX TimeTicks
			MAX-ACCESS read-only
			STATUS current
			DESCRIPTION
				"Description."
			::= { topUniAttrEntry 10 }

		
		-- 1.3.6.1.4.1.32285.11.2.3.5.1.1.11
		topUniAttrIsolationEnable OBJECT-TYPE
			SYNTAX INTEGER
				{
				true(1),
				false(2)
				}
			MAX-ACCESS read-write
			STATUS current
			DESCRIPTION
				"Description."
			::= { topUniAttrEntry 11 }

		
		-- 1.3.6.1.4.1.32285.11.2.3.5.1.1.12
		topUniAttrMacAddrLearnMaxNum OBJECT-TYPE
			SYNTAX INTEGER
			MAX-ACCESS read-write
			STATUS current
			DESCRIPTION
				"Description."
			DEFVAL { ''b }
			::= { topUniAttrEntry 12 }

		
		-- 1.3.6.1.4.1.32285.11.2.3.5.1.1.13
		topUniAttrAutoNegotiationAdvertisedTechAbility OBJECT-TYPE
			SYNTAX BITS
				{
				oneBaseTHalfDuplex(0),
				tenBaseTFullDuplex(1),
				tenBaseTHalfDuplex(2),
				hundredBaseTFullDuplex(3),
				hundredBaseTHalfDuplex(4),
				thousandBaseTFullDuplex(5),
				thousandBaseTHalfDuplex(6),
				thousandBaseXFullDuplex(7),
				thousandBaseXHalfDuplex(8),
				fdxPause(9),
				fdxApause(10),
				fdxSpause(11),
				fdxBpause(12)
				}
			MAX-ACCESS read-write
			STATUS current
			DESCRIPTION
				"Description."
			::= { topUniAttrEntry 13 }

		
		-- 1.3.6.1.4.1.32285.11.2.3.5.1.1.12
		topUniAttrMacAddrClearByPort OBJECT-TYPE
			SYNTAX INTEGER { clearDynamic(1) }
			MAX-ACCESS read-write
			STATUS current
			DESCRIPTION
				"Description."
			::= { topUniAttrEntry 14 }

        -- 1.3.6.1.4.1.32285.11.2.3.5.1.1.15
		topUniAttrMacAge OBJECT-TYPE
			SYNTAX INTEGER 
			MAX-ACCESS read-write
			STATUS current
			DESCRIPTION
				"Mac Address Table Aging Time"
			::= { topUniAttrEntry 15 }
		
		-- 1.3.6.1.4.1.32285.11.2.3.5.1.1.16
		topUniLoopDetectEnable OBJECT-TYPE
			SYNTAX INTEGER
				{
				enable(1),
				disable(2)
				}
			MAX-ACCESS read-write
			STATUS current
			DESCRIPTION
				"Set the loopDetect enable mode of uni port."
			::= { topUniAttrEntry 16 }
			
		-- 1.3.6.1.4.1.32285.11.2.3.5.1.1.17
		topUniName OBJECT-TYPE
			SYNTAX OCTET STRING (SIZE (1..63))
			MAX-ACCESS read-write
			STATUS current
			DESCRIPTION
				"Uni port-name."
			::= { topUniAttrEntry 17 }


		-- 1.3.6.1.4.1.32285.11.2.3.5.2
		topUniBroadcastStormSuppressionTable OBJECT-TYPE
			SYNTAX SEQUENCE OF TopUniBroadcastStormSuppressionEntry
			MAX-ACCESS not-accessible
			STATUS current
			DESCRIPTION
				"Description."
			::= { topUniObjects 2 }

		
		-- 1.3.6.1.4.1.32285.11.2.3.5.2.1
		topUniBroadcastStormSuppressionEntry OBJECT-TYPE
			SYNTAX TopUniBroadcastStormSuppressionEntry
			MAX-ACCESS not-accessible
			STATUS current
			DESCRIPTION
				"Description."
			INDEX { topUniBroadcastStormSuppressionCardIndex, topUniBroadcastStormSuppressionPonIndex, topUniBroadcastStormSuppressionOnuIndex, topUniBroadcastStormSuppressionPortIndex }
			::= { topUniBroadcastStormSuppressionTable 1 }

		
		TopUniBroadcastStormSuppressionEntry ::=
			SEQUENCE { 
				topUniBroadcastStormSuppressionCardIndex
					TopEPonSlotIndex,
				topUniBroadcastStormSuppressionPonIndex
					TopEPonPonIndex,
				topUniBroadcastStormSuppressionOnuIndex
					TopEPonOnuAuthNum,
				topUniBroadcastStormSuppressionPortIndex
					TopEPonUniPortIndex,
				topUniUnicastStormEnable
					INTEGER,
				topUniUnicastStormInPacketRate
					INTEGER,
				topUniUnicastStormOutPacketRate
					INTEGER,
				topUniMulticastStormEnable
					INTEGER,
				topUniMulticastStormInPacketRate
					INTEGER,
				topUniMulticastStormOutPacketRate
					INTEGER,
				topUniBroadcastStormEnable
					INTEGER,
				topUniBroadcastStormInPacketRate
					INTEGER,
				topUniBroadcastStormOutPacketRate
					INTEGER
			 }

		-- 1.3.6.1.4.1.32285.11.2.3.5.2.1.1
		topUniBroadcastStormSuppressionCardIndex OBJECT-TYPE
			SYNTAX TopEPonSlotIndex
			MAX-ACCESS not-accessible
			STATUS current
			DESCRIPTION
				"Card Index
				The value of this cardIndex depends on onuType.
				fixed(1) - set to 0, to indicate slot num is meaningless.
				chassisBased(2) - MUST NOT be zero
				"
			::= { topUniBroadcastStormSuppressionEntry 1 }

		
		-- 1.3.6.1.4.1.32285.11.2.3.5.2.1.2
		topUniBroadcastStormSuppressionPonIndex OBJECT-TYPE
			SYNTAX TopEPonPonIndex
			MAX-ACCESS not-accessible
			STATUS current
			DESCRIPTION
				"Pon index"
			::= { topUniBroadcastStormSuppressionEntry 2 }

		
		-- 1.3.6.1.4.1.32285.11.2.3.5.2.1.3
		topUniBroadcastStormSuppressionOnuIndex OBJECT-TYPE
			SYNTAX TopEPonOnuAuthNum
			MAX-ACCESS not-accessible
			STATUS current
			DESCRIPTION
				"Pon index"
			::= { topUniBroadcastStormSuppressionEntry 3 }

		
		-- 1.3.6.1.4.1.32285.11.2.3.5.2.1.4
		topUniBroadcastStormSuppressionPortIndex OBJECT-TYPE
			SYNTAX TopEPonUniPortIndex
			MAX-ACCESS not-accessible
			STATUS current
			DESCRIPTION
				"Port Index"
			::= { topUniBroadcastStormSuppressionEntry 4 }

		
		-- 1.3.6.1.4.1.32285.11.2.3.5.2.1.5
		topUniUnicastStormEnable OBJECT-TYPE
			SYNTAX INTEGER
				{
				true(1),
				false(2)
				}
			MAX-ACCESS read-write
			STATUS current
			DESCRIPTION
				"Description."
			::= { topUniBroadcastStormSuppressionEntry 5 }

		
		-- 1.3.6.1.4.1.32285.11.2.3.5.2.1.6
		topUniUnicastStormInPacketRate OBJECT-TYPE
			SYNTAX INTEGER
			MAX-ACCESS read-write
			STATUS current
			DESCRIPTION
				"Description."
			::= { topUniBroadcastStormSuppressionEntry 6 }

		
		-- 1.3.6.1.4.1.32285.11.2.3.5.2.1.7
		topUniUnicastStormOutPacketRate OBJECT-TYPE
			SYNTAX INTEGER
			MAX-ACCESS read-write
			STATUS current
			DESCRIPTION
				"Description."
			::= { topUniBroadcastStormSuppressionEntry 7 }

		
		-- 1.3.6.1.4.1.32285.11.2.3.5.2.1.8
		topUniMulticastStormEnable OBJECT-TYPE
			SYNTAX INTEGER
				{
				true(1),
				false(2)
				}
			MAX-ACCESS read-write
			STATUS current
			DESCRIPTION
				"Description."
			::= { topUniBroadcastStormSuppressionEntry 8 }

		
		-- 1.3.6.1.4.1.32285.11.2.3.5.2.1.9
		topUniMulticastStormInPacketRate OBJECT-TYPE
			SYNTAX INTEGER
			MAX-ACCESS read-write
			STATUS current
			DESCRIPTION
				"Description."
			::= { topUniBroadcastStormSuppressionEntry 9 }

		
		-- 1.3.6.1.4.1.32285.11.2.3.5.2.1.10
		topUniMulticastStormOutPacketRate OBJECT-TYPE
			SYNTAX INTEGER
			MAX-ACCESS read-write
			STATUS current
			DESCRIPTION
				"Description."
			::= { topUniBroadcastStormSuppressionEntry 10 }

		
		-- 1.3.6.1.4.1.32285.11.2.3.5.2.1.11
		topUniBroadcastStormEnable OBJECT-TYPE
			SYNTAX INTEGER
				{
				true(1),
				false(2)
				}
			MAX-ACCESS read-write
			STATUS current
			DESCRIPTION
				"Description."
			::= { topUniBroadcastStormSuppressionEntry 11 }

		
		-- 1.3.6.1.4.1.32285.11.2.3.5.2.1.12
		topUniBroadcastStormInPacketRate OBJECT-TYPE
			SYNTAX INTEGER
			MAX-ACCESS read-write
			STATUS current
			DESCRIPTION
				"Description."
			::= { topUniBroadcastStormSuppressionEntry 12 }

		
		-- 1.3.6.1.4.1.32285.11.2.3.5.2.1.13
		topUniBroadcastStormOutPacketRate OBJECT-TYPE
			SYNTAX INTEGER
			MAX-ACCESS read-write
			STATUS current
			DESCRIPTION
				"Description."
			::= { topUniBroadcastStormSuppressionEntry 13 }

		
		-- 1.3.6.1.4.1.32285.11.2.3.5.3
		topUniManageObject OBJECT IDENTIFIER ::= { topUniObjects 3 }

		
		-- 1.3.6.1.4.1.32285.11.2.3.5.3.1
		topUniFilterCfgTable OBJECT-TYPE
			SYNTAX SEQUENCE OF TopUniFilterCfgEntry
			MAX-ACCESS not-accessible
			STATUS current
			DESCRIPTION
				"Description."
			::= { topUniManageObject 1 }

		
		-- 1.3.6.1.4.1.32285.11.2.3.5.3.1.1
		topUniFilterCfgEntry OBJECT-TYPE
			SYNTAX TopUniFilterCfgEntry
			MAX-ACCESS not-accessible
			STATUS current
			DESCRIPTION
				"Description."
			INDEX { topUniFiltSlotIndex, topUniFiltPortIndex, topUniFiltOnuIndex, topUniFiltIdIndex
				 }
			::= { topUniFilterCfgTable 1 }

		
		TopUniFilterCfgEntry ::=
			SEQUENCE { 
				topUniFiltSlotIndex
					TopEPonSlotIndex,
				topUniFiltPortIndex
					TopEPonPonIndex,
				topUniFiltOnuIndex
					TopEPonOnuAuthNum,
				topUniFiltIdIndex
					INTEGER,
				topUniFiltMac
					MacAddress,
				topUniFiltIp
					IpAddress,
				topUniFiltRowstatus
					RowStatus
			 }

		-- 1.3.6.1.4.1.32285.11.2.3.5.3.1.1.1
		topUniFiltSlotIndex OBJECT-TYPE
			SYNTAX TopEPonSlotIndex
			MAX-ACCESS not-accessible
			STATUS current
			DESCRIPTION
				"Description."
			::= { topUniFilterCfgEntry 1 }

		
		-- 1.3.6.1.4.1.32285.11.2.3.5.3.1.1.2
		topUniFiltPortIndex OBJECT-TYPE
			SYNTAX TopEPonPonIndex
			MAX-ACCESS not-accessible
			STATUS current
			DESCRIPTION
				"Description."
			::= { topUniFilterCfgEntry 2 }

		
		-- 1.3.6.1.4.1.32285.11.2.3.5.3.1.1.3
		topUniFiltOnuIndex OBJECT-TYPE
			SYNTAX TopEPonOnuAuthNum
			MAX-ACCESS not-accessible
			STATUS current
			DESCRIPTION
				"Description."
			::= { topUniFilterCfgEntry 3 }

		
		-- 1.3.6.1.4.1.32285.11.2.3.5.3.1.1.4
		topUniFiltIdIndex OBJECT-TYPE
			SYNTAX INTEGER (1..4)
			MAX-ACCESS not-accessible
			STATUS current
			DESCRIPTION
				"Description."
			::= { topUniFilterCfgEntry 4 }

		
		-- 1.3.6.1.4.1.32285.11.2.3.5.3.1.1.5
		topUniFiltMac OBJECT-TYPE
			SYNTAX MacAddress 
			MAX-ACCESS read-write
			STATUS current
			DESCRIPTION
				"Description."
			::= { topUniFilterCfgEntry 5 }

		
		-- 1.3.6.1.4.1.32285.11.2.3.5.3.1.1.6
		topUniFiltIp OBJECT-TYPE
			SYNTAX IpAddress
			MAX-ACCESS read-write
			STATUS current
			DESCRIPTION
				"Description."
			::= { topUniFilterCfgEntry 6 }

		
		-- 1.3.6.1.4.1.32285.11.2.3.5.3.1.1.7
		topUniFiltRowstatus OBJECT-TYPE
			SYNTAX RowStatus
			MAX-ACCESS read-create
			STATUS current
			DESCRIPTION
				"Description."
			::= { topUniFilterCfgEntry 7 }

		
		-- 1.3.6.1.4.1.32285.11.2.3.5.3.2
		topUniDevInfoTable OBJECT-TYPE
			SYNTAX SEQUENCE OF TopUniDevInfoEntry
			MAX-ACCESS not-accessible
			STATUS current
			DESCRIPTION
				"Description."
			::= { topUniManageObject 2 }

		
		-- 1.3.6.1.4.1.32285.11.2.3.5.3.2.1
		topUniDevInfoEntry OBJECT-TYPE
			SYNTAX TopUniDevInfoEntry
			MAX-ACCESS not-accessible
			STATUS current
			DESCRIPTION
				"Description."
			INDEX { topUniDevInfoSlotIndex, topUniDevInfoPortIndex, topUniDevInfoOnuIndex, topUniDevInfoIdIndex
				 }
			::= { topUniDevInfoTable 1 }

		
		TopUniDevInfoEntry ::=
			SEQUENCE { 
				topUniDevInfoSlotIndex
					TopEPonSlotIndex,
				topUniDevInfoPortIndex
					TopEPonPonIndex,
				topUniDevInfoOnuIndex
					TopEPonOnuAuthNum,
				topUniDevInfoIdIndex
					INTEGER,
				topUniDevInfoMac
					MacAddress,
				topUniDevInfoIp
					INTEGER,
				topUniDevInfoOperStat
					INTEGER,
				topUniDevInfoPresStat
					INTEGER
			 }

		-- 1.3.6.1.4.1.32285.11.2.3.5.3.2.1.1
		topUniDevInfoSlotIndex OBJECT-TYPE
			SYNTAX TopEPonSlotIndex
			MAX-ACCESS not-accessible
			STATUS current
			DESCRIPTION
				"Description."
			::= { topUniDevInfoEntry 1 }

		
		-- 1.3.6.1.4.1.32285.11.2.3.5.3.2.1.2
		topUniDevInfoPortIndex OBJECT-TYPE
			SYNTAX TopEPonPonIndex
			MAX-ACCESS not-accessible
			STATUS current
			DESCRIPTION
				"Description."
			::= { topUniDevInfoEntry 2 }

		
		-- 1.3.6.1.4.1.32285.11.2.3.5.3.2.1.3
		topUniDevInfoOnuIndex OBJECT-TYPE
			SYNTAX TopEPonOnuAuthNum
			MAX-ACCESS not-accessible
			STATUS current
			DESCRIPTION
				"Description."
			::= { topUniDevInfoEntry 3 }

		
		-- 1.3.6.1.4.1.32285.11.2.3.5.3.2.1.4
		topUniDevInfoIdIndex OBJECT-TYPE
			SYNTAX INTEGER
			MAX-ACCESS not-accessible
			STATUS current
			DESCRIPTION
				"Description."
			::= { topUniDevInfoEntry 4 }

		
		-- 1.3.6.1.4.1.32285.11.2.3.5.3.2.1.5
		topUniDevInfoMac OBJECT-TYPE
			SYNTAX MacAddress
			MAX-ACCESS read-only
			STATUS current
			DESCRIPTION
				"Description."
			::= { topUniDevInfoEntry 5 }

		
		-- 1.3.6.1.4.1.32285.11.2.3.5.3.2.1.6
		topUniDevInfoIp OBJECT-TYPE
			SYNTAX INTEGER
			MAX-ACCESS read-only
			STATUS current
			DESCRIPTION
				"Description."
			::= { topUniDevInfoEntry 6 }

		
		-- 1.3.6.1.4.1.32285.11.2.3.5.3.2.1.7
		topUniDevInfoOperStat OBJECT-TYPE
			SYNTAX INTEGER
			MAX-ACCESS read-only
			STATUS current
			DESCRIPTION
				"Description."
			::= { topUniDevInfoEntry 7 }

		
		-- 1.3.6.1.4.1.32285.11.2.3.5.3.2.1.8
		topUniDevInfoPresStat OBJECT-TYPE
			SYNTAX INTEGER
			MAX-ACCESS read-only
			STATUS current
			DESCRIPTION
				"Description."
			::= { topUniDevInfoEntry 8 }

		
		-- 1.3.6.1.4.1.32285.11.2.3.5.4
		topUniMacAddressObjects OBJECT IDENTIFIER ::= { topUniObjects 4 }

		
		-- 1.3.6.1.4.1.32285.11.2.3.5.4.1
		topUniMacCfgTable OBJECT-TYPE
			SYNTAX SEQUENCE OF TopUniMacCfgEntry
			MAX-ACCESS not-accessible
			STATUS current
			DESCRIPTION
				"Description."
			::= { topUniMacAddressObjects 1 }

		
		-- 1.3.6.1.4.1.32285.11.2.3.5.4.1.1
		topUniMacCfgEntry OBJECT-TYPE
			SYNTAX TopUniMacCfgEntry
			MAX-ACCESS not-accessible
			STATUS current
			DESCRIPTION
				"Description."
			INDEX { topUniMacCfgSlotIndex, topUniMacCfgPortIndex, topUniMacCfgOnuIndex, topUniMacCfgUniIndex }
			::= { topUniMacCfgTable 1 }

		
		TopUniMacCfgEntry ::=
			SEQUENCE { 
				topUniMacCfgSlotIndex
					TopEPonSlotIndex,
				topUniMacCfgPortIndex
					TopEPonPonIndex,
				topUniMacCfgOnuIndex
					TopEPonOnuAuthNum,
				topUniMacCfgUniIndex
					TopEPonUniPortIndex,
				topUniMacCfg
					OCTET STRING,
				topUniMacCfgSetFlag
					INTEGER,
				topUniMacCfgTotal
					OCTET STRING
			 }

		-- 1.3.6.1.4.1.32285.11.2.3.5.4.1.1.1
		topUniMacCfgSlotIndex OBJECT-TYPE
			SYNTAX TopEPonSlotIndex
			MAX-ACCESS not-accessible
			STATUS current
			DESCRIPTION
				"Description."
			::= { topUniMacCfgEntry 1 }

		
		-- 1.3.6.1.4.1.32285.11.2.3.5.4.1.1.2
		topUniMacCfgPortIndex OBJECT-TYPE
			SYNTAX TopEPonPonIndex
			MAX-ACCESS not-accessible
			STATUS current
			DESCRIPTION
				"Description."
			::= { topUniMacCfgEntry 2 }

		
		-- 1.3.6.1.4.1.32285.11.2.3.5.4.1.1.3
		topUniMacCfgOnuIndex OBJECT-TYPE
			SYNTAX TopEPonOnuAuthNum
			MAX-ACCESS not-accessible
			STATUS current
			DESCRIPTION
				"Description."
			::= { topUniMacCfgEntry 3 }

		
		-- 1.3.6.1.4.1.32285.11.2.3.5.4.1.1.4
		topUniMacCfgUniIndex OBJECT-TYPE
			SYNTAX TopEPonUniPortIndex
			MAX-ACCESS not-accessible
			STATUS current
			DESCRIPTION
				"Description."
			::= { topUniMacCfgEntry 4 }

		
		-- 1.3.6.1.4.1.32285.11.2.3.5.4.1.1.5
		topUniMacCfg OBJECT-TYPE
			SYNTAX OCTET STRING (SIZE (12))
			MAX-ACCESS read-write
			STATUS current
			DESCRIPTION
				"Description."
			::= { topUniMacCfgEntry 5 }

		
		-- 1.3.6.1.4.1.32285.11.2.3.5.4.1.1.6
		topUniMacCfgSetFlag OBJECT-TYPE
			SYNTAX INTEGER
				{
				add(1),
				delete(2)
				}
			MAX-ACCESS read-write
			STATUS current
			DESCRIPTION
				"Description."
			::= { topUniMacCfgEntry 6 }

		
		-- 1.3.6.1.4.1.32285.11.2.3.5.4.1.1.7
		topUniMacCfgTotal OBJECT-TYPE
			SYNTAX OCTET STRING (SIZE (0..96))
			MAX-ACCESS read-only
			STATUS current
			DESCRIPTION
				"Description."
			::= { topUniMacCfgEntry 7 }

		
		-- 1.3.6.1.4.1.32285.11.2.3.5.4.2
		topUniMacInfoTable OBJECT-TYPE
			SYNTAX SEQUENCE OF TopUniMacInfoEntry
			MAX-ACCESS not-accessible
			STATUS current
			DESCRIPTION
				"Description."
			::= { topUniMacAddressObjects 2 }

		
		-- 1.3.6.1.4.1.32285.11.2.3.5.4.2.1
		topUniMacInfoEntry OBJECT-TYPE
			SYNTAX TopUniMacInfoEntry
			MAX-ACCESS not-accessible
			STATUS current
			DESCRIPTION
				"Description."
			INDEX { topUniMacInfoSlotIndex, topUniMacInfoPortIndex, topUniMacInfoOnuIndex, topUniMacInfoUniIndex }
			::= { topUniMacInfoTable 1 }

		
		TopUniMacInfoEntry ::=
			SEQUENCE { 
				topUniMacInfoSlotIndex
					TopEPonSlotIndex,
				topUniMacInfoPortIndex
					TopEPonPonIndex,
				topUniMacInfoOnuIndex
					TopEPonOnuAuthNum,
				topUniMacInfoUniIndex
					TopEPonUniPortIndex,
				topUniMacInfoTotal
					OCTET STRING
			 }

		-- 1.3.6.1.4.1.32285.11.2.3.5.4.2.1.1
		topUniMacInfoSlotIndex OBJECT-TYPE
			SYNTAX TopEPonSlotIndex
			MAX-ACCESS not-accessible
			STATUS current
			DESCRIPTION
				"Description."
			::= { topUniMacInfoEntry 1 }

		
		-- 1.3.6.1.4.1.32285.11.2.3.5.4.2.1.2
		topUniMacInfoPortIndex OBJECT-TYPE
			SYNTAX TopEPonPonIndex
			MAX-ACCESS not-accessible
			STATUS current
			DESCRIPTION
				"Description."
			::= { topUniMacInfoEntry 2 }

		
		-- 1.3.6.1.4.1.32285.11.2.3.5.4.2.1.3
		topUniMacInfoOnuIndex OBJECT-TYPE
			SYNTAX TopEPonOnuAuthNum
			MAX-ACCESS not-accessible
			STATUS current
			DESCRIPTION
				"Description."
			::= { topUniMacInfoEntry 3 }

		
		-- 1.3.6.1.4.1.32285.11.2.3.5.4.2.1.4
		topUniMacInfoUniIndex OBJECT-TYPE
			SYNTAX TopEPonUniPortIndex
			MAX-ACCESS not-accessible
			STATUS current
			DESCRIPTION
				"Description."
			::= { topUniMacInfoEntry 4 }

		
		-- 1.3.6.1.4.1.32285.11.2.3.5.4.2.1.5
		topUniMacInfoTotal OBJECT-TYPE
			SYNTAX OCTET STRING (SIZE (0..768))
			MAX-ACCESS read-only
			STATUS current
			DESCRIPTION
				"Description."
			::= { topUniMacInfoEntry 5 }

		
		-- 1.3.6.1.4.1.32285.11.2.3.5.5
		topUniMirrorObjects OBJECT IDENTIFIER ::= { topUniObjects 5 }

		
		-- 1.3.6.1.4.1.32285.11.2.3.5.5.1
		topUniMirrorTable OBJECT-TYPE
			SYNTAX SEQUENCE OF TopUniMirrorEntry
			MAX-ACCESS not-accessible
			STATUS current
			DESCRIPTION
				"Description."
			::= { topUniMirrorObjects 1 }

		
		-- 1.3.6.1.4.1.32285.11.2.3.5.5.1.1
		topUniMirrorEntry OBJECT-TYPE
			SYNTAX TopUniMirrorEntry
			MAX-ACCESS not-accessible
			STATUS current
			DESCRIPTION
				"Description."
			INDEX { topUniMirrorSlotIndex, topUniMirrorPortIndex, topUniMirrorOnuIndex }
			::= { topUniMirrorTable 1 }

		
		TopUniMirrorEntry ::=
			SEQUENCE { 
				topUniMirrorSlotIndex
					TopEPonSlotIndex,
				topUniMirrorPortIndex
					TopEPonPonIndex,
				topUniMirrorOnuIndex
					TopEPonOnuAuthNum,
				topUniMirrorDesc
					OCTET STRING,
				topUniMirrorDstPort
					INTEGER,
				topUniMirrorSrcInPortList
					OCTET STRING,
				topUniMirrorSrcOutPortList
					OCTET STRING
			 }

		-- 1.3.6.1.4.1.32285.11.2.3.5.5.1.1.1
		topUniMirrorSlotIndex OBJECT-TYPE
			SYNTAX TopEPonSlotIndex
			MAX-ACCESS not-accessible
			STATUS current
			DESCRIPTION
				"Description."
			::= { topUniMirrorEntry 1 }

		
		-- 1.3.6.1.4.1.32285.11.2.3.5.5.1.1.2
		topUniMirrorPortIndex OBJECT-TYPE
			SYNTAX TopEPonPonIndex
			MAX-ACCESS not-accessible
			STATUS current
			DESCRIPTION
				"Description."
			::= { topUniMirrorEntry 2 }

		
		-- 1.3.6.1.4.1.32285.11.2.3.5.5.1.1.3
		topUniMirrorOnuIndex OBJECT-TYPE
			SYNTAX TopEPonOnuAuthNum
			MAX-ACCESS not-accessible
			STATUS current
			DESCRIPTION
				"Description."
			::= { topUniMirrorEntry 3 }

		
		-- 1.3.6.1.4.1.32285.11.2.3.5.5.1.1.4
		topUniMirrorDesc OBJECT-TYPE
			SYNTAX OCTET STRING (SIZE (0..31))
			MAX-ACCESS read-write
			STATUS current
			DESCRIPTION
				"Description."
			::= { topUniMirrorEntry 4 }

		
		-- 1.3.6.1.4.1.32285.11.2.3.5.5.1.1.5
		topUniMirrorDstPort OBJECT-TYPE
			SYNTAX INTEGER
			MAX-ACCESS read-write
			STATUS current
			DESCRIPTION
				"Description."
			::= { topUniMirrorEntry 5 }

		
		-- 1.3.6.1.4.1.32285.11.2.3.5.5.1.1.6
		topUniMirrorSrcInPortList OBJECT-TYPE
			SYNTAX OCTET STRING (SIZE (0..48))
			MAX-ACCESS read-write
			STATUS current
			DESCRIPTION
				"Description."
			::= { topUniMirrorEntry 6 }

		
		-- 1.3.6.1.4.1.32285.11.2.3.5.5.1.1.7
		topUniMirrorSrcOutPortList OBJECT-TYPE
			SYNTAX OCTET STRING (SIZE (0..48))
			MAX-ACCESS read-write
			STATUS current
			DESCRIPTION
				"Description."
			::= { topUniMirrorEntry 7 }

		
		-- 1.3.6.1.4.1.32285.11.2.3.5.6
		topUniTrunkMgmtObjects OBJECT IDENTIFIER ::= { topUniObjects 6 }

		
		-- 1.3.6.1.4.1.32285.11.2.3.5.6.1
		topUniTrunkConfigTable OBJECT-TYPE
			SYNTAX SEQUENCE OF TopUniTrunkConfigEntry
			MAX-ACCESS not-accessible
			STATUS current
			DESCRIPTION
				"Description."
			::= { topUniTrunkMgmtObjects 1 }

		
		-- 1.3.6.1.4.1.32285.11.2.3.5.6.1.1
		topUniTrunkConfigEntry OBJECT-TYPE
			SYNTAX TopUniTrunkConfigEntry
			MAX-ACCESS not-accessible
			STATUS current
			DESCRIPTION
				"Description."
			INDEX { topUniTrunkConfigSlotIndex, topUniTrunkConfigPortIndex, topUniTrunkConfigOnuIndex, topUniTrunkConfigIdIndex }
			::= { topUniTrunkConfigTable 1 }

		
		TopUniTrunkConfigEntry ::=
			SEQUENCE { 
				topUniTrunkConfigSlotIndex
					INTEGER,
				topUniTrunkConfigPortIndex
					INTEGER,
				topUniTrunkConfigOnuIndex
					INTEGER,
				topUniTrunkConfigIdIndex
					INTEGER,
				topUniTrunkConfigDesc
					OCTET STRING,
				topUniTrunkConfigMember
					OCTET STRING,
				topUniTrunkConfigPolicy
					INTEGER,
				topUniTrunkConfigAdminStatus
					INTEGER,
				topUniTrunkConfigRowstatus
					RowStatus
			 }

		-- 1.3.6.1.4.1.32285.11.2.3.5.6.1.1.1
		topUniTrunkConfigSlotIndex OBJECT-TYPE
			SYNTAX INTEGER
			MAX-ACCESS not-accessible
			STATUS current
			DESCRIPTION
				"Description."
			::= { topUniTrunkConfigEntry 1 }

		
		-- 1.3.6.1.4.1.32285.11.2.3.5.6.1.1.2
		topUniTrunkConfigPortIndex OBJECT-TYPE
			SYNTAX INTEGER
			MAX-ACCESS not-accessible
			STATUS current
			DESCRIPTION
				"Description."
			::= { topUniTrunkConfigEntry 2 }

		
		-- 1.3.6.1.4.1.32285.11.2.3.5.6.1.1.3
		topUniTrunkConfigOnuIndex OBJECT-TYPE
			SYNTAX INTEGER
			MAX-ACCESS not-accessible
			STATUS current
			DESCRIPTION
				"Description."
			::= { topUniTrunkConfigEntry 3 }

		
		-- 1.3.6.1.4.1.32285.11.2.3.5.6.1.1.4
		topUniTrunkConfigIdIndex OBJECT-TYPE
			SYNTAX INTEGER
			MAX-ACCESS not-accessible
			STATUS current
			DESCRIPTION
				"Description."
			::= { topUniTrunkConfigEntry 4 }

		
		-- 1.3.6.1.4.1.32285.11.2.3.5.6.1.1.5
		topUniTrunkConfigDesc OBJECT-TYPE
			SYNTAX OCTET STRING (SIZE (0..31))
			MAX-ACCESS read-write
			STATUS current
			DESCRIPTION
				"Description."
			::= { topUniTrunkConfigEntry 5 }

		
		-- 1.3.6.1.4.1.32285.11.2.3.5.6.1.1.6
		topUniTrunkConfigMember OBJECT-TYPE
			SYNTAX OCTET STRING (SIZE (48))
			MAX-ACCESS read-write
			STATUS current
			DESCRIPTION
				"Description."
			::= { topUniTrunkConfigEntry 6 }

		
		-- 1.3.6.1.4.1.32285.11.2.3.5.6.1.1.7
		topUniTrunkConfigPolicy OBJECT-TYPE
			SYNTAX INTEGER
				{
				srcMac(1),
				destMac(2),
				srcMacNDestMac(3),
				srcIp(4),
				destIp(5),
				srcIpNDestIp(6)
				}
			MAX-ACCESS read-write
			STATUS current
			DESCRIPTION
				"Description."
			::= { topUniTrunkConfigEntry 7 }

		
		-- 1.3.6.1.4.1.32285.11.2.3.5.6.1.1.8
		topUniTrunkConfigAdminStatus OBJECT-TYPE
			SYNTAX INTEGER
				{
				up(1),
				down(2)
				}
			MAX-ACCESS read-write
			STATUS current
			DESCRIPTION
				"Description."
			::= { topUniTrunkConfigEntry 8 }

		
		-- 1.3.6.1.4.1.32285.11.2.3.5.6.1.1.9
		topUniTrunkConfigRowstatus OBJECT-TYPE
			SYNTAX RowStatus
			MAX-ACCESS read-create
			STATUS current
			DESCRIPTION
				"Description."
			::= { topUniTrunkConfigEntry 9 }

		
		-- 1.3.6.1.4.1.32285.11.2.3.5.6.2
		topUniTrunkTable OBJECT-TYPE
			SYNTAX SEQUENCE OF TopUniTrunkEntry
			MAX-ACCESS not-accessible
			STATUS current
			DESCRIPTION
				"Description."
			::= { topUniTrunkMgmtObjects 2 }

		
		-- 1.3.6.1.4.1.32285.11.2.3.5.6.2.1
		topUniTrunkEntry OBJECT-TYPE
			SYNTAX TopUniTrunkEntry
			MAX-ACCESS not-accessible
			STATUS current
			DESCRIPTION
				"Description."
			INDEX { topUniTrunkSlotIndex, topUniTrunkPortIndex, topUniTrunkOnuIndex, topUniTrunkIdIndex }
			::= { topUniTrunkTable 1 }

		
		TopUniTrunkEntry ::=
			SEQUENCE { 
				topUniTrunkSlotIndex
					INTEGER,
				topUniTrunkPortIndex
					INTEGER,
				topUniTrunkOnuIndex
					INTEGER,
				topUniTrunkIdIndex
					INTEGER,
				topUniTrunkOperationStatus
					INTEGER,
				topUniTrunkActualSpeed
					INTEGER
			 }

		-- 1.3.6.1.4.1.32285.11.2.3.5.6.2.1.1
		topUniTrunkSlotIndex OBJECT-TYPE
			SYNTAX INTEGER
			MAX-ACCESS not-accessible
			STATUS current
			DESCRIPTION
				"Description."
			::= { topUniTrunkEntry 1 }

		
		-- 1.3.6.1.4.1.32285.11.2.3.5.6.2.1.2
		topUniTrunkPortIndex OBJECT-TYPE
			SYNTAX INTEGER
			MAX-ACCESS not-accessible
			STATUS current
			DESCRIPTION
				"Description."
			::= { topUniTrunkEntry 2 }

		
		-- 1.3.6.1.4.1.32285.11.2.3.5.6.2.1.3
		topUniTrunkOnuIndex OBJECT-TYPE
			SYNTAX INTEGER
			MAX-ACCESS not-accessible
			STATUS current
			DESCRIPTION
				"Description."
			::= { topUniTrunkEntry 3 }

		
		-- 1.3.6.1.4.1.32285.11.2.3.5.6.2.1.4
		topUniTrunkIdIndex OBJECT-TYPE
			SYNTAX INTEGER
			MAX-ACCESS not-accessible
			STATUS current
			DESCRIPTION
				"Description."
			::= { topUniTrunkEntry 4 }

		
		-- 1.3.6.1.4.1.32285.11.2.3.5.6.2.1.5
		topUniTrunkOperationStatus OBJECT-TYPE
			SYNTAX INTEGER
				{
				up(1),
				down(2)
				}
			MAX-ACCESS read-only
			STATUS current
			DESCRIPTION
				"Description."
			::= { topUniTrunkEntry 5 }

		
		-- 1.3.6.1.4.1.32285.11.2.3.5.6.2.1.6
		topUniTrunkActualSpeed OBJECT-TYPE
			SYNTAX INTEGER
			UNITS "Mbps"
			MAX-ACCESS read-only
			STATUS current
			DESCRIPTION
				"Description."
			::= { topUniTrunkEntry 6 }

		
		-- 1.3.6.1.4.1.32285.11.2.3.6
		topIgmpMgmtObjects OBJECT IDENTIFIER ::= { topvisionEponTree 6 }

		
		-- 1.3.6.1.4.1.32285.11.2.3.6.1
		topIgmpOltConfigMgmtObjects OBJECT IDENTIFIER ::= { topIgmpMgmtObjects 1 }

		
		-- 1.3.6.1.4.1.32285.11.2.3.6.1.1
		topIgmpParamObjects OBJECT IDENTIFIER ::= { topIgmpOltConfigMgmtObjects 1 }

		
		-- 1.3.6.1.4.1.32285.11.2.3.6.1.1.1
		topIgmpVersion OBJECT-TYPE
			SYNTAX INTEGER
				{
				v1(1),
				v2(2),
				v3Compatible(3),
				v3Only(4)
				}
			MAX-ACCESS read-write
			STATUS current
			DESCRIPTION
				"V1 is not support."
			DEFVAL { v3Compatible }
			::= { topIgmpParamObjects 1 }

		
		-- 1.3.6.1.4.1.32285.11.2.3.6.1.1.2
		topIgmpMode OBJECT-TYPE
			SYNTAX INTEGER
				{
				proxy(1),
				router(2),
				disable(3),
				snooping(4)
				}
			MAX-ACCESS read-write
			STATUS current
			DESCRIPTION
				"Description."
			DEFVAL { disable }
			::= { topIgmpParamObjects 2 }

		
		-- 1.3.6.1.4.1.32285.11.2.3.6.1.1.3
		topIgmpV3CompatV2Timeout OBJECT-TYPE
			SYNTAX INTEGER (1..5000)
			UNITS "second"
			MAX-ACCESS read-write
			STATUS current
			DESCRIPTION
				"Description."
			DEFVAL { 400 }
			::= { topIgmpParamObjects 3 }

		
		-- 1.3.6.1.4.1.32285.11.2.3.6.1.1.4
		topIgmpV3QueryRespTime OBJECT-TYPE
			SYNTAX INTEGER (1..31744)
			UNITS "tenth second"
			MAX-ACCESS read-write
			STATUS current
			DESCRIPTION
				"Description."
			DEFVAL { 100 }
			::= { topIgmpParamObjects 4 }

		
		-- 1.3.6.1.4.1.32285.11.2.3.6.1.1.5
		topIgmpV2QueryRespTime OBJECT-TYPE
			SYNTAX INTEGER (1..255)
			UNITS "tenth second"
			MAX-ACCESS read-write
			STATUS current
			DESCRIPTION
				"Description."
			DEFVAL { 100 }
			::= { topIgmpParamObjects 5 }

		
		-- 1.3.6.1.4.1.32285.11.2.3.6.1.1.6
		topIgmpQueryInterval OBJECT-TYPE
			SYNTAX INTEGER (30..5000)
			UNITS "second"
			MAX-ACCESS read-write
			STATUS current
			DESCRIPTION
				"Description."
			DEFVAL { 125 }
			::= { topIgmpParamObjects 6 }

		
		-- 1.3.6.1.4.1.32285.11.2.3.6.1.1.7
		topIgmpSqueryInterval OBJECT-TYPE
			SYNTAX INTEGER (2..50000)
			UNITS "tenth second"
			MAX-ACCESS read-write
			STATUS current
			DESCRIPTION
				"Description."
			DEFVAL { 10 }
			::= { topIgmpParamObjects 7 }

		
		-- 1.3.6.1.4.1.32285.11.2.3.6.1.1.8
		topIgmpSqueryNum OBJECT-TYPE
			SYNTAX INTEGER (1..10)
			MAX-ACCESS read-write
			STATUS current
			DESCRIPTION
				"Description."
			DEFVAL { 2 }
			::= { topIgmpParamObjects 8 }

		
		-- 1.3.6.1.4.1.32285.11.2.3.6.1.1.9
		topIgmpV3SqueryRespTime OBJECT-TYPE
			SYNTAX INTEGER (1..31744)
			UNITS "tenth second"
			MAX-ACCESS read-write
			STATUS current
			DESCRIPTION
				"Description."
			DEFVAL { 8 }
			::= { topIgmpParamObjects 9 }

		
		-- 1.3.6.1.4.1.32285.11.2.3.6.1.1.10
		topIgmpV2SqueryRespTime OBJECT-TYPE
			SYNTAX INTEGER (1..255)
			UNITS "tenth second"
			MAX-ACCESS read-write
			STATUS current
			DESCRIPTION
				"Description."
			DEFVAL { 8 }
			::= { topIgmpParamObjects 10 }

		
		-- 1.3.6.1.4.1.32285.11.2.3.6.1.1.11
		topIgmpRobustVariable OBJECT-TYPE
			SYNTAX INTEGER (1..10)
			MAX-ACCESS read-write
			STATUS current
			DESCRIPTION
				"Description."
			DEFVAL { 2 }
			::= { topIgmpParamObjects 11 }

		
		-- 1.3.6.1.4.1.32285.11.2.3.6.1.1.12
		topIgmpQuerySrcIp OBJECT-TYPE
			SYNTAX IpAddress
			MAX-ACCESS read-write
			STATUS current
			DESCRIPTION
				"Description."
			DEFVAL { 'c0a80101'h }
			::= { topIgmpParamObjects 12 }

		
		-- 1.3.6.1.4.1.32285.11.2.3.6.1.1.13
		topIgmpGlobalBW OBJECT-TYPE
			SYNTAX INTEGER (0..1000000)
			UNITS "kbps"
			MAX-ACCESS read-write
			STATUS current
			DESCRIPTION
				"Description."
			DEFVAL { 1000000 }
			::= { topIgmpParamObjects 13 }

		
		-- 1.3.6.1.4.1.32285.11.2.3.6.1.1.14
		topIgmpSnoopingAgingTime OBJECT-TYPE
			SYNTAX INTEGER (1..30)
			UNITS "minute"
			MAX-ACCESS read-write
			STATUS current
			DESCRIPTION
				"Description."
			DEFVAL { 30 }
			::= { topIgmpParamObjects 14 }

		
		-- 1.3.6.1.4.1.32285.11.2.3.6.1.2
		topIgmpCascadePortTable OBJECT-TYPE
			SYNTAX SEQUENCE OF TopIgmpCascadePortEntry
			MAX-ACCESS not-accessible
			STATUS current
			DESCRIPTION
				"Description."
			::= { topIgmpOltConfigMgmtObjects 2 }

		
		-- 1.3.6.1.4.1.32285.11.2.3.6.1.2.1
		topIgmpCascadePortEntry OBJECT-TYPE
			SYNTAX TopIgmpCascadePortEntry
			MAX-ACCESS not-accessible
			STATUS current
			DESCRIPTION
				"Description."
			INDEX { topIgmpCascadeTypeIndex, topIgmpCascadeSlotIndex, topIgmpCascadePortIndex }
			::= { topIgmpCascadePortTable 1 }

		
		TopIgmpCascadePortEntry ::=
			SEQUENCE { 
				topIgmpCascadeTypeIndex
					INTEGER,
				topIgmpCascadeSlotIndex
					INTEGER,
				topIgmpCascadePortIndex
					INTEGER,
				topIgmpCascadePortRowStatus 
					RowStatus
			 }

		-- 1.3.6.1.4.1.32285.11.2.3.6.1.2.1.1
		topIgmpCascadeTypeIndex OBJECT-TYPE
			SYNTAX INTEGER
				{
				ge(3),
				xe(4)
				}
			MAX-ACCESS not-accessible
			STATUS current
			DESCRIPTION
				"Description."
			::= { topIgmpCascadePortEntry 1 }

		
		-- 1.3.6.1.4.1.32285.11.2.3.6.1.2.1.2
		topIgmpCascadeSlotIndex OBJECT-TYPE
			SYNTAX INTEGER
			MAX-ACCESS not-accessible
			STATUS current
			DESCRIPTION
				"Description."
			::= { topIgmpCascadePortEntry 2 }

		
		-- 1.3.6.1.4.1.32285.11.2.3.6.1.2.1.3
		topIgmpCascadePortIndex OBJECT-TYPE
			SYNTAX INTEGER
			MAX-ACCESS not-accessible
			STATUS current
			DESCRIPTION
				"Description."
			::= { topIgmpCascadePortEntry 3 }

		
		-- 1.3.6.1.4.1.32285.11.2.3.6.1.2.1.4
		topIgmpCascadePortRowStatus  OBJECT-TYPE
			SYNTAX RowStatus
			MAX-ACCESS read-create
			STATUS current
			DESCRIPTION
				"Description."
			::= { topIgmpCascadePortEntry 4 }

		
		-- 1.3.6.1.4.1.32285.11.2.3.6.1.3
		topIgmpSnoopingObjects OBJECT IDENTIFIER ::= { topIgmpOltConfigMgmtObjects 3 }

		
		-- 1.3.6.1.4.1.32285.11.2.3.6.1.3.1
		topIgmpSnpUpLinkObjects OBJECT IDENTIFIER ::= { topIgmpSnoopingObjects 1 }

		
		-- 1.3.6.1.4.1.32285.11.2.3.6.1.3.1.1
		topIgmpSnpUpLinkType OBJECT-TYPE
			SYNTAX INTEGER
				{
				invalid(1),
				ge(3),
				xe(4),
				ethagg(9)
				}
			MAX-ACCESS read-write
			STATUS current
			DESCRIPTION
				"Description."
			::= { topIgmpSnpUpLinkObjects 1 }

		
		-- 1.3.6.1.4.1.32285.11.2.3.6.1.3.1.2
		topIgmpSnpUpLinkSlot OBJECT-TYPE
			SYNTAX INTEGER
			MAX-ACCESS read-write
			STATUS current
			DESCRIPTION
				"Description."
			::= { topIgmpSnpUpLinkObjects 2 }

		
		-- 1.3.6.1.4.1.32285.11.2.3.6.1.3.1.3
		topIgmpSnpUpLinkPort OBJECT-TYPE
			SYNTAX INTEGER
			MAX-ACCESS read-write
			STATUS current
			DESCRIPTION
				"Description."
			::= { topIgmpSnpUpLinkObjects 3 }

		
		-- 1.3.6.1.4.1.32285.11.2.3.6.1.3.1.4
		topIgmpSnpUpLinkAggId  OBJECT-TYPE
			SYNTAX INTEGER (0..32)
			MAX-ACCESS read-write
			STATUS current
			DESCRIPTION
				"Description."
			::= { topIgmpSnpUpLinkObjects 4 }

		
		-- 1.3.6.1.4.1.32285.11.2.3.6.1.3.2
		topIgmpSnpStaticFwdTable OBJECT-TYPE
			SYNTAX SEQUENCE OF TopIgmpSnpStaticFwdEntry
			MAX-ACCESS not-accessible
			STATUS current
			DESCRIPTION
				"Description."
			::= { topIgmpSnoopingObjects 2 }

		
		-- 1.3.6.1.4.1.32285.11.2.3.6.1.3.2.1
		topIgmpSnpStaticFwdEntry OBJECT-TYPE
			SYNTAX TopIgmpSnpStaticFwdEntry
			MAX-ACCESS not-accessible
			STATUS current
			DESCRIPTION
				"Description."
			INDEX { topIgmpSnpSGFwdTypeIndex, topIgmpSnpSGFwdSlotIndex, topIgmpSnpSGFwdPortIndex, topIgmpSnpSGFwdGrpIpIndex, topIgmpSnpSGFwdMvlanIndex, 
				topIgmpSnpSGFwdSrcIpIndex }
			::= { topIgmpSnpStaticFwdTable 1 }

		
		TopIgmpSnpStaticFwdEntry ::=
			SEQUENCE { 
				topIgmpSnpSGFwdTypeIndex
					INTEGER,
				topIgmpSnpSGFwdSlotIndex
					INTEGER,
				topIgmpSnpSGFwdPortIndex
					INTEGER,
				topIgmpSnpSGFwdGrpIpIndex
					IpAddress,
				topIgmpSnpSGFwdMvlanIndex
					INTEGER,
				topIgmpSnpSGFwdSrcIpIndex
					IpAddress,
				topIgmpSnpSGFwdRowStatus 
					RowStatus
			 }

		-- 1.3.6.1.4.1.32285.11.2.3.6.1.3.2.1.1
		topIgmpSnpSGFwdTypeIndex OBJECT-TYPE
			SYNTAX INTEGER
				{
				ge(3),
				xe(4),
				epon(5),
				epon10g(7)
				}
			MAX-ACCESS not-accessible
			STATUS current
			DESCRIPTION
				"Description."
			::= { topIgmpSnpStaticFwdEntry 1 }

		
		-- 1.3.6.1.4.1.32285.11.2.3.6.1.3.2.1.2
		topIgmpSnpSGFwdSlotIndex OBJECT-TYPE
			SYNTAX INTEGER
			MAX-ACCESS not-accessible
			STATUS current
			DESCRIPTION
				"Description."
			::= { topIgmpSnpStaticFwdEntry 2 }

		
		-- 1.3.6.1.4.1.32285.11.2.3.6.1.3.2.1.3
		topIgmpSnpSGFwdPortIndex OBJECT-TYPE
			SYNTAX INTEGER
			MAX-ACCESS not-accessible
			STATUS current
			DESCRIPTION
				"Description."
			::= { topIgmpSnpStaticFwdEntry 3 }

		
		-- 1.3.6.1.4.1.32285.11.2.3.6.1.3.2.1.4
		topIgmpSnpSGFwdGrpIpIndex OBJECT-TYPE
			SYNTAX IpAddress
			MAX-ACCESS not-accessible
			STATUS current
			DESCRIPTION
				"Description."
			::= { topIgmpSnpStaticFwdEntry 4 }

		
		-- 1.3.6.1.4.1.32285.11.2.3.6.1.3.2.1.5
		topIgmpSnpSGFwdMvlanIndex OBJECT-TYPE
			SYNTAX INTEGER (2..4094)
			MAX-ACCESS not-accessible
			STATUS current
			DESCRIPTION
				"Description."
			::= { topIgmpSnpStaticFwdEntry 5 }

		
		-- 1.3.6.1.4.1.32285.11.2.3.6.1.3.2.1.6
		topIgmpSnpSGFwdSrcIpIndex OBJECT-TYPE
			SYNTAX IpAddress
			MAX-ACCESS not-accessible
			STATUS current
			DESCRIPTION
				"Description."
			::= { topIgmpSnpStaticFwdEntry 6 }

		
		-- 1.3.6.1.4.1.32285.11.2.3.6.1.3.2.1.7
		topIgmpSnpSGFwdRowStatus  OBJECT-TYPE
			SYNTAX RowStatus
			MAX-ACCESS read-create
			STATUS current
			DESCRIPTION
				"Description."
			::= { topIgmpSnpStaticFwdEntry 7 }

		
		-- 1.3.6.1.4.1.32285.11.2.3.6.1.4
		topIgmpMvlanObjects OBJECT IDENTIFIER ::= { topIgmpOltConfigMgmtObjects 4 }

		
		-- 1.3.6.1.4.1.32285.11.2.3.6.1.4.1
		topIgmpMvlanTable OBJECT-TYPE
			SYNTAX SEQUENCE OF TopIgmpMvlanEntry
			MAX-ACCESS not-accessible
			STATUS current
			DESCRIPTION
				"Description."
			::= { topIgmpMvlanObjects 1 }

		
		-- 1.3.6.1.4.1.32285.11.2.3.6.1.4.1.1
		topIgmpMvlanEntry OBJECT-TYPE
			SYNTAX TopIgmpMvlanEntry
			MAX-ACCESS not-accessible
			STATUS current
			DESCRIPTION
				"Description."
			INDEX { topIgmpMvlanIdIndex }
			::= { topIgmpMvlanTable 1 }

		
		TopIgmpMvlanEntry ::=
			SEQUENCE { 
				topIgmpMvlanIdIndex
					INTEGER,
				topIgmpMvlanUpLinkType
					INTEGER,
				topIgmpMvlanUpLinkSlot
					INTEGER,
				topIgmpMvlanUpLinkPort
					INTEGER,
				topIgmpMvlanUpLinkAggId 
					INTEGER,
				topIgmpMvlanVrfName
					OCTET STRING,
				topIgmpMvlanRowstatus
					RowStatus
			 }

		-- 1.3.6.1.4.1.32285.11.2.3.6.1.4.1.1.1
		topIgmpMvlanIdIndex OBJECT-TYPE
			SYNTAX INTEGER (2..4094)
			MAX-ACCESS not-accessible
			STATUS current
			DESCRIPTION
				"Description."
			::= { topIgmpMvlanEntry 1 }

		
		-- 1.3.6.1.4.1.32285.11.2.3.6.1.4.1.1.2
		topIgmpMvlanUpLinkType OBJECT-TYPE
			SYNTAX INTEGER
				{
				invalid(1),
				ge(3),
				xe(4),
				ethagg(9)
				}
			MAX-ACCESS read-write
			STATUS current
			DESCRIPTION
				"Description."
			::= { topIgmpMvlanEntry 2 }

		
		-- 1.3.6.1.4.1.32285.11.2.3.6.1.4.1.1.3
		topIgmpMvlanUpLinkSlot OBJECT-TYPE
			SYNTAX INTEGER
			MAX-ACCESS read-write
			STATUS current
			DESCRIPTION
				"Description."
			::= { topIgmpMvlanEntry 3 }

		
		-- 1.3.6.1.4.1.32285.11.2.3.6.1.4.1.1.4
		topIgmpMvlanUpLinkPort OBJECT-TYPE
			SYNTAX INTEGER
			MAX-ACCESS read-write
			STATUS current
			DESCRIPTION
				"Description."
			::= { topIgmpMvlanEntry 4 }

		
		-- 1.3.6.1.4.1.32285.11.2.3.6.1.4.1.1.5
		topIgmpMvlanUpLinkAggId  OBJECT-TYPE
			SYNTAX INTEGER (0..32)
			MAX-ACCESS read-write
			STATUS current
			DESCRIPTION
				"Description."
			::= { topIgmpMvlanEntry 5 }

		
		-- 1.3.6.1.4.1.32285.11.2.3.6.1.4.1.1.6
		topIgmpMvlanVrfName OBJECT-TYPE
			SYNTAX OCTET STRING (SIZE (0..31))
			MAX-ACCESS read-create
			STATUS current
			DESCRIPTION
				"Description."
			::= { topIgmpMvlanEntry 6 }

		
		-- 1.3.6.1.4.1.32285.11.2.3.6.1.4.1.1.7
		topIgmpMvlanRowstatus OBJECT-TYPE
			SYNTAX RowStatus
			MAX-ACCESS read-create
			STATUS current
			DESCRIPTION
				"Description."
			::= { topIgmpMvlanEntry 7 }

		
		-- 1.3.6.1.4.1.32285.11.2.3.6.1.4.2
		topIgmpMvlanGroupTable OBJECT-TYPE
			SYNTAX SEQUENCE OF TopIgmpMvlanGroupEntry
			MAX-ACCESS not-accessible
			STATUS current
			DESCRIPTION
				"Description."
			::= { topIgmpMvlanObjects 2 }

		
		-- 1.3.6.1.4.1.32285.11.2.3.6.1.4.2.1
		topIgmpMvlanGroupEntry OBJECT-TYPE
			SYNTAX TopIgmpMvlanGroupEntry
			MAX-ACCESS not-accessible
			STATUS current
			DESCRIPTION
				"Description."
			INDEX { topIgmpMvlanGroupMvlanIndex, topIgmpMvlanGroupIdIndex, topIgmpMvlanGroupIpIndex, topIgmpMvlanGroupSrcIpIndex }
			::= { topIgmpMvlanGroupTable 1 }

		
		TopIgmpMvlanGroupEntry ::=
			SEQUENCE { 
				topIgmpMvlanGroupMvlanIndex
					INTEGER,
				topIgmpMvlanGroupIdIndex
					INTEGER,
				topIgmpMvlanGroupIpIndex
					IpAddress,
				topIgmpMvlanGroupSrcIpIndex
					IpAddress,
				topIgmpMvlanGroupDesc
					OCTET STRING,
				topIgmpMvlanGroupMaxBW
					INTEGER,
				topIgmpMvlanGroupJoinMode
					INTEGER,
				topIgmpMvlanGroupRowstatus
					RowStatus
			 }

		-- 1.3.6.1.4.1.32285.11.2.3.6.1.4.2.1.1
		topIgmpMvlanGroupMvlanIndex OBJECT-TYPE
			SYNTAX INTEGER (2..4094)
			MAX-ACCESS not-accessible
			STATUS current
			DESCRIPTION
				"Description."
			::= { topIgmpMvlanGroupEntry 1 }

		
		-- 1.3.6.1.4.1.32285.11.2.3.6.1.4.2.1.2
		topIgmpMvlanGroupIdIndex OBJECT-TYPE
			SYNTAX INTEGER (1..2000)
			MAX-ACCESS not-accessible
			STATUS current
			DESCRIPTION
				"Description."
			::= { topIgmpMvlanGroupEntry 2 }

		
		-- 1.3.6.1.4.1.32285.11.2.3.6.1.4.2.1.3
		topIgmpMvlanGroupIpIndex OBJECT-TYPE
			SYNTAX IpAddress
			MAX-ACCESS not-accessible
			STATUS current
			DESCRIPTION
				"Description."
			::= { topIgmpMvlanGroupEntry 3 }

		
		-- 1.3.6.1.4.1.32285.11.2.3.6.1.4.2.1.4
		topIgmpMvlanGroupSrcIpIndex OBJECT-TYPE
			SYNTAX IpAddress
			MAX-ACCESS not-accessible
			STATUS current
			DESCRIPTION
				"Description."
			::= { topIgmpMvlanGroupEntry 4 }

		
		-- 1.3.6.1.4.1.32285.11.2.3.6.1.4.2.1.5
		topIgmpMvlanGroupDesc OBJECT-TYPE
			SYNTAX OCTET STRING (SIZE (1..31))
			MAX-ACCESS read-write
			STATUS current
			DESCRIPTION
				"Description."
			::= { topIgmpMvlanGroupEntry 5 }

		
		-- 1.3.6.1.4.1.32285.11.2.3.6.1.4.2.1.6
		topIgmpMvlanGroupMaxBW OBJECT-TYPE
			SYNTAX INTEGER (0..1000000)
			UNITS "kbps"
			MAX-ACCESS read-write
			STATUS current
			DESCRIPTION
				"Description."
			DEFVAL { 500 }
			::= { topIgmpMvlanGroupEntry 6 }

		
		-- 1.3.6.1.4.1.32285.11.2.3.6.1.4.2.1.7
		topIgmpMvlanGroupJoinMode OBJECT-TYPE
			SYNTAX INTEGER
				{
				prejoin(1),
				noprejoin(2)
				}
			MAX-ACCESS read-write
			STATUS current
			DESCRIPTION
				"Description."
			DEFVAL { noprejoin }
			::= { topIgmpMvlanGroupEntry 7 }

		
		-- 1.3.6.1.4.1.32285.11.2.3.6.1.4.2.1.8
		topIgmpMvlanGroupRowstatus OBJECT-TYPE
			SYNTAX RowStatus
			MAX-ACCESS read-create
			STATUS current
			DESCRIPTION
				"Description."
			::= { topIgmpMvlanGroupEntry 8 }

		
		-- 1.3.6.1.4.1.32285.11.2.3.6.1.5
		topIgmpCtcObjects OBJECT IDENTIFIER ::= { topIgmpOltConfigMgmtObjects 5 }

		
		-- 1.3.6.1.4.1.32285.11.2.3.6.1.5.1
		topIgmpCtcParamObjects OBJECT IDENTIFIER ::= { topIgmpCtcObjects 1 }

		
		-- 1.3.6.1.4.1.32285.11.2.3.6.1.5.1.1
		topIgmpCtcEnable OBJECT-TYPE
			SYNTAX INTEGER
				{
				enable(1),
				disable(2)
				}
			MAX-ACCESS read-write
			STATUS current
			DESCRIPTION
				"Description."
			DEFVAL { disable }
			::= { topIgmpCtcParamObjects 1 }

		
		-- 1.3.6.1.4.1.32285.11.2.3.6.1.5.1.2
		topIgmpCtcCdrInterval OBJECT-TYPE
			SYNTAX INTEGER (60..43200)
			UNITS "second"
			MAX-ACCESS read-write
			STATUS current
			DESCRIPTION
				"Description."
			DEFVAL { 600 }
			::= { topIgmpCtcParamObjects 2 }

		
		-- 1.3.6.1.4.1.32285.11.2.3.6.1.5.1.3
		topIgmpCtcCdrNum OBJECT-TYPE
			SYNTAX INTEGER (100..200)
			MAX-ACCESS read-write
			STATUS current
			DESCRIPTION
				"Description."
			DEFVAL { 200 }
			::= { topIgmpCtcParamObjects 3 }

		
		-- 1.3.6.1.4.1.32285.11.2.3.6.1.5.1.4
		topIgmpCtcCdrReport OBJECT-TYPE
			SYNTAX INTEGER
			       {
			        noreport(0),
				report(1)
				}
			MAX-ACCESS read-write
			STATUS current
			DESCRIPTION
				"Description."
			DEFVAL { noreport }
			::= { topIgmpCtcParamObjects 4 }

		
		-- 1.3.6.1.4.1.32285.11.2.3.6.1.5.1.5
		topIgmpCtcAutoResetTime OBJECT-TYPE
			SYNTAX INTEGER (0..86399)
			MAX-ACCESS read-write
			STATUS current
			DESCRIPTION
				"Range:00:00:00to23:59:59, default 4:00:00
				."
			DEFVAL { 14400 }
			::= { topIgmpCtcParamObjects 5 }

		
		-- 1.3.6.1.4.1.32285.11.2.3.6.1.5.1.6
		topIgmpCtcRecognitionTime OBJECT-TYPE
			SYNTAX INTEGER (1..120)
			UNITS "second"
			MAX-ACCESS read-write
			STATUS current
			DESCRIPTION
				"Description."
			DEFVAL { 30 }
			::= { topIgmpCtcParamObjects 6 }

		
		-- 1.3.6.1.4.1.32285.11.2.3.6.1.5.1.7
		topIgmpCtcOnuFwdMode OBJECT-TYPE
			SYNTAX INTEGER
				{
				vlanMac(1),
				vlanIp(2)
				}
			MAX-ACCESS read-write
			STATUS current
			DESCRIPTION
				"Description."
			::= { topIgmpCtcParamObjects 7 }

		
		-- 1.3.6.1.4.1.32285.11.2.3.6.1.5.2
		topIgmpCtcProfileTable OBJECT-TYPE
			SYNTAX SEQUENCE OF TopIgmpCtcProfileEntry
			MAX-ACCESS not-accessible
			STATUS current
			DESCRIPTION
				"Description."
			::= { topIgmpCtcObjects 2 }

		
		-- 1.3.6.1.4.1.32285.11.2.3.6.1.5.2.1
		topIgmpCtcProfileEntry OBJECT-TYPE
			SYNTAX TopIgmpCtcProfileEntry
			MAX-ACCESS not-accessible
			STATUS current
			DESCRIPTION
				"Description."
			INDEX { topIgmpCtcProfileIdIndex }
			::= { topIgmpCtcProfileTable 1 }

		
		TopIgmpCtcProfileEntry ::=
			SEQUENCE { 
				topIgmpCtcProfileIdIndex
					INTEGER,
				topIgmpCtcProfileDesc
					OCTET STRING,
				topIgmpCtcProfileAuth
					INTEGER,
				topIgmpCtcProfileSinglePreviewTime
					INTEGER,
				topIgmpCtcProfilePreviewInterval
					INTEGER,
				topIgmpCtcProfilePreviewCount
					INTEGER,
				topIgmpCtcProfileRowstatus
					RowStatus
			 }

		-- 1.3.6.1.4.1.32285.11.2.3.6.1.5.2.1.1
		topIgmpCtcProfileIdIndex OBJECT-TYPE
			SYNTAX INTEGER (1..256)
			MAX-ACCESS not-accessible
			STATUS current
			DESCRIPTION
				"Description."
			::= { topIgmpCtcProfileEntry 1 }

		
		-- 1.3.6.1.4.1.32285.11.2.3.6.1.5.2.1.2
		topIgmpCtcProfileDesc OBJECT-TYPE
			SYNTAX OCTET STRING (SIZE (1..31))
			MAX-ACCESS read-write
			STATUS current
			DESCRIPTION
				"Description."
			::= { topIgmpCtcProfileEntry 2 }

		
		-- 1.3.6.1.4.1.32285.11.2.3.6.1.5.2.1.3
		topIgmpCtcProfileAuth OBJECT-TYPE
			SYNTAX INTEGER
				{
				deny(1),
				permit(2),
				preview(3)
				}
			MAX-ACCESS read-write
			STATUS current
			DESCRIPTION
				"Description."
			DEFVAL { permit }
			::= { topIgmpCtcProfileEntry 3 }

		
		-- 1.3.6.1.4.1.32285.11.2.3.6.1.5.2.1.4
		topIgmpCtcProfileSinglePreviewTime OBJECT-TYPE
			SYNTAX INTEGER (10..6000)
			UNITS "second"
			MAX-ACCESS read-write
			STATUS current
			DESCRIPTION
				"Description."
			DEFVAL { 120 }
			::= { topIgmpCtcProfileEntry 4 }

		
		-- 1.3.6.1.4.1.32285.11.2.3.6.1.5.2.1.5
		topIgmpCtcProfilePreviewInterval OBJECT-TYPE
			SYNTAX INTEGER (0..7650)
			UNITS "second"
			MAX-ACCESS read-write
			STATUS current
			DESCRIPTION
				"Description."
			DEFVAL { 120 }
			::= { topIgmpCtcProfileEntry 5 }

		
		-- 1.3.6.1.4.1.32285.11.2.3.6.1.5.2.1.6
		topIgmpCtcProfilePreviewCount OBJECT-TYPE
			SYNTAX INTEGER (1..255)
			MAX-ACCESS read-write
			STATUS current
			DESCRIPTION
				"Description."
			DEFVAL { 8 }
			::= { topIgmpCtcProfileEntry 6 }

		
		-- 1.3.6.1.4.1.32285.11.2.3.6.1.5.2.1.7
		topIgmpCtcProfileRowstatus OBJECT-TYPE
			SYNTAX RowStatus
			MAX-ACCESS read-create
			STATUS current
			DESCRIPTION
				"Description."
			::= { topIgmpCtcProfileEntry 7 }

		
		-- 1.3.6.1.4.1.32285.11.2.3.6.1.5.3
		topIgmpCtcProfileConfigGroupTable OBJECT-TYPE
			SYNTAX SEQUENCE OF TopIgmpCtcProfileConfigGroupEntry
			MAX-ACCESS not-accessible
			STATUS current
			DESCRIPTION
				"Description."
			::= { topIgmpCtcObjects 3 }

		
		-- 1.3.6.1.4.1.32285.11.2.3.6.1.5.3.1
		topIgmpCtcProfileConfigGroupEntry OBJECT-TYPE
			SYNTAX TopIgmpCtcProfileConfigGroupEntry
			MAX-ACCESS not-accessible
			STATUS current
			DESCRIPTION
				"Description."
			INDEX { topIgmpCtcProfileConfigIdIndex, topIgmpCtcProfileConfigGroupIdIndex }
			::= { topIgmpCtcProfileConfigGroupTable 1 }

		
		TopIgmpCtcProfileConfigGroupEntry ::=
			SEQUENCE { 
				topIgmpCtcProfileConfigIdIndex
					INTEGER,
				topIgmpCtcProfileConfigGroupIdIndex
					INTEGER,
				topIgmpCtcProfileConfigGroupRowstatus
					RowStatus
			 }

		-- 1.3.6.1.4.1.32285.11.2.3.6.1.5.3.1.1
		topIgmpCtcProfileConfigIdIndex OBJECT-TYPE
			SYNTAX INTEGER (1..256)
			MAX-ACCESS not-accessible
			STATUS current
			DESCRIPTION
				"Description."
			::= { topIgmpCtcProfileConfigGroupEntry 1 }

		
		-- 1.3.6.1.4.1.32285.11.2.3.6.1.5.3.1.2
		topIgmpCtcProfileConfigGroupIdIndex OBJECT-TYPE
			SYNTAX INTEGER (1..2000)
			MAX-ACCESS not-accessible
			STATUS current
			DESCRIPTION
				"Description."
			::= { topIgmpCtcProfileConfigGroupEntry 2 }

		
		-- 1.3.6.1.4.1.32285.11.2.3.6.1.5.3.1.3
		topIgmpCtcProfileConfigGroupRowstatus OBJECT-TYPE
			SYNTAX RowStatus
			MAX-ACCESS read-create
			STATUS current
			DESCRIPTION
				"Description."
			::= { topIgmpCtcProfileConfigGroupEntry 3 }

		
		-- 1.3.6.1.4.1.32285.11.2.3.6.1.5.4
		topIgmpCtcProfileBindUniTable OBJECT-TYPE
			SYNTAX SEQUENCE OF TopIgmpCtcProfileBindUniEntry
			MAX-ACCESS not-accessible
			STATUS current
			DESCRIPTION
				"Description."
			::= { topIgmpCtcObjects 4 }

		
		-- 1.3.6.1.4.1.32285.11.2.3.6.1.5.4.1
		topIgmpCtcProfileBindUniEntry OBJECT-TYPE
			SYNTAX TopIgmpCtcProfileBindUniEntry
			MAX-ACCESS not-accessible
			STATUS current
			DESCRIPTION
				"Description."
			INDEX { topIgmpCtcProfileBindUniProfIdIndex, topIgmpCtcProfileBindUniTypeIndex, topIgmpCtcProfileBindUniSlotIndex, topIgmpCtcProfileBindUniPortIndex, topIgmpCtcProfileBindUniOnuIndex, 
				topIgmpCtcProfileBindUniIdIndex }
			::= { topIgmpCtcProfileBindUniTable 1 }

		
		TopIgmpCtcProfileBindUniEntry ::=
			SEQUENCE { 
				topIgmpCtcProfileBindUniProfIdIndex
					INTEGER,
				topIgmpCtcProfileBindUniTypeIndex
					INTEGER,
				topIgmpCtcProfileBindUniSlotIndex
					INTEGER,
				topIgmpCtcProfileBindUniPortIndex
					INTEGER,
				topIgmpCtcProfileBindUniOnuIndex
					INTEGER,
				topIgmpCtcProfileBindUniIdIndex
					INTEGER,
				topIgmpCtcProfileBindUniRowstatus
					RowStatus
			 }

		-- 1.3.6.1.4.1.32285.11.2.3.6.1.5.4.1.1
		topIgmpCtcProfileBindUniProfIdIndex OBJECT-TYPE
			SYNTAX INTEGER (1..256)
			MAX-ACCESS not-accessible
			STATUS current
			DESCRIPTION
				"Description."
			::= { topIgmpCtcProfileBindUniEntry 1 }

		
		-- 1.3.6.1.4.1.32285.11.2.3.6.1.5.4.1.2
		topIgmpCtcProfileBindUniTypeIndex OBJECT-TYPE
			SYNTAX INTEGER { onuUni(11) }
			MAX-ACCESS not-accessible
			STATUS current
			DESCRIPTION
				"Description."
			::= { topIgmpCtcProfileBindUniEntry 2 }

		
		-- 1.3.6.1.4.1.32285.11.2.3.6.1.5.4.1.3
		topIgmpCtcProfileBindUniSlotIndex OBJECT-TYPE
			SYNTAX INTEGER
			MAX-ACCESS not-accessible
			STATUS current
			DESCRIPTION
				"Description."
			::= { topIgmpCtcProfileBindUniEntry 3 }

		
		-- 1.3.6.1.4.1.32285.11.2.3.6.1.5.4.1.4
		topIgmpCtcProfileBindUniPortIndex OBJECT-TYPE
			SYNTAX INTEGER
			MAX-ACCESS not-accessible
			STATUS current
			DESCRIPTION
				"Description."
			::= { topIgmpCtcProfileBindUniEntry 4 }

		
		-- 1.3.6.1.4.1.32285.11.2.3.6.1.5.4.1.5
		topIgmpCtcProfileBindUniOnuIndex OBJECT-TYPE
			SYNTAX INTEGER
			MAX-ACCESS not-accessible
			STATUS current
			DESCRIPTION
				"Description."
			::= { topIgmpCtcProfileBindUniEntry 5 }

		
		-- 1.3.6.1.4.1.32285.11.2.3.6.1.5.4.1.6
		topIgmpCtcProfileBindUniIdIndex OBJECT-TYPE
			SYNTAX INTEGER
			MAX-ACCESS not-accessible
			STATUS current
			DESCRIPTION
				"Description."
			::= { topIgmpCtcProfileBindUniEntry 6 }

		
		-- 1.3.6.1.4.1.32285.11.2.3.6.1.5.4.1.7
		topIgmpCtcProfileBindUniRowstatus OBJECT-TYPE
			SYNTAX RowStatus
			MAX-ACCESS read-create
			STATUS current
			DESCRIPTION
				"Description."
			::= { topIgmpCtcProfileBindUniEntry 7 }

		
		-- 1.3.6.1.4.1.32285.11.2.3.6.1.5.5
		topIgmpCtcCdrTable OBJECT-TYPE
			SYNTAX SEQUENCE OF TopIgmpCtcCdrEntry
			MAX-ACCESS not-accessible
			STATUS current
			DESCRIPTION
				"Description."
			::= { topIgmpCtcObjects 5 }

		
		-- 1.3.6.1.4.1.32285.11.2.3.6.1.5.5.1
		topIgmpCtcCdrEntry OBJECT-TYPE
			SYNTAX TopIgmpCtcCdrEntry
			MAX-ACCESS not-accessible
			STATUS current
			DESCRIPTION
				"Description."
			INDEX { IMPLIED topIgmpCtcCdrSequenceIndex }
			::= { topIgmpCtcCdrTable 1 }

		
		TopIgmpCtcCdrEntry ::=
			SEQUENCE { 
				topIgmpCtcCdrSequenceIndex
					OCTET STRING,
				topIgmpCtcCdrType
					INTEGER,
				topIgmpCtcCdrSlot
					INTEGER,
				topIgmpCtcCdrPon
					INTEGER,
				topIgmpCtcCdrOnu
					INTEGER,
				topIgmpCtcCdrUni
					INTEGER,
				topIgmpCtcCdrReqType
					INTEGER,
				topIgmpCtcCdrReqTime
					TimeTicks,
				topIgmpCtcCdrReqGrpId
					INTEGER,
				topIgmpCtcCdrGrpAuth
					INTEGER,
				topIgmpCtcCdrReqResult
					INTEGER,
				topIgmpCtcCdrLeaveType
					INTEGER,
				topIgmpCtcCdrRecordTime
					TimeTicks
			 }

		-- 1.3.6.1.4.1.32285.11.2.3.6.1.5.5.1.1
		topIgmpCtcCdrSequenceIndex OBJECT-TYPE
			SYNTAX OCTET STRING (SIZE (8))
			MAX-ACCESS not-accessible
			STATUS current
			DESCRIPTION
				"Description."
			::= { topIgmpCtcCdrEntry 1 }

		
		-- 1.3.6.1.4.1.32285.11.2.3.6.1.5.5.1.2
		topIgmpCtcCdrType OBJECT-TYPE
			SYNTAX INTEGER
				{
				invalid(1),
				onu(10),
				uni(11)
				}
			MAX-ACCESS read-only
			STATUS current
			DESCRIPTION
				"Description."
			::= { topIgmpCtcCdrEntry 2 }

		
		-- 1.3.6.1.4.1.32285.11.2.3.6.1.5.5.1.3
		topIgmpCtcCdrSlot OBJECT-TYPE
			SYNTAX INTEGER
			MAX-ACCESS read-only
			STATUS current
			DESCRIPTION
				"Description."
			::= { topIgmpCtcCdrEntry 3 }

		
		-- 1.3.6.1.4.1.32285.11.2.3.6.1.5.5.1.4
		topIgmpCtcCdrPon OBJECT-TYPE
			SYNTAX INTEGER
			MAX-ACCESS read-only
			STATUS current
			DESCRIPTION
				"Description."
			::= { topIgmpCtcCdrEntry 4 }

		
		-- 1.3.6.1.4.1.32285.11.2.3.6.1.5.5.1.5
		topIgmpCtcCdrOnu OBJECT-TYPE
			SYNTAX INTEGER
			MAX-ACCESS read-only
			STATUS current
			DESCRIPTION
				"Description."
			::= { topIgmpCtcCdrEntry 5 }

		
		-- 1.3.6.1.4.1.32285.11.2.3.6.1.5.5.1.6
		topIgmpCtcCdrUni OBJECT-TYPE
			SYNTAX INTEGER
			MAX-ACCESS read-only
			STATUS current
			DESCRIPTION
				"Description."
			::= { topIgmpCtcCdrEntry 6 }

		
		-- 1.3.6.1.4.1.32285.11.2.3.6.1.5.5.1.7
		topIgmpCtcCdrReqType OBJECT-TYPE
			SYNTAX INTEGER
				{
				join(1),
				leave(2)
				}
			MAX-ACCESS read-only
			STATUS current
			DESCRIPTION
				"Description."
			::= { topIgmpCtcCdrEntry 7 }

		
		-- 1.3.6.1.4.1.32285.11.2.3.6.1.5.5.1.8
		topIgmpCtcCdrReqTime OBJECT-TYPE
			SYNTAX TimeTicks
			MAX-ACCESS read-only
			STATUS current
			DESCRIPTION
				"Description."
			::= { topIgmpCtcCdrEntry 8 }

		
		-- 1.3.6.1.4.1.32285.11.2.3.6.1.5.5.1.9
		topIgmpCtcCdrReqGrpId OBJECT-TYPE
			SYNTAX INTEGER
			MAX-ACCESS read-only
			STATUS current
			DESCRIPTION
				"Description."
			::= { topIgmpCtcCdrEntry 9 }

		
		-- 1.3.6.1.4.1.32285.11.2.3.6.1.5.5.1.10
		topIgmpCtcCdrGrpAuth OBJECT-TYPE
			SYNTAX INTEGER
				{
				deny(1),
				permit(2),
				preview(3)
				}
			MAX-ACCESS read-only
			STATUS current
			DESCRIPTION
				"Description."
			::= { topIgmpCtcCdrEntry 10 }

		
		-- 1.3.6.1.4.1.32285.11.2.3.6.1.5.5.1.11
		topIgmpCtcCdrReqResult OBJECT-TYPE
			SYNTAX INTEGER
				{
				success(1),
				failure(2)
				}
			MAX-ACCESS read-only
			STATUS current
			DESCRIPTION
				"Description."
			::= { topIgmpCtcCdrEntry 11 }

		
		-- 1.3.6.1.4.1.32285.11.2.3.6.1.5.5.1.12
		topIgmpCtcCdrLeaveType OBJECT-TYPE
			SYNTAX INTEGER
				{
				selfleaving(1),
				forceleaving(2)
				}
			MAX-ACCESS read-only
			STATUS current
			DESCRIPTION
				"Description."
			::= { topIgmpCtcCdrEntry 12 }

		
		-- 1.3.6.1.4.1.32285.11.2.3.6.1.5.5.1.13
		topIgmpCtcCdrRecordTime OBJECT-TYPE
			SYNTAX TimeTicks
			MAX-ACCESS read-only
			STATUS current
			DESCRIPTION
				"Description."
			::= { topIgmpCtcCdrEntry 13 }

		
		-- 1.3.6.1.4.1.32285.11.2.3.6.1.6
		topIgmpGroupInfoTable OBJECT-TYPE
			SYNTAX SEQUENCE OF TopIgmpGroupInfoEntry
			MAX-ACCESS not-accessible
			STATUS current
			DESCRIPTION
				"Description."
			::= { topIgmpOltConfigMgmtObjects 6 }

		
		-- 1.3.6.1.4.1.32285.11.2.3.6.1.6.1
		topIgmpGroupInfoEntry OBJECT-TYPE
			SYNTAX TopIgmpGroupInfoEntry
			MAX-ACCESS not-accessible
			STATUS current
			DESCRIPTION
				"Description."
			INDEX { topIgmpGroupIdIndex }
			::= { topIgmpGroupInfoTable 1 }

		
		TopIgmpGroupInfoEntry ::=
			SEQUENCE { 
				topIgmpGroupIdIndex
					INTEGER,
				topIgmpGroupIp
					IpAddress,
				topIgmpGroupMvlan
					INTEGER,
				topIgmpGroupSrcIp
					IpAddress,
				topIgmpGroupState
					BITS,
				topIgmpGroupPortList
					OCTET STRING
			 }

		-- 1.3.6.1.4.1.32285.11.2.3.6.1.6.1.1
		topIgmpGroupIdIndex OBJECT-TYPE
			SYNTAX INTEGER (1..2000)
			MAX-ACCESS not-accessible
			STATUS current
			DESCRIPTION
				"Description."
			::= { topIgmpGroupInfoEntry 1 }

		
		-- 1.3.6.1.4.1.32285.11.2.3.6.1.6.1.2
		topIgmpGroupIp OBJECT-TYPE
			SYNTAX IpAddress
			MAX-ACCESS read-only
			STATUS current
			DESCRIPTION
				"Description."
			::= { topIgmpGroupInfoEntry 2 }

		
		-- 1.3.6.1.4.1.32285.11.2.3.6.1.6.1.3
		topIgmpGroupMvlan OBJECT-TYPE
			SYNTAX INTEGER
			MAX-ACCESS read-only
			STATUS current
			DESCRIPTION
				"Description."
			::= { topIgmpGroupInfoEntry 3 }

		
		-- 1.3.6.1.4.1.32285.11.2.3.6.1.6.1.4
		topIgmpGroupSrcIp OBJECT-TYPE
			SYNTAX IpAddress
			MAX-ACCESS read-only
			STATUS current
			DESCRIPTION
				"Description."
			::= { topIgmpGroupInfoEntry 4 }

		
		-- 1.3.6.1.4.1.32285.11.2.3.6.1.6.1.5
		topIgmpGroupState OBJECT-TYPE
			SYNTAX BITS
				{
				activegroup(0),
				prejoingroup(1),
				staticgroup(2)
				}
			MAX-ACCESS read-only
			STATUS current
			DESCRIPTION
				"Description."
			::= { topIgmpGroupInfoEntry 5 }

		
		-- 1.3.6.1.4.1.32285.11.2.3.6.1.6.1.6
		topIgmpGroupPortList OBJECT-TYPE
			SYNTAX OCTET STRING (SIZE (0..1024))
			MAX-ACCESS read-only
			STATUS current
			DESCRIPTION
				"Max support 256 ports, each port is 4 bytes, bit(24-31 )is type, bit(16-23 )is slot, bit(8-15 )is port, bit(0-7 )is reserved, such as ge 0/2 pon 3/1:
				 03 00 02 00 05 03 01 00."
			::= { topIgmpGroupInfoEntry 6 }

		
		-- 1.3.6.1.4.1.32285.11.2.3.6.2
		topIgmpOnuConfigMgmtObjects OBJECT IDENTIFIER ::= { topIgmpMgmtObjects 2 }

		
		-- 1.3.6.1.4.1.32285.11.2.3.6.2.1
		topIgmpOnuConfigTable OBJECT-TYPE
			SYNTAX SEQUENCE OF TopIgmpOnuConfigEntry
			MAX-ACCESS not-accessible
			STATUS current
			DESCRIPTION
				"Description."
			::= { topIgmpOnuConfigMgmtObjects 1 }

		
		-- 1.3.6.1.4.1.32285.11.2.3.6.2.1.1
		topIgmpOnuConfigEntry OBJECT-TYPE
			SYNTAX TopIgmpOnuConfigEntry
			MAX-ACCESS not-accessible
			STATUS current
			DESCRIPTION
				"Description."
			INDEX { topIgmpOnuTypeIndex, topIgmpOnuSlotIndex, topIgmpOnuPonIndex, topIgmpOnuIndex }
			::= { topIgmpOnuConfigTable 1 }

		
		TopIgmpOnuConfigEntry ::=
			SEQUENCE { 
				topIgmpOnuTypeIndex
					INTEGER,
				topIgmpOnuSlotIndex
					INTEGER,
				topIgmpOnuPonIndex
					INTEGER,
				topIgmpOnuIndex
					INTEGER,
				topIgmpOnuMode
					INTEGER,
				topIgmpOnuFastLeave
					INTEGER
			 }

		-- 1.3.6.1.4.1.32285.11.2.3.6.2.1.1.1
		topIgmpOnuTypeIndex OBJECT-TYPE
			SYNTAX INTEGER { onu(10) }
			MAX-ACCESS not-accessible
			STATUS current
			DESCRIPTION
				"Description."
			::= { topIgmpOnuConfigEntry 1 }

		
		-- 1.3.6.1.4.1.32285.11.2.3.6.2.1.1.2
		topIgmpOnuSlotIndex OBJECT-TYPE
			SYNTAX INTEGER
			MAX-ACCESS not-accessible
			STATUS current
			DESCRIPTION
				"Description."
			::= { topIgmpOnuConfigEntry 2 }

		
		-- 1.3.6.1.4.1.32285.11.2.3.6.2.1.1.3
		topIgmpOnuPonIndex OBJECT-TYPE
			SYNTAX INTEGER
			MAX-ACCESS not-accessible
			STATUS current
			DESCRIPTION
				"Description."
			::= { topIgmpOnuConfigEntry 3 }

		
		-- 1.3.6.1.4.1.32285.11.2.3.6.2.1.1.4
		topIgmpOnuIndex OBJECT-TYPE
			SYNTAX INTEGER
			MAX-ACCESS not-accessible
			STATUS current
			DESCRIPTION
				"Description."
			::= { topIgmpOnuConfigEntry 4 }

		
		-- 1.3.6.1.4.1.32285.11.2.3.6.2.1.1.5
		topIgmpOnuMode OBJECT-TYPE
			SYNTAX INTEGER
				{
				ctc(1),
				snooping(2),
				disable(3)
				}
			MAX-ACCESS read-write
			STATUS current
			DESCRIPTION
				"Description."
			DEFVAL { disable }
			::= { topIgmpOnuConfigEntry 5 }

		
		-- 1.3.6.1.4.1.32285.11.2.3.6.2.1.1.6
		topIgmpOnuFastLeave OBJECT-TYPE
			SYNTAX INTEGER
				{
				enable(1),
				disable(2)
				}
			MAX-ACCESS read-write
			STATUS current
			DESCRIPTION
				"Description."
			DEFVAL { disable }
			::= { topIgmpOnuConfigEntry 6 }

		
		-- 1.3.6.1.4.1.32285.11.2.3.6.2.2
		topIgmpUniConfigTable OBJECT-TYPE
			SYNTAX SEQUENCE OF TopIgmpUniConfigEntry
			MAX-ACCESS not-accessible
			STATUS current
			DESCRIPTION
				"Description."
			::= { topIgmpOnuConfigMgmtObjects 2 }

		
		-- 1.3.6.1.4.1.32285.11.2.3.6.2.2.1
		topIgmpUniConfigEntry OBJECT-TYPE
			SYNTAX TopIgmpUniConfigEntry
			MAX-ACCESS not-accessible
			STATUS current
			DESCRIPTION
				"Description."
			INDEX { topIgmpUniTypeIndex, topIgmpUniSlotIndex, topIgmpUniPonIndex, topIgmpUniOnuIndex, topIgmpUniIndex
				 }
			::= { topIgmpUniConfigTable 1 }

		
		TopIgmpUniConfigEntry ::=
			SEQUENCE { 
				topIgmpUniTypeIndex
					INTEGER,
				topIgmpUniSlotIndex
					INTEGER,
				topIgmpUniPonIndex
					INTEGER,
				topIgmpUniOnuIndex
					INTEGER,
				topIgmpUniIndex
					INTEGER,
				topIgmpUniMaxGroupNum
					INTEGER,
				topIgmpUniVlanList
					OCTET STRING,
				topIgmpUniVlanMode
					INTEGER
			 }

		-- 1.3.6.1.4.1.32285.11.2.3.6.2.2.1.1
		topIgmpUniTypeIndex OBJECT-TYPE
			SYNTAX INTEGER { uni(11) }
			MAX-ACCESS not-accessible
			STATUS current
			DESCRIPTION
				"Description."
			::= { topIgmpUniConfigEntry 1 }

		
		-- 1.3.6.1.4.1.32285.11.2.3.6.2.2.1.2
		topIgmpUniSlotIndex OBJECT-TYPE
			SYNTAX INTEGER
			MAX-ACCESS not-accessible
			STATUS current
			DESCRIPTION
				"Description."
			::= { topIgmpUniConfigEntry 2 }

		
		-- 1.3.6.1.4.1.32285.11.2.3.6.2.2.1.3
		topIgmpUniPonIndex OBJECT-TYPE
			SYNTAX INTEGER
			MAX-ACCESS not-accessible
			STATUS current
			DESCRIPTION
				"Description."
			::= { topIgmpUniConfigEntry 3 }

		
		-- 1.3.6.1.4.1.32285.11.2.3.6.2.2.1.4
		topIgmpUniOnuIndex OBJECT-TYPE
			SYNTAX INTEGER
			MAX-ACCESS not-accessible
			STATUS current
			DESCRIPTION
				"Description."
			::= { topIgmpUniConfigEntry 4 }

		
		-- 1.3.6.1.4.1.32285.11.2.3.6.2.2.1.5
		topIgmpUniIndex OBJECT-TYPE
			SYNTAX INTEGER
			MAX-ACCESS not-accessible
			STATUS current
			DESCRIPTION
				"Description."
			::= { topIgmpUniConfigEntry 5 }

		
		-- 1.3.6.1.4.1.32285.11.2.3.6.2.2.1.6
		topIgmpUniMaxGroupNum OBJECT-TYPE
			SYNTAX INTEGER (0..64)
			MAX-ACCESS read-write
			STATUS current
			DESCRIPTION
				"0: do not limit other value: use specific value
				"
			DEFVAL { 64 }
			::= { topIgmpUniConfigEntry 6 }

		
		-- 1.3.6.1.4.1.32285.11.2.3.6.2.2.1.7
		topIgmpUniVlanList OBJECT-TYPE
			SYNTAX OCTET STRING (SIZE (0..64))
			MAX-ACCESS read-write
			STATUS current
			DESCRIPTION
				"Two byte values are represented by a VLAN ID,one UNI port just only config 32 VLANs
				"
			::= { topIgmpUniConfigEntry 7 }

		
		-- 1.3.6.1.4.1.32285.11.2.3.6.2.2.1.8
		topIgmpUniVlanMode OBJECT-TYPE
			SYNTAX INTEGER
				{
				strip(1),
				translation(2),
				keep(3)
				}
			MAX-ACCESS read-write
			STATUS current
			DESCRIPTION
				"Description."
			DEFVAL { keep }
			::= { topIgmpUniConfigEntry 8 }

		
		-- 1.3.6.1.4.1.32285.11.2.3.6.2.3
		topIgmpUniVlanTransTable OBJECT-TYPE
			SYNTAX SEQUENCE OF TopIgmpUniVlanTransEntry
			MAX-ACCESS not-accessible
			STATUS current
			DESCRIPTION
				"Description."
			::= { topIgmpOnuConfigMgmtObjects 3 }

		
		-- 1.3.6.1.4.1.32285.11.2.3.6.2.3.1
		topIgmpUniVlanTransEntry OBJECT-TYPE
			SYNTAX TopIgmpUniVlanTransEntry
			MAX-ACCESS not-accessible
			STATUS current
			DESCRIPTION
				"Description."
			INDEX { topIgmpUniVlanTransTypeIndex, topIgmpUniVlanTransSlotIndex, topIgmpUniVlanTransPonIndex, topIgmpUniVlanTransOnuIndex, topIgmpUniVlanTransUniIndex, 
				topIgmpUniVlanTransIndex }
			::= { topIgmpUniVlanTransTable 1 }

		
		TopIgmpUniVlanTransEntry ::=
			SEQUENCE { 
				topIgmpUniVlanTransTypeIndex
					INTEGER,
				topIgmpUniVlanTransSlotIndex
					INTEGER,
				topIgmpUniVlanTransPonIndex
					INTEGER,
				topIgmpUniVlanTransOnuIndex
					INTEGER,
				topIgmpUniVlanTransUniIndex
					INTEGER,
				topIgmpUniVlanTransIndex
					INTEGER,
				topIgmpUniVlanTransOldVlan
					INTEGER,
				topIgmpUniVlanTransNewVlan
					INTEGER,
				topIgmpUniVlanTransRowStatus
					RowStatus
			 }

		-- 1.3.6.1.4.1.32285.11.2.3.6.2.3.1.1
		topIgmpUniVlanTransTypeIndex OBJECT-TYPE
			SYNTAX INTEGER { uni(11) }
			MAX-ACCESS not-accessible
			STATUS current
			DESCRIPTION
				"Description."
			::= { topIgmpUniVlanTransEntry 1 }

		
		-- 1.3.6.1.4.1.32285.11.2.3.6.2.3.1.2
		topIgmpUniVlanTransSlotIndex OBJECT-TYPE
			SYNTAX INTEGER
			MAX-ACCESS not-accessible
			STATUS current
			DESCRIPTION
				"Description."
			::= { topIgmpUniVlanTransEntry 2 }

		
		-- 1.3.6.1.4.1.32285.11.2.3.6.2.3.1.3
		topIgmpUniVlanTransPonIndex OBJECT-TYPE
			SYNTAX INTEGER
			MAX-ACCESS not-accessible
			STATUS current
			DESCRIPTION
				"Description."
			::= { topIgmpUniVlanTransEntry 3 }

		
		-- 1.3.6.1.4.1.32285.11.2.3.6.2.3.1.4
		topIgmpUniVlanTransOnuIndex OBJECT-TYPE
			SYNTAX INTEGER
			MAX-ACCESS not-accessible
			STATUS current
			DESCRIPTION
				"Description."
			::= { topIgmpUniVlanTransEntry 4 }

		
		-- 1.3.6.1.4.1.32285.11.2.3.6.2.3.1.5
		topIgmpUniVlanTransUniIndex OBJECT-TYPE
			SYNTAX INTEGER
			MAX-ACCESS not-accessible
			STATUS current
			DESCRIPTION
				"Description."
			::= { topIgmpUniVlanTransEntry 5 }

		
		-- 1.3.6.1.4.1.32285.11.2.3.6.2.3.1.6
		topIgmpUniVlanTransIndex OBJECT-TYPE
			SYNTAX INTEGER (1..8)
			MAX-ACCESS not-accessible
			STATUS current
			DESCRIPTION
				"Description."
			::= { topIgmpUniVlanTransEntry 6 }

		
		-- 1.3.6.1.4.1.32285.11.2.3.6.2.3.1.7
		topIgmpUniVlanTransOldVlan OBJECT-TYPE
			SYNTAX INTEGER (1..4094)
			MAX-ACCESS read-write
			STATUS current
			DESCRIPTION
				"Description."
			::= { topIgmpUniVlanTransEntry 7 }

		
		-- 1.3.6.1.4.1.32285.11.2.3.6.2.3.1.8
		topIgmpUniVlanTransNewVlan OBJECT-TYPE
			SYNTAX INTEGER (1..4094)
			MAX-ACCESS read-write
			STATUS current
			DESCRIPTION
				"Description."
			::= { topIgmpUniVlanTransEntry 8 }

		
		-- 1.3.6.1.4.1.32285.11.2.3.6.2.3.1.9
		topIgmpUniVlanTransRowStatus OBJECT-TYPE
			SYNTAX RowStatus
			MAX-ACCESS read-create
			STATUS current
			DESCRIPTION
				"Description."
			::= { topIgmpUniVlanTransEntry 9 }

		-- 1.3.6.1.4.1.32285.11.2.3.7
		topVlanMgmtObjects OBJECT IDENTIFIER ::= { topvisionEponTree 7 }

		
		-- 1.3.6.1.4.1.32285.11.2.3.7.1
		topLlidVlanGroup OBJECT-IDENTITY
			STATUS current
			DESCRIPTION 
				"llid-based vlan management."
			::= { topVlanMgmtObjects 1 }

		
		-- 1.3.6.1.4.1.32285.11.2.3.7.1.1
		topLlidVlanTransTable OBJECT-TYPE
			SYNTAX SEQUENCE OF TopLlidVlanTransEntry
			MAX-ACCESS not-accessible
			STATUS current
			DESCRIPTION
				"LLID, identify with ONU MAC"
			::= { topLlidVlanGroup 1 }

		
		-- 1.3.6.1.4.1.32285.11.2.3.7.1.1.1
		topLlidVlanTransEntry OBJECT-TYPE
			SYNTAX TopLlidVlanTransEntry
			MAX-ACCESS not-accessible
			STATUS current
			DESCRIPTION
				"llid-based vlan translation entry "
			INDEX { topLlidTransCardIdx, topLlidTransPonIdx, topLlidTransDevMac,topLlidTransVidIdx  }
			::= { topLlidVlanTransTable 1 }

		
		TopLlidVlanTransEntry ::=
			SEQUENCE { 
				topLlidTransCardIdx
					TopEPonSlotIndex,
				topLlidTransPonIdx
					TopEPonPonIndex,
				topLlidTransDevMac
					MacAddress,
				topLlidTransVidIdx
					INTEGER,
				topLlidTransNewVid
					INTEGER,
				topLlidTransCosMode
					INTEGER,
				topLlidTransNewCos
					INTEGER,
				topLlidTransNewTpid
					INTEGER,
				topLlidTransRowStatus
					RowStatus
			 }

		-- 1.3.6.1.4.1.32285.11.2.3.7.1.1.1.1
		topLlidTransCardIdx OBJECT-TYPE
			SYNTAX TopEPonSlotIndex
			MAX-ACCESS not-accessible
			STATUS current
			DESCRIPTION
				"slot index"
			::= { topLlidVlanTransEntry 1 }

		
		-- 1.3.6.1.4.1.32285.11.2.3.7.1.1.1.2
		topLlidTransPonIdx OBJECT-TYPE
			SYNTAX TopEPonPonIndex
			MAX-ACCESS not-accessible
			STATUS current
			DESCRIPTION
				"pon index"
			::= { topLlidVlanTransEntry 2 }

		
		-- 1.3.6.1.4.1.32285.11.2.3.7.1.1.1.3
		topLlidTransDevMac OBJECT-TYPE
			SYNTAX MacAddress
			MAX-ACCESS not-accessible
			STATUS current
			DESCRIPTION
				"ONU MAC"
			::= { topLlidVlanTransEntry 3 }

		
		-- 1.3.6.1.4.1.32285.11.2.3.7.1.1.1.4
		topLlidTransVidIdx OBJECT-TYPE
			SYNTAX INTEGER (1..4094)
			MAX-ACCESS not-accessible
			STATUS current
			DESCRIPTION
				"VLAN ID"
			::= { topLlidVlanTransEntry 4 }

		
		-- 1.3.6.1.4.1.32285.11.2.3.7.1.1.1.5
		topLlidTransNewVid OBJECT-TYPE
			SYNTAX INTEGER (1..4094)
			MAX-ACCESS read-create
			STATUS current
			DESCRIPTION
				"tvlan"
			::= { topLlidVlanTransEntry 5 }

		
		-- 1.3.6.1.4.1.32285.11.2.3.7.1.1.1.6
		topLlidTransCosMode OBJECT-TYPE
			SYNTAX INTEGER
				{
				remark(1),
				keepCos(2)
				}
			MAX-ACCESS read-create
			STATUS current
			DESCRIPTION
				"keepCos(2)-keep the current CoS.
				remark(1)-change Cos as per variable topLlidTransNewCos"
			DEFVAL { 2 }
			::= { topLlidVlanTransEntry 6 }

		
		-- 1.3.6.1.4.1.32285.11.2.3.7.1.1.1.7
		topLlidTransNewCos OBJECT-TYPE
			SYNTAX INTEGER (0..7)
			MAX-ACCESS read-create
			STATUS current
			DESCRIPTION
				"in case topLlidTransCosMode is remark(1),
				set new cos value"
			DEFVAL { 0 }
			::= { topLlidVlanTransEntry 7 }

		
		-- 1.3.6.1.4.1.32285.11.2.3.7.1.1.1.8
		topLlidTransNewTpid OBJECT-TYPE
			SYNTAX INTEGER (1..65535)
			MAX-ACCESS read-create
			STATUS current
			DESCRIPTION
				"value 0xFFFF means not to change the current TPID,
				otherwise modify it into this value."
			DEFVAL { '8100'h }
			::= { topLlidVlanTransEntry 8 }

		
		-- 1.3.6.1.4.1.32285.11.2.3.7.1.1.1.9
		topLlidTransRowStatus OBJECT-TYPE
			SYNTAX RowStatus
			MAX-ACCESS read-create
			STATUS current
			DESCRIPTION
				"add/del/set"
			::= { topLlidVlanTransEntry 9 }

		
		-- 1.3.6.1.4.1.32285.11.2.3.7.1.2
		topLlidVlanAggTable OBJECT-TYPE
			SYNTAX SEQUENCE OF TopLlidVlanAggEntry
			MAX-ACCESS not-accessible
			STATUS current
			DESCRIPTION
				"vlan based on llid aggregation."
			::= { topLlidVlanGroup 2 }

		
		-- 1.3.6.1.4.1.32285.11.2.3.7.1.2.1
		topLlidVlanAggEntry OBJECT-TYPE
			SYNTAX TopLlidVlanAggEntry
			MAX-ACCESS not-accessible
			STATUS current
			DESCRIPTION
				"vlan based on llid aggregation entry"
			INDEX { llidVlanAggCardIndex, llidVlanAggPonIndex, llidVlanAggMacAddr, llidVlanAfterAggVid }
			::= { topLlidVlanAggTable 1 }

		
		TopLlidVlanAggEntry ::=
			SEQUENCE { 
				llidVlanAggCardIndex
					TopEPonSlotIndex,
				llidVlanAggPonIndex
					TopEPonPonIndex,
				llidVlanAggMacAddr
					MacAddress,
				llidVlanAfterAggVid
					INTEGER,
				llidVlanBeforeAggVidList
					OCTET STRING,
				llidVlanAggCosMode
					INTEGER,
				llidVlanAggNewCos
					INTEGER,
				llidVlanAggNewTpid
					INTEGER,
				llidVlanAggRowStatus
					RowStatus
			 }

		-- 1.3.6.1.4.1.32285.11.2.3.7.1.2.1.1
		llidVlanAggCardIndex OBJECT-TYPE
			SYNTAX TopEPonSlotIndex
			MAX-ACCESS not-accessible
			STATUS current
			DESCRIPTION
				"Slot index"
			::= { topLlidVlanAggEntry 1 }

		
		-- 1.3.6.1.4.1.32285.11.2.3.7.1.2.1.2
		llidVlanAggPonIndex OBJECT-TYPE
			SYNTAX TopEPonPonIndex
			MAX-ACCESS not-accessible
			STATUS current
			DESCRIPTION
				"pon index"
			::= { topLlidVlanAggEntry 2 }

		
		-- 1.3.6.1.4.1.32285.11.2.3.7.1.2.1.3
		llidVlanAggMacAddr OBJECT-TYPE
			SYNTAX MacAddress
			MAX-ACCESS not-accessible
			STATUS current
			DESCRIPTION
				"ONU MAC"
			::= { topLlidVlanAggEntry 3 }

		
		-- 1.3.6.1.4.1.32285.11.2.3.7.1.2.1.4
		llidVlanAfterAggVid OBJECT-TYPE
			SYNTAX INTEGER (1..4094)
			MAX-ACCESS not-accessible
			STATUS current
			DESCRIPTION
				"vlan id"
			::= { topLlidVlanAggEntry 4 }

		
		-- 1.3.6.1.4.1.32285.11.2.3.7.1.2.1.5
		llidVlanBeforeAggVidList OBJECT-TYPE
			SYNTAX OCTET STRING (SIZE (512))
			MAX-ACCESS read-create
			STATUS current
			DESCRIPTION
				"vlan id"
			::= { topLlidVlanAggEntry 5 }

		
		-- 1.3.6.1.4.1.32285.11.2.3.7.1.2.1.6
		llidVlanAggCosMode OBJECT-TYPE
			SYNTAX INTEGER
				{
				remark(1),
				keepCos(2)
				}
			MAX-ACCESS read-create
			STATUS current
			DESCRIPTION
				"keepCos(2)-keep the current CoS.
				remark(1)-change Cos as per variable topLlidCosTransNewCos"
			DEFVAL { 2 }
			::= { topLlidVlanAggEntry 6 }

		
		-- 1.3.6.1.4.1.32285.11.2.3.7.1.2.1.7
		llidVlanAggNewCos OBJECT-TYPE
			SYNTAX INTEGER (0..7)
			MAX-ACCESS read-create
			STATUS current
			DESCRIPTION
				"in case topLlidCosTransCosMode is remark(1),
				set new cos value"
			DEFVAL { 0 }
			::= { topLlidVlanAggEntry 7 }

		
		-- 1.3.6.1.4.1.32285.11.2.3.7.1.2.1.8
		llidVlanAggNewTpid OBJECT-TYPE
			SYNTAX INTEGER (0..65535)
			MAX-ACCESS read-create
			STATUS current
			DESCRIPTION
				"value 0xFFFF means not to change the current TPID,
				otherwise modify it into this value."
			DEFVAL { '8100'h }
			::= { topLlidVlanAggEntry 8 }

		
		-- 1.3.6.1.4.1.32285.11.2.3.7.1.2.1.9
		llidVlanAggRowStatus OBJECT-TYPE
			SYNTAX RowStatus
			MAX-ACCESS read-create
			STATUS current
			DESCRIPTION
				"add/del/set"
			::= { topLlidVlanAggEntry 9 }

		
		-- 1.3.6.1.4.1.32285.11.2.3.7.1.3
		topLlidVlanTrunkTable OBJECT-TYPE
			SYNTAX SEQUENCE OF TopLlidVlanTrunkEntry
			MAX-ACCESS not-accessible
			STATUS current
			DESCRIPTION
				"Vlan trunk based on LLID only"
			::= { topLlidVlanGroup 3 }

		
		-- 1.3.6.1.4.1.32285.11.2.3.7.1.3.1
		topLlidVlanTrunkEntry OBJECT-TYPE
			SYNTAX TopLlidVlanTrunkEntry
			MAX-ACCESS not-accessible
			STATUS current
			DESCRIPTION
				"Vlan trunk based on LLID entry"
			INDEX { llidVlanTrunkCardIndex, llidVlanTrunkPonIndex, llidVlanTrunkMacIdx }
			::= { topLlidVlanTrunkTable 1 }

		
		TopLlidVlanTrunkEntry ::=
			SEQUENCE { 
				llidVlanTrunkCardIndex
					TopEPonSlotIndex,
				llidVlanTrunkPonIndex
					TopEPonPonIndex,
				llidVlanTrunkMacIdx
					MacAddress,
				llidVlanTrunkVidBmp
					OCTET STRING,
				llidVlanTrunkRowStatus
					RowStatus
			 }

		-- 1.3.6.1.4.1.32285.11.2.3.7.1.3.1.1
		llidVlanTrunkCardIndex OBJECT-TYPE
			SYNTAX TopEPonSlotIndex
			MAX-ACCESS not-accessible
			STATUS current
			DESCRIPTION
				"slot index"
			::= { topLlidVlanTrunkEntry 1 }

		
		-- 1.3.6.1.4.1.32285.11.2.3.7.1.3.1.2
		llidVlanTrunkPonIndex OBJECT-TYPE
			SYNTAX TopEPonPonIndex
			MAX-ACCESS not-accessible
			STATUS current
			DESCRIPTION
				"pon index"
			::= { topLlidVlanTrunkEntry 2 }

		
		-- 1.3.6.1.4.1.32285.11.2.3.7.1.3.1.3
		llidVlanTrunkMacIdx OBJECT-TYPE
			SYNTAX MacAddress
			MAX-ACCESS not-accessible
			STATUS current
			DESCRIPTION
				"MAC address"
			::= { topLlidVlanTrunkEntry 3 }

		
		-- 1.3.6.1.4.1.32285.11.2.3.7.1.3.1.4
		llidVlanTrunkVidBmp OBJECT-TYPE
			SYNTAX OCTET STRING (SIZE (512))
			MAX-ACCESS read-create
			STATUS current
			DESCRIPTION
				"Trunked Vlan List for the port
				INTERNETOCTETOCTET 0, OCTET 1, ...
				OCTETbitbit0bit1...bit7
				bitOCTETbitVLANVLAN ID0..4095
				bitVLAN 0,bitVLAN 4095
				bit"
			::= { topLlidVlanTrunkEntry 4 }

		
		-- 1.3.6.1.4.1.32285.11.2.3.7.1.3.1.5
		llidVlanTrunkRowStatus OBJECT-TYPE
			SYNTAX RowStatus
			MAX-ACCESS read-create
			STATUS current
			DESCRIPTION
				"add/del/set"
			::= { topLlidVlanTrunkEntry 5 }

		
		-- 1.3.6.1.4.1.32285.11.2.3.7.2
		topLlidQinQConfigGroup OBJECT-IDENTITY
			STATUS current
			DESCRIPTION 
				"llid-based vlan management."
			::= { topVlanMgmtObjects 2 }

		
		-- 1.3.6.1.4.1.32285.11.2.3.7.2.1
		topLlidQinQVlanTable OBJECT-TYPE
			SYNTAX SEQUENCE OF TopLlidQinQVlanEntry
			MAX-ACCESS not-accessible
			STATUS current
			DESCRIPTION
				"QinQ service based on VLAN for LLID"
			::= { topLlidQinQConfigGroup 1 }

		
		-- 1.3.6.1.4.1.32285.11.2.3.7.2.1.1
		topLlidQinQVlanEntry OBJECT-TYPE
			SYNTAX TopLlidQinQVlanEntry
			MAX-ACCESS not-accessible
			STATUS current
			DESCRIPTION
				"qinq based on llid config entry"
			INDEX { topLqVlanCardIndex, topLqVlanPonIndex, topLqVlanMacIndex, topLqVlanStartCVid, topLqVlanEndCVid
				 }
			::= { topLlidQinQVlanTable 1 }

		
		TopLlidQinQVlanEntry ::=
			SEQUENCE { 
				topLqVlanCardIndex
					TopEPonSlotIndex,
				topLqVlanPonIndex
					TopEPonPonIndex,
				topLqVlanMacIndex
					MacAddress,
				topLqVlanStartCVid
					INTEGER,
				topLqVlanEndCVid
					INTEGER,
				topLqVlanSVlan
					INTEGER,
				topLqVlanCosMode
					INTEGER,
				topLqVlanSCos
					INTEGER,
				topLqVlanOuterTpid
					INTEGER,
				topLqVlanRowStatus
					RowStatus
			 }

		-- 1.3.6.1.4.1.32285.11.2.3.7.2.1.1.1
		topLqVlanCardIndex OBJECT-TYPE
			SYNTAX TopEPonSlotIndex
			MAX-ACCESS not-accessible
			STATUS current
			DESCRIPTION
				"slot index"
			::= { topLlidQinQVlanEntry 1 }

		
		-- 1.3.6.1.4.1.32285.11.2.3.7.2.1.1.2
		topLqVlanPonIndex OBJECT-TYPE
			SYNTAX TopEPonPonIndex
			MAX-ACCESS not-accessible
			STATUS current
			DESCRIPTION
				"pon index"
			::= { topLlidQinQVlanEntry 2 }

		
		-- 1.3.6.1.4.1.32285.11.2.3.7.2.1.1.3
		topLqVlanMacIndex OBJECT-TYPE
			SYNTAX MacAddress
			MAX-ACCESS not-accessible
			STATUS current
			DESCRIPTION
				"ONU MAC, for a specific ONU"
			::= { topLlidQinQVlanEntry 3 }

		
		-- 1.3.6.1.4.1.32285.11.2.3.7.2.1.1.4
		topLqVlanStartCVid OBJECT-TYPE
			SYNTAX INTEGER (1..4094)
			MAX-ACCESS not-accessible
			STATUS current
			DESCRIPTION
				"The starting value"
			::= { topLlidQinQVlanEntry 4 }

		
		-- 1.3.6.1.4.1.32285.11.2.3.7.2.1.1.5
		topLqVlanEndCVid OBJECT-TYPE
			SYNTAX INTEGER (1..4094)
			MAX-ACCESS not-accessible
			STATUS current
			DESCRIPTION
				"The ending value"
			::= { topLlidQinQVlanEntry 5 }

		
		-- 1.3.6.1.4.1.32285.11.2.3.7.2.1.1.6
		topLqVlanSVlan OBJECT-TYPE
			SYNTAX INTEGER (1..4094)
			MAX-ACCESS read-create
			STATUS current
			DESCRIPTION
				"The outer VLAN id to be QinQed"
			::= { topLlidQinQVlanEntry 6 }

		
		-- 1.3.6.1.4.1.32285.11.2.3.7.2.1.1.7
		topLqVlanCosMode OBJECT-TYPE
			SYNTAX INTEGER
				{
				remark(1),
				copyFromCTag(2)
				}
			MAX-ACCESS read-create
			STATUS current
			DESCRIPTION
				"The SCoS value.
				remark(1) means to use the value from variable topLqVlanSCos.
				copyFromCTag(2) means to copy from CTAG."
			DEFVAL { 2 }
			::= { topLlidQinQVlanEntry 7 }

		
		-- 1.3.6.1.4.1.32285.11.2.3.7.2.1.1.8
		topLqVlanSCos OBJECT-TYPE
			SYNTAX INTEGER (0..7)
			MAX-ACCESS read-create
			STATUS current
			DESCRIPTION
				"The new STAG COS value if topLqVlanCosMode is selected as
				remark(1)"
			DEFVAL { 0 }
			::= { topLlidQinQVlanEntry 8 }

		
		-- 1.3.6.1.4.1.32285.11.2.3.7.2.1.1.9
		topLqVlanOuterTpid OBJECT-TYPE
			SYNTAX INTEGER
			MAX-ACCESS read-create
			STATUS current
			DESCRIPTION
				"value 0xFFFF means not to change the current TPID,
				otherwise modify it into this value."
			DEFVAL { '8100'h }
			::= { topLlidQinQVlanEntry 9 }

		
		-- 1.3.6.1.4.1.32285.11.2.3.7.2.1.1.10
		topLqVlanRowStatus OBJECT-TYPE
			SYNTAX RowStatus
			MAX-ACCESS read-create
			STATUS current
			DESCRIPTION
				"add/del/set"
			::= { topLlidQinQVlanEntry 10 }

		topOltVlanConfigTable OBJECT-TYPE
			SYNTAX SEQUENCE OF TopOltVlanConfigEntry
			MAX-ACCESS not-accessible
			STATUS current
			DESCRIPTION
				"OLT VLAN config table"
			::= { topVlanMgmtObjects 3 }

		
		-- 1.3.6.1.4.1.32285.11.2.3.7.3.1
		topOltVlanConfigEntry OBJECT-TYPE
			SYNTAX TopOltVlanConfigEntry
			MAX-ACCESS not-accessible
			STATUS current
			DESCRIPTION
				"OLT VLAN config entry"
			INDEX { topOltVlanIndex }
			::= { topOltVlanConfigTable 1 }

		
		TopOltVlanConfigEntry ::=
			SEQUENCE { 
				topOltVlanIndex
					INTEGER,
				topMcFloodMode
					INTEGER
			 }

		-- 1.3.6.1.4.1.32285.11.2.3.7.3.1.1
		topOltVlanIndex OBJECT-TYPE
			SYNTAX INTEGER (1..4094)
			MAX-ACCESS not-accessible
			STATUS current
			DESCRIPTION
				"Vlan id"
			::= { topOltVlanConfigEntry 1 }

		
		-- 1.3.6.1.4.1.32285.11.2.3.7.3.1.2
		topMcFloodMode OBJECT-TYPE
			SYNTAX INTEGER
				{
				all(1),
				unknown(2),
				none(3)
				}
			MAX-ACCESS read-write
			STATUS current
			DESCRIPTION
				"OLT vlan multicast flood mode
				all(1):all package flood
				unkonw(2):unknown package flood
				none(3): no package flood"
			DEFVAL { 3 }
			::= { topOltVlanConfigEntry 2 }

		
		-- 1.3.6.1.4.1.32285.11.2.3.7.4
		topOltVlanIntfGroup OBJECT-IDENTITY
			STATUS current
			DESCRIPTION 
				"vlan interface management."
			::= { topVlanMgmtObjects 4 }
			
		-- 1.3.6.1.4.1.32285.11.2.3.7.4.1
		topOltVifPriIpTable OBJECT-TYPE
			SYNTAX SEQUENCE OF TopOltVifPriIpEntry
			MAX-ACCESS not-accessible
			STATUS current
			DESCRIPTION
				"OLT VIF primary ip table."
			::= { topOltVlanIntfGroup 1 }
			
		-- 1.3.6.1.4.1.32285.11.2.3.7.4.1.1
		topOltVifPriIpEntry OBJECT-TYPE
			SYNTAX TopOltVifPriIpEntry
			MAX-ACCESS not-accessible
			STATUS current
			DESCRIPTION
				"OLT VIF primary ip entry."
			INDEX { topOltVifPriIpVlanIdx }
			::= { topOltVifPriIpTable 1 }
			
		TopOltVifPriIpEntry ::=
			SEQUENCE { 
				topOltVifPriIpVlanIdx
					INTEGER,
				topOltVifPriIpAddr
					IpAddress,
				topOltVifPriIpMask
					IpAddress,
				topOltVifPriIpRowStatus
					RowStatus
			 }
			 
		-- 1.3.6.1.4.1.32285.11.2.3.7.4.1.1.1
		topOltVifPriIpVlanIdx OBJECT-TYPE
			SYNTAX INTEGER (1..4094)
			MAX-ACCESS not-accessible
			STATUS current
			DESCRIPTION
				"VIF primary ip ,vlan index from 1 to 4094, but the max quanlity is 16."
			::= { topOltVifPriIpEntry 1 }
			
		-- 1.3.6.1.4.1.32285.11.2.3.7.4.1.1.2
		topOltVifPriIpAddr OBJECT-TYPE
			SYNTAX IpAddress
			MAX-ACCESS read-create
			STATUS current
			DESCRIPTION
				"vif primary ip address."
			::= { topOltVifPriIpEntry 2 }
			
		-- 1.3.6.1.4.1.32285.11.2.3.7.4.1.1.3
		topOltVifPriIpMask OBJECT-TYPE
			SYNTAX IpAddress
			MAX-ACCESS read-create
			STATUS current
			DESCRIPTION
				"vif primary ip mask."
			::= { topOltVifPriIpEntry 3 }
			
		-- 1.3.6.1.4.1.32285.11.2.3.7.4.1.1.4
		topOltVifPriIpRowStatus OBJECT-TYPE
			SYNTAX RowStatus
			MAX-ACCESS read-create
			STATUS current
			DESCRIPTION
				"create/delete/set"
			::= { topOltVifPriIpEntry 4 }
			
		-- 1.3.6.1.4.1.32285.11.2.3.7.4.2
		topOltVifSubIpTable OBJECT-TYPE
			SYNTAX SEQUENCE OF TopOltVifSubIpEntry
			MAX-ACCESS not-accessible
			STATUS current
			DESCRIPTION
				"OLT VIF sub IP table"
			::= { topOltVlanIntfGroup 2 }
			
		-- 1.3.6.1.4.1.32285.11.2.3.7.4.2.1
		topOltVifSubIpEntry OBJECT-TYPE
			SYNTAX TopOltVifSubIpEntry
			MAX-ACCESS not-accessible
			STATUS current
			DESCRIPTION
				"OLT VIF sub IP entry."
			INDEX { topOltVifSubIpVlanIdx, topOltVifSubIpSeqIdx }
			::= { topOltVifSubIpTable 1 }
			
		TopOltVifSubIpEntry ::=
			SEQUENCE { 
				topOltVifSubIpVlanIdx
					INTEGER,
				topOltVifSubIpSeqIdx
					INTEGER,
				topOltVifSubIpAddr
					IpAddress,
				topOltVifSubIpMask
					IpAddress,
				topOltVifSubIpRowStatus
					RowStatus
			 }
			 
		-- 1.3.6.1.4.1.32285.11.2.3.7.4.2.1.1
		topOltVifSubIpVlanIdx OBJECT-TYPE
			SYNTAX INTEGER (1..4094)
			MAX-ACCESS not-accessible
			STATUS current
			DESCRIPTION
				"VIF sub ip ,vlan index from 1 to 4094 ."
			::= { topOltVifSubIpEntry 1 }
			
		-- 1.3.6.1.4.1.32285.11.2.3.7.4.2.1.2
		topOltVifSubIpSeqIdx OBJECT-TYPE
			SYNTAX INTEGER (1..4)
			MAX-ACCESS not-accessible
			STATUS current
			DESCRIPTION
				"VIF sub ip,  sequence index from 1 to 4."
			::= { topOltVifSubIpEntry 2 }
			
		-- 1.3.6.1.4.1.32285.11.2.3.7.4.2.1.3
		topOltVifSubIpAddr OBJECT-TYPE
			SYNTAX IpAddress
			MAX-ACCESS read-create
			STATUS current
			DESCRIPTION
				"VIF sub IP address."
			::= { topOltVifSubIpEntry 3 }
			
		-- 1.3.6.1.4.1.32285.11.2.3.7.4.2.1.4
		topOltVifSubIpMask OBJECT-TYPE
			SYNTAX IpAddress
			MAX-ACCESS read-create
			STATUS current
			DESCRIPTION
				"vif sub ip mask."
			::= { topOltVifSubIpEntry 4 }
			
		-- 1.3.6.1.4.1.32285.11.2.3.7.4.2.1.5
		topOltVifSubIpRowStatus OBJECT-TYPE
			SYNTAX RowStatus
			MAX-ACCESS read-create
			STATUS current
			DESCRIPTION
				"create/delete/set."
			::= { topOltVifSubIpEntry 5 }
		
		-- 1.3.6.1.4.1.32285.11.2.3.7.5
		topOltVlanTransTable OBJECT-TYPE
			SYNTAX SEQUENCE OF TopOltVlanTransEntry
			MAX-ACCESS not-accessible
			STATUS current
			DESCRIPTION
				"Description."
			::= { topVlanMgmtObjects 5 }

		
		-- 1.3.6.1.4.1.32285.11.2.3.7.5.1
		topOltVlanTransEntry OBJECT-TYPE
			SYNTAX TopOltVlanTransEntry
			MAX-ACCESS not-accessible
			STATUS current
			DESCRIPTION
				"Description."
			INDEX { topOltVlanTransDeviceIndex, topOltVlanTransCardIndex, topOltVlanTransPortIndex }
			::= { topOltVlanTransTable 1 }

		
		TopOltVlanTransEntry ::=
			SEQUENCE { 
				topOltVlanTransDeviceIndex
					INTEGER,
				topOltVlanTransCardIndex
					TopEPonSlotIndex,
				topOltVlanTransPortIndex
					TopEPonPonIndex,
				topOltVlanTransVidList
					OCTET STRING,
				topOltVlanTransVidModeList
					OCTET STRING,
				topOltVlanTransRowStatus
					RowStatus
			 }

		-- 1.3.6.1.4.1.32285.11.2.3.7.5.1.1
		topOltVlanTransDeviceIndex OBJECT-TYPE
			SYNTAX INTEGER
			MAX-ACCESS not-accessible
			STATUS current
			DESCRIPTION
				"Device index."
			::= { topOltVlanTransEntry 1 }

		
		-- 1.3.6.1.4.1.32285.11.2.3.7.5.1.2
		topOltVlanTransCardIndex OBJECT-TYPE
			SYNTAX TopEPonSlotIndex
			MAX-ACCESS not-accessible
			STATUS current
			DESCRIPTION
				"Slot index."
			::= { topOltVlanTransEntry 2 }

		
		-- 1.3.6.1.4.1.32285.11.2.3.7.5.1.3
		topOltVlanTransPortIndex OBJECT-TYPE
			SYNTAX TopEPonPonIndex
			MAX-ACCESS not-accessible
			STATUS current
			DESCRIPTION
				"Pon index."
			::= { topOltVlanTransEntry 3 }

		
		-- 1.3.6.1.4.1.32285.11.2.3.7.5.1.4
		topOltVlanTransVidList OBJECT-TYPE
			SYNTAX OCTET STRING (SIZE (512))
			MAX-ACCESS read-write
			STATUS current
			DESCRIPTION
				"Transparent vlan list, bit map, as same as olt vlan table."
			::= { topOltVlanTransEntry 4 }

		
		-- 1.3.6.1.4.1.32285.11.2.3.7.5.1.5
		topOltVlanTransVidModeList OBJECT-TYPE
			SYNTAX OCTET STRING (SIZE (512))
			MAX-ACCESS read-write
			STATUS current
			DESCRIPTION
				"vlan mode, tag or untag, set 0 tag, set 1 untag, also bitmap,
				 if one vlan doesn't be set in topOltVlanTransVidList, 
				 its bit in topOltVlanTransVidModeList does not work."
			::= { topOltVlanTransEntry 5 }

		
		-- 1.3.6.1.4.1.32285.11.2.3.7.5.1.6
		topOltVlanTransRowStatus OBJECT-TYPE
			SYNTAX RowStatus
			MAX-ACCESS read-create
			STATUS current
			DESCRIPTION
				"creat/set/del."
			::= { topOltVlanTransEntry 6 }

		
		-- 1.3.6.1.4.1.32285.11.2.3.7.6
		topLoopbackObjects OBJECT IDENTIFIER ::= { topVlanMgmtObjects 6 }

		
		-- 1.3.6.1.4.1.32285.11.2.3.7.6.1
		topLoopbackConfigTable OBJECT-TYPE
			SYNTAX SEQUENCE OF TopLoopbackConfigEntry
			MAX-ACCESS not-accessible
			STATUS current
			DESCRIPTION
				"LoopBack config table."
			::= { topLoopbackObjects 1 }

		
		-- 1.3.6.1.4.1.32285.11.2.3.7.6.1.1
		topLoopbackConfigEntry OBJECT-TYPE
			SYNTAX TopLoopbackConfigEntry
			MAX-ACCESS not-accessible
			STATUS current
			DESCRIPTION
				"LoopBack config entry."
			INDEX { topLoopbackIndex }
			::= { topLoopbackConfigTable 1 }

		
		TopLoopbackConfigEntry ::=
			SEQUENCE { 
				topLoopbackIndex
					INTEGER,
				topLoopbackPriIpAddr
					IpAddress,
				topLoopbackPriMask
					IpAddress,
				topLoopbackPriMac
					MacAddress,
				topLoopbackRowStatus
					RowStatus
			 }

		-- 1.3.6.1.4.1.32285.11.2.3.7.6.1.1.1
		topLoopbackIndex OBJECT-TYPE
			SYNTAX INTEGER (1..8)
			MAX-ACCESS not-accessible
			STATUS current
			DESCRIPTION
				"LoopBack interface index from 1 to 8, but the max quanlity is 8."
			::= { topLoopbackConfigEntry 1 }

		
		-- 1.3.6.1.4.1.32285.11.2.3.7.6.1.1.2
		topLoopbackPriIpAddr OBJECT-TYPE
			SYNTAX IpAddress
			MAX-ACCESS read-write
			STATUS current
			DESCRIPTION
				"LoopBack primary ip address."
			::= { topLoopbackConfigEntry 2 }

		
		-- 1.3.6.1.4.1.32285.11.2.3.7.6.1.1.3
		topLoopbackPriMask OBJECT-TYPE
			SYNTAX IpAddress
			MAX-ACCESS read-write
			STATUS current
			DESCRIPTION
				"LoopBack primary ip mask."
			::= { topLoopbackConfigEntry 3 }

		
		-- 1.3.6.1.4.1.32285.11.2.3.7.6.1.1.4
		topLoopbackPriMac OBJECT-TYPE
			SYNTAX MacAddress
			MAX-ACCESS read-only
			STATUS deprecated
			DESCRIPTION
				"LoopBack primary MAC."
			::= { topLoopbackConfigEntry 4 }

		
		-- 1.3.6.1.4.1.32285.11.2.3.7.6.1.1.5
		topLoopbackRowStatus OBJECT-TYPE
			SYNTAX RowStatus
			MAX-ACCESS read-create
			STATUS current
			DESCRIPTION
				"create/delete/set"
			::= { topLoopbackConfigEntry 5 }

		
		-- 1.3.6.1.4.1.32285.11.2.3.7.6.2
		topLoopbackSubIpTable OBJECT-TYPE
			SYNTAX SEQUENCE OF TopLoopbackSubIpEntry
			MAX-ACCESS not-accessible
			STATUS current
			DESCRIPTION
				"OLT LoopBack sub IP table."
			::= { topLoopbackObjects 2 }

		
		-- 1.3.6.1.4.1.32285.11.2.3.7.6.2.1
		topLoopbackSubIpEntry OBJECT-TYPE
			SYNTAX TopLoopbackSubIpEntry
			MAX-ACCESS not-accessible
			STATUS current
			DESCRIPTION
				"OLT LoopBack sub IP entry."
			INDEX { topLoopbackSubIpIdx, topLoopbackSubIpSeqIdx }
			::= { topLoopbackSubIpTable 1 }

		
		TopLoopbackSubIpEntry ::=
			SEQUENCE { 
				topLoopbackSubIpIdx
					INTEGER,
				topLoopbackSubIpSeqIdx
					INTEGER,
				topLoopbackSubIpAddr
					IpAddress,
				topLoopbackSubMask
					IpAddress,
				topLoopbackSubMac
					MacAddress,
				topLoopbackSubIpRowStatus
					RowStatus
			 }

		-- 1.3.6.1.4.1.32285.11.2.3.7.6.2.1.1
		topLoopbackSubIpIdx OBJECT-TYPE
			SYNTAX INTEGER (1..8)
			MAX-ACCESS not-accessible
			STATUS current
			DESCRIPTION
				"LoopBack interface index from 1 to 8, but the max quanlity is 8."
			::= { topLoopbackSubIpEntry 1 }

		
		-- 1.3.6.1.4.1.32285.11.2.3.7.6.2.1.2
		topLoopbackSubIpSeqIdx OBJECT-TYPE
			SYNTAX INTEGER (1..20)
			MAX-ACCESS not-accessible
			STATUS current
			DESCRIPTION
				"LoopBack sub ip,  sequence index from 1 to 20."
			::= { topLoopbackSubIpEntry 2 }

		
		-- 1.3.6.1.4.1.32285.11.2.3.7.6.2.1.3
		topLoopbackSubIpAddr OBJECT-TYPE
			SYNTAX IpAddress
			MAX-ACCESS read-write
			STATUS current
			DESCRIPTION
				"LoopBack sub IP address."
			::= { topLoopbackSubIpEntry 3 }

		
		-- 1.3.6.1.4.1.32285.11.2.3.7.6.2.1.4
		topLoopbackSubMask OBJECT-TYPE
			SYNTAX IpAddress
			MAX-ACCESS read-write
			STATUS current
			DESCRIPTION
				"LoopBack sub IP mask."
			::= { topLoopbackSubIpEntry 4 }

		
		-- 1.3.6.1.4.1.32285.11.2.3.7.6.2.1.5
		topLoopbackSubMac OBJECT-TYPE
			SYNTAX MacAddress
			MAX-ACCESS read-only
			STATUS deprecated
			DESCRIPTION
				"LoopBack sub MAC."
			::= { topLoopbackSubIpEntry 5 }

		
		-- 1.3.6.1.4.1.32285.11.2.3.7.6.2.1.6
		topLoopbackSubIpRowStatus OBJECT-TYPE
			SYNTAX RowStatus
			MAX-ACCESS read-create
			STATUS current
			DESCRIPTION
				"create/delete/set"
			::= { topLoopbackSubIpEntry 6 }

		
		-- 1.3.6.1.4.1.32285.11.2.3.7.7
		topUniVlanObjects OBJECT IDENTIFIER ::= { topVlanMgmtObjects 7 }

		
		-- 1.3.6.1.4.1.32285.11.2.3.7.7.1
		topUniVlanProfileTable OBJECT-TYPE
			SYNTAX SEQUENCE OF TopUniVlanProfileEntry
			MAX-ACCESS not-accessible
			STATUS current
			DESCRIPTION
				"Description."
			::= { topUniVlanObjects 1 }

		
		-- 1.3.6.1.4.1.32285.11.2.3.7.7.1.1
		topUniVlanProfileEntry OBJECT-TYPE
			SYNTAX TopUniVlanProfileEntry
			MAX-ACCESS not-accessible
			STATUS current
			DESCRIPTION
				"Description."
			INDEX { topUniVlanProfileIndex }
			::= { topUniVlanProfileTable 1 }

		
		TopUniVlanProfileEntry ::=
			SEQUENCE { 
				topUniVlanProfileIndex
					INTEGER,
				topUniVlanProfileRefCnt
					INTEGER,
				topUniVlanProfileName
					OCTET STRING,
				topUniVlanProfileMode
					INTEGER,
				topUniVlanProfileRowstatus
					RowStatus
			 }

		-- 1.3.6.1.4.1.32285.11.2.3.7.7.1.1.1
		topUniVlanProfileIndex OBJECT-TYPE
			SYNTAX INTEGER (1..4094)
			MAX-ACCESS not-accessible
			STATUS current
			DESCRIPTION
				"1-4094 vlan-profile."
			::= { topUniVlanProfileEntry 1 }

		
		-- 1.3.6.1.4.1.32285.11.2.3.7.7.1.1.2
		topUniVlanProfileRefCnt OBJECT-TYPE
			SYNTAX INTEGER
			MAX-ACCESS read-only
			STATUS current
			DESCRIPTION
				"Description."
			::= { topUniVlanProfileEntry 2 }

		
		-- 1.3.6.1.4.1.32285.11.2.3.7.7.1.1.3
		topUniVlanProfileName OBJECT-TYPE
			SYNTAX OCTET STRING (SIZE (1..31))
			MAX-ACCESS read-write
			STATUS current
			DESCRIPTION
				"Description."
			::= { topUniVlanProfileEntry 3 }

		
		-- 1.3.6.1.4.1.32285.11.2.3.7.7.1.1.4
		topUniVlanProfileMode OBJECT-TYPE
			SYNTAX INTEGER
				{
				none(0),
				transparent(1),
				tag(2),
				translate(3),
				agg(4),
				trunk(5)
				}
			MAX-ACCESS read-write
			STATUS current
			DESCRIPTION
				"Description."
			DEFVAL { 0 }
			::= { topUniVlanProfileEntry 4 }

		
		-- 1.3.6.1.4.1.32285.11.2.3.7.7.1.1.5
		topUniVlanProfileRowstatus OBJECT-TYPE
			SYNTAX RowStatus
			MAX-ACCESS read-create
			STATUS current
			DESCRIPTION
				"Description."
			::= { topUniVlanProfileEntry 5 }

		
		-- 1.3.6.1.4.1.32285.11.2.3.7.7.2
		topUniVlanRuleTable OBJECT-TYPE
			SYNTAX SEQUENCE OF TopUniVlanRuleEntry
			MAX-ACCESS not-accessible
			STATUS current
			DESCRIPTION
				"Description."
			::= { topUniVlanObjects 2 }

		
		-- 1.3.6.1.4.1.32285.11.2.3.7.7.2.1
		topUniVlanRuleEntry OBJECT-TYPE
			SYNTAX TopUniVlanRuleEntry
			MAX-ACCESS not-accessible
			STATUS current
			DESCRIPTION
				"Description."
			INDEX { topUniVlanRuleProfileIndex, topUniVlanRuleIndex }
			::= { topUniVlanRuleTable 1 }

		
		TopUniVlanRuleEntry ::=
			SEQUENCE { 
				topUniVlanRuleProfileIndex
					INTEGER,
				topUniVlanRuleIndex
					INTEGER,
				topUniVlanRuleMode
					INTEGER,
				topUniVlanRuleCvlan
					OCTET STRING,
				topUniVlanRuleSvlan
					INTEGER,
				topUniVlanRuleRowstatus
					RowStatus
			 }

		-- 1.3.6.1.4.1.32285.11.2.3.7.7.2.1.1
		topUniVlanRuleProfileIndex OBJECT-TYPE
			SYNTAX INTEGER (1..4094)
			MAX-ACCESS not-accessible
			STATUS current
			DESCRIPTION
				"Description."
			::= { topUniVlanRuleEntry 1 }

		
		-- 1.3.6.1.4.1.32285.11.2.3.7.7.2.1.2
		topUniVlanRuleIndex OBJECT-TYPE
			SYNTAX INTEGER (1..8)
			MAX-ACCESS not-accessible
			STATUS current
			DESCRIPTION
				"Description."
			::= { topUniVlanRuleEntry 2 }

		
		-- 1.3.6.1.4.1.32285.11.2.3.7.7.2.1.3
		topUniVlanRuleMode OBJECT-TYPE
			SYNTAX INTEGER
				{
				none(0),
				transparent(1),
				tag(2),
				translate(3),
				agg(4),
				trunk(5)
				}
			MAX-ACCESS read-write
			STATUS current
			DESCRIPTION
				"Description."
			DEFVAL { 0 }
			::= { topUniVlanRuleEntry 3 }

		
		-- 1.3.6.1.4.1.32285.11.2.3.7.7.2.1.4
		topUniVlanRuleCvlan OBJECT-TYPE
			SYNTAX OCTET STRING (SIZE (16))
			MAX-ACCESS read-write
			STATUS current
			DESCRIPTION
				"Tow bytes is a representative of vlan-id."
			::= { topUniVlanRuleEntry 4 }

		
		-- 1.3.6.1.4.1.32285.11.2.3.7.7.2.1.5
		topUniVlanRuleSvlan OBJECT-TYPE
			SYNTAX INTEGER (1..4094)
			MAX-ACCESS read-write
			STATUS current
			DESCRIPTION
				"Description."
			::= { topUniVlanRuleEntry 5 }

		
		-- 1.3.6.1.4.1.32285.11.2.3.7.7.2.1.6
		topUniVlanRuleRowstatus OBJECT-TYPE
			SYNTAX RowStatus
			MAX-ACCESS read-create
			STATUS current
			DESCRIPTION
				"Description."
			::= { topUniVlanRuleEntry 6 }

		
		-- 1.3.6.1.4.1.32285.11.2.3.7.7.3
		topUniVlanBindTable OBJECT-TYPE
			SYNTAX SEQUENCE OF TopUniVlanBindEntry
			MAX-ACCESS not-accessible
			STATUS current
			DESCRIPTION
				"Description."
			::= { topUniVlanObjects 3 }

		
		-- 1.3.6.1.4.1.32285.11.2.3.7.7.3.1
		topUniVlanBindEntry OBJECT-TYPE
			SYNTAX TopUniVlanBindEntry
			MAX-ACCESS not-accessible
			STATUS current
			DESCRIPTION
				"Description."
			INDEX { topUniVlanBindSlotIndex, topUniVlanBindPonIndex, topUniVlanBindOnuIndex, topUniVlanBindUniIndex }
			::= { topUniVlanBindTable 1 }

		
		TopUniVlanBindEntry ::=
			SEQUENCE { 
				topUniVlanBindSlotIndex
					INTEGER,
				topUniVlanBindPonIndex
					INTEGER,
				topUniVlanBindOnuIndex
					INTEGER,
				topUniVlanBindUniIndex
					INTEGER,
				topUniVlanBindPvid
					INTEGER,
				topUniVlanBindProfileId
					INTEGER,
				topUniVlanBindProfAttr
					INTEGER
			 }

		-- 1.3.6.1.4.1.32285.11.2.3.7.7.3.1.1
		topUniVlanBindSlotIndex OBJECT-TYPE
			SYNTAX INTEGER
			MAX-ACCESS not-accessible
			STATUS current
			DESCRIPTION
				"Description."
			::= { topUniVlanBindEntry 1 }

		
		-- 1.3.6.1.4.1.32285.11.2.3.7.7.3.1.2
		topUniVlanBindPonIndex OBJECT-TYPE
			SYNTAX INTEGER
			MAX-ACCESS not-accessible
			STATUS current
			DESCRIPTION
				"Description."
			::= { topUniVlanBindEntry 2 }

		
		-- 1.3.6.1.4.1.32285.11.2.3.7.7.3.1.3
		topUniVlanBindOnuIndex OBJECT-TYPE
			SYNTAX INTEGER
			MAX-ACCESS not-accessible
			STATUS current
			DESCRIPTION
				"Description."
			::= { topUniVlanBindEntry 3 }

		
		-- 1.3.6.1.4.1.32285.11.2.3.7.7.3.1.4
		topUniVlanBindUniIndex OBJECT-TYPE
			SYNTAX INTEGER
			MAX-ACCESS not-accessible
			STATUS current
			DESCRIPTION
				"Description."
			::= { topUniVlanBindEntry 4 }

		
		-- 1.3.6.1.4.1.32285.11.2.3.7.7.3.1.5
		topUniVlanBindPvid OBJECT-TYPE
			SYNTAX INTEGER
			MAX-ACCESS read-write
			STATUS current
			DESCRIPTION
				"Description."
			DEFVAL { 1 }
			::= { topUniVlanBindEntry 5 }

		
		-- 1.3.6.1.4.1.32285.11.2.3.7.7.3.1.6
		topUniVlanBindProfileId OBJECT-TYPE
			SYNTAX INTEGER (0..4094)
			MAX-ACCESS read-write
			STATUS current
			DESCRIPTION
				"Description."
			DEFVAL { 0 }
			::= { topUniVlanBindEntry 6 }

		
		-- 1.3.6.1.4.1.32285.11.2.3.7.7.3.1.7
		topUniVlanBindProfAttr OBJECT-TYPE
			SYNTAX INTEGER
				{
				default(1),
				non-default(2)
				}
			MAX-ACCESS read-only
			STATUS current
			DESCRIPTION
				"Description."
			::= { topUniVlanBindEntry 7 }

		
		-- 1.3.6.1.4.1.32285.11.2.3.7.8
		topOnuVlanObjects OBJECT IDENTIFIER ::= { topVlanMgmtObjects 8 }

		
		-- 1.3.6.1.4.1.32285.11.2.3.7.8.1
		topOnuQinQTable OBJECT-TYPE
			SYNTAX SEQUENCE OF TopOnuQinQEntry
			MAX-ACCESS not-accessible
			STATUS current
			DESCRIPTION
				"Description."
			::= { topOnuVlanObjects 1 }

		
		-- 1.3.6.1.4.1.32285.11.2.3.7.8.1.1
		topOnuQinQEntry OBJECT-TYPE
			SYNTAX TopOnuQinQEntry
			MAX-ACCESS not-accessible
			STATUS current
			DESCRIPTION
				"Description."
			INDEX { topOnuQinQSlotIndex, topOnuQinQPonIndex, topOnuQinQOnuIndex, topOnuQinQStartVlanId, topOnuQinQEndVlanId
				 }
			::= { topOnuQinQTable 1 }

		
		TopOnuQinQEntry ::=
			SEQUENCE { 
				topOnuQinQSlotIndex
					INTEGER,
				topOnuQinQPonIndex
					INTEGER,
				topOnuQinQOnuIndex
					INTEGER,
				topOnuQinQStartVlanId
					INTEGER,
				topOnuQinQEndVlanId
					INTEGER,
				topOnuQinQSVlanId
					INTEGER,
				topOnuQinQSTagCosDetermine
					INTEGER,
				topOnuQinQSTagCosNewValue
					INTEGER,
				topOnuQinQRowStatus
					RowStatus
			 }

		-- 1.3.6.1.4.1.32285.11.2.3.7.8.1.1.1
		topOnuQinQSlotIndex OBJECT-TYPE
			SYNTAX INTEGER
			MAX-ACCESS not-accessible
			STATUS current
			DESCRIPTION
				"Description."
			::= { topOnuQinQEntry 1 }

		
		-- 1.3.6.1.4.1.32285.11.2.3.7.8.1.1.2
		topOnuQinQPonIndex OBJECT-TYPE
			SYNTAX INTEGER
			MAX-ACCESS not-accessible
			STATUS current
			DESCRIPTION
				"Description."
			::= { topOnuQinQEntry 2 }

		
		-- 1.3.6.1.4.1.32285.11.2.3.7.8.1.1.3
		topOnuQinQOnuIndex OBJECT-TYPE
			SYNTAX INTEGER
			MAX-ACCESS not-accessible
			STATUS current
			DESCRIPTION
				"Description."
			::= { topOnuQinQEntry 3 }

		
		-- 1.3.6.1.4.1.32285.11.2.3.7.8.1.1.4
		topOnuQinQStartVlanId OBJECT-TYPE
			SYNTAX INTEGER (1..4094)
			MAX-ACCESS not-accessible
			STATUS current
			DESCRIPTION
				"Description."
			::= { topOnuQinQEntry 4 }

		
		-- 1.3.6.1.4.1.32285.11.2.3.7.8.1.1.5
		topOnuQinQEndVlanId OBJECT-TYPE
			SYNTAX INTEGER (1..4094)
			MAX-ACCESS not-accessible
			STATUS current
			DESCRIPTION
				"Description."
			::= { topOnuQinQEntry 5 }

		
		-- 1.3.6.1.4.1.32285.11.2.3.7.8.1.1.6
		topOnuQinQSVlanId OBJECT-TYPE
			SYNTAX INTEGER (1..4094)
			MAX-ACCESS read-create
			STATUS current
			DESCRIPTION
				"Description."
			::= { topOnuQinQEntry 6 }

		
		-- 1.3.6.1.4.1.32285.11.2.3.7.8.1.1.7
		topOnuQinQSTagCosDetermine OBJECT-TYPE
			SYNTAX INTEGER
				{
				redefine(1),
				copyFromCTag(2)
				}
			MAX-ACCESS read-create
			STATUS current
			DESCRIPTION
				"What STAG COS will be set for this QinQ instance. It could be either a new definition or copied from CTAG."
			::= { topOnuQinQEntry 7 }

		
		-- 1.3.6.1.4.1.32285.11.2.3.7.8.1.1.8
		topOnuQinQSTagCosNewValue OBJECT-TYPE
			SYNTAX INTEGER (0..7)
			MAX-ACCESS read-create
			STATUS current
			DESCRIPTION
				"The new STAG COS value if pqSTagCosDetermine is selected as redefine(1)."
			DEFVAL { 0 }
			::= { topOnuQinQEntry 8 }

		
		-- 1.3.6.1.4.1.32285.11.2.3.7.8.1.1.9
		topOnuQinQRowStatus OBJECT-TYPE
			SYNTAX RowStatus
			MAX-ACCESS read-create
			STATUS current
			DESCRIPTION
				"Description."
			::= { topOnuQinQEntry 9 }

		

		-- 1.3.6.1.4.1.32285.11.2.3.9
		topPerfStatObjects OBJECT IDENTIFIER ::= { topvisionEponTree 9 }

		
		-- 1.3.6.1.4.1.32285.11.2.3.9.1
		topPerfStatGlobalSet OBJECT-IDENTITY
			STATUS current
			DESCRIPTION 
				"global config"
			::= { topPerfStatObjects 1 }

		
		-- 1.3.6.1.4.1.32285.11.2.3.9.1.1
		topPerfStatOLTCycle OBJECT-TYPE
			SYNTAX INTEGER (5..900)
			UNITS "seconds"
			MAX-ACCESS read-write
			STATUS deprecated
			DESCRIPTION
				"OLT performace statistic time interval. unit: seconds"
			DEFVAL { 10 }
			::= { topPerfStatGlobalSet 1 }

		
		-- 1.3.6.1.4.1.32285.11.2.3.9.1.2
		topPerfStatONUCycle OBJECT-TYPE
			SYNTAX INTEGER (5..900)
			UNITS "seconds"
			MAX-ACCESS read-write
			STATUS deprecated
			DESCRIPTION
				"ONU performace statistic time interval. unit: seconds"
			DEFVAL { 10 }
			::= { topPerfStatGlobalSet 2 }

		
		-- 1.3.6.1.4.1.32285.11.2.3.9.1.3
		topPerfOLTTemperatureCycle OBJECT-TYPE
			SYNTAX INTEGER (1..10)
			MAX-ACCESS read-write
			STATUS current
			DESCRIPTION
				"OLT temperature sampling time interval. unit: seconds"
			DEFVAL { 10 }
			::= { topPerfStatGlobalSet 3 }

		
		-- 1.3.6.1.4.1.32285.11.2.3.9.1.4
		topPerfONUTemperatureCycle OBJECT-TYPE
			SYNTAX INTEGER (1..10)
			MAX-ACCESS read-write
			STATUS current
			DESCRIPTION
				"ONU temperature sampling time interval. unit: seconds"
			DEFVAL { 10 }
			::= { topPerfStatGlobalSet 4 }

		
		-- 1.3.6.1.4.1.32285.11.2.3.9.2
		topPerfThresholdTypeTable OBJECT-TYPE
			SYNTAX SEQUENCE OF TopPerfThresholdTypeEntry
			MAX-ACCESS not-accessible
			STATUS current
			DESCRIPTION
				"performance stata based on object type"
			::= { topPerfStatObjects 2 }

		
		-- 1.3.6.1.4.1.32285.11.2.3.9.2.1
		topPerfThresholdTypeEntry OBJECT-TYPE
			SYNTAX TopPerfThresholdTypeEntry
			MAX-ACCESS not-accessible
			STATUS current
			DESCRIPTION
				"performance statistic based on object type"
			INDEX { topPerfThresholdTypeIndex, topPerfThresholdObject }
			::= { topPerfThresholdTypeTable 1 }

		
		TopPerfThresholdTypeEntry ::=
			SEQUENCE { 
				topPerfThresholdTypeIndex
					TopEponStatsThresholdType,
				topPerfThresholdObject
					INTEGER,
				topPerfThresholdUpper
					Counter64,
				topPerfThresholdLower
					Counter64
			 }

		-- 1.3.6.1.4.1.32285.11.2.3.9.2.1.1
		topPerfThresholdTypeIndex OBJECT-TYPE
			SYNTAX TopEponStatsThresholdType
			MAX-ACCESS not-accessible
			STATUS current
			DESCRIPTION
				"performace threshold type"
			::= { topPerfThresholdTypeEntry 1 }

		
		-- 1.3.6.1.4.1.32285.11.2.3.9.2.1.2
		topPerfThresholdObject OBJECT-TYPE
			SYNTAX INTEGER
				{
				sni(1),
				pon(2),
				onupon(3),
				uni(4)
				}
			MAX-ACCESS not-accessible
			STATUS current
			DESCRIPTION
				"performace threshold object"
			::= { topPerfThresholdTypeEntry 2 }

		
		-- 1.3.6.1.4.1.32285.11.2.3.9.2.1.3
		topPerfThresholdUpper OBJECT-TYPE
			SYNTAX Counter64
			MAX-ACCESS read-write
			STATUS current
			DESCRIPTION
				" "
			::= { topPerfThresholdTypeEntry 3 }

		
		-- 1.3.6.1.4.1.32285.11.2.3.9.2.1.4
		topPerfThresholdLower OBJECT-TYPE
			SYNTAX Counter64
			MAX-ACCESS read-write
			STATUS current
			DESCRIPTION
				" "
			::= { topPerfThresholdTypeEntry 4 }

		
		-- 1.3.6.1.4.1.32285.11.2.3.9.3
		topPerfTemperatureThresholdTable OBJECT-TYPE
			SYNTAX SEQUENCE OF TopPerfTemperatureThresholdEntry
			MAX-ACCESS not-accessible
			STATUS current
			DESCRIPTION
				"performance stata based on object type"
			::= { topPerfStatObjects 3 }

		
		-- 1.3.6.1.4.1.32285.11.2.3.9.3.1
		topPerfTemperatureThresholdEntry OBJECT-TYPE
			SYNTAX TopPerfTemperatureThresholdEntry
			MAX-ACCESS not-accessible
			STATUS current
			DESCRIPTION
				"temperature stat based on object type"
			INDEX { topPerfTemperatureThresholdTypeIdx, topPerfTemperatureThresholdObject }
			::= { topPerfTemperatureThresholdTable 1 }

		
		TopPerfTemperatureThresholdEntry ::=
			SEQUENCE { 
				topPerfTemperatureThresholdTypeIdx
					TopEponStatsThresholdType,
				topPerfTemperatureThresholdObject
					INTEGER,
				topPerfTemperatureThresholdUpper
					INTEGER,
				topPerfTemperatureThresholdLower
					INTEGER
			 }

		-- 1.3.6.1.4.1.32285.11.2.3.9.3.1.1
		topPerfTemperatureThresholdTypeIdx OBJECT-TYPE
			SYNTAX TopEponStatsThresholdType
			MAX-ACCESS not-accessible
			STATUS current
			DESCRIPTION
				"performace threshold type"
			::= { topPerfTemperatureThresholdEntry 1 }

		
		-- 1.3.6.1.4.1.32285.11.2.3.9.3.1.2
		topPerfTemperatureThresholdObject OBJECT-TYPE
			SYNTAX INTEGER
				{
				reserved(0),
				mpuBoard(1),
				ponBoard(2),
				uplinkBoard(3),
				onu(4)
				}
			MAX-ACCESS not-accessible
			STATUS current
			DESCRIPTION
				"performace threshold"
			::= { topPerfTemperatureThresholdEntry 2 }

		
		-- 1.3.6.1.4.1.32285.11.2.3.9.3.1.3
		topPerfTemperatureThresholdUpper OBJECT-TYPE
			SYNTAX INTEGER
			MAX-ACCESS read-write
			STATUS current
			DESCRIPTION
				" "
			::= { topPerfTemperatureThresholdEntry 3 }

		
		-- 1.3.6.1.4.1.32285.11.2.3.9.3.1.4
		topPerfTemperatureThresholdLower OBJECT-TYPE
			SYNTAX INTEGER
			MAX-ACCESS read-write
			STATUS current
			DESCRIPTION
				" "
			::= { topPerfTemperatureThresholdEntry 4 }

		

		-- 1.3.6.1.4.1.32285.11.2.3.9.4
		topPerfStatThresholdTable OBJECT-TYPE
			SYNTAX SEQUENCE OF TopPerfStatThresholdEntry
			MAX-ACCESS not-accessible
			STATUS current
			DESCRIPTION
				"Description."
			::= { topPerfStatObjects 4 }

		

		-- 1.3.6.1.4.1.32285.11.2.3.9.4.1
		topPerfStatThresholdEntry OBJECT-TYPE
			SYNTAX TopPerfStatThresholdEntry
			MAX-ACCESS not-accessible
			STATUS current
			DESCRIPTION
				"Description."
			INDEX { topPerfStatThrTypeIdx, topPerfStatThrDeviceIdx, topPerfStatThrSlotIdx, topPerfStatThrPortIdx, topPerfStatThrOnuIdx, 
				topPerfStatThrUniIdx, topPerfStatThrIdx }
			::= { topPerfStatThresholdTable 1 }

		
		TopPerfStatThresholdEntry ::=
			SEQUENCE { 
				topPerfStatThrTypeIdx
					INTEGER,
				topPerfStatThrDeviceIdx
					EponDeviceIndex,
				topPerfStatThrSlotIdx
					TopEPonSlotIndex,
				topPerfStatThrPortIdx
					TopEPonPonIndex,
				topPerfStatThrOnuIdx
					TopEPonOnuAuthNum,
				topPerfStatThrUniIdx
					TopEPonUniPortIndex,
				topPerfStatThrIdx
					INTEGER,
				topPerfStatThrUpper
					Counter64,
				topPerfStatThrLower
					Counter64
			 }

		-- 1.3.6.1.4.1.32285.11.2.3.9.4.1.1
		topPerfStatThrTypeIdx OBJECT-TYPE
			SYNTAX INTEGER
			MAX-ACCESS not-accessible
			STATUS current
			DESCRIPTION
				"The first 16 bit: 1-current,2-15 minutes,3-24 hours;
				 the last 16 bit:0-ETH 1-OLT PON,2-ONU PON,3-ONU UNI,
				 4-OLT TEMPERATURE,5-ONU TEMPERATURE, 6-OLT-GPON, 7-ONU-GPON."
			::= { topPerfStatThresholdEntry 1 }

		

		-- 1.3.6.1.4.1.32285.11.2.3.9.4.1.2
		topPerfStatThrDeviceIdx OBJECT-TYPE
			SYNTAX EponDeviceIndex
			MAX-ACCESS not-accessible
			STATUS current
			DESCRIPTION
				"The default Value is 1."
			::= { topPerfStatThresholdEntry 2 }

		
		-- 1.3.6.1.4.1.32285.11.2.3.9.4.1.3
		topPerfStatThrSlotIdx OBJECT-TYPE
			SYNTAX TopEPonSlotIndex
			MAX-ACCESS not-accessible
			STATUS current
			DESCRIPTION
				"Slot ID."
			::= { topPerfStatThresholdEntry 3 }

		

		-- 1.3.6.1.4.1.32285.11.2.3.9.4.1.4
		topPerfStatThrPortIdx OBJECT-TYPE
			SYNTAX TopEPonPonIndex
			MAX-ACCESS not-accessible
			STATUS current
			DESCRIPTION
				"PON Port ID."
			::= { topPerfStatThresholdEntry 4 }

		

		-- 1.3.6.1.4.1.32285.11.2.3.9.4.1.5
		topPerfStatThrOnuIdx OBJECT-TYPE
			SYNTAX TopEPonOnuAuthNum
			MAX-ACCESS not-accessible
			STATUS current
			DESCRIPTION
				"ONU ID."
			::= { topPerfStatThresholdEntry 5 }

		

		-- 1.3.6.1.4.1.32285.11.2.3.9.4.1.6
		topPerfStatThrUniIdx OBJECT-TYPE
			SYNTAX TopEPonUniPortIndex
			MAX-ACCESS not-accessible
			STATUS current
			DESCRIPTION
				"UNI Port ID."
			::= { topPerfStatThresholdEntry 6 }

		
		-- 1.3.6.1.4.1.32285.11.2.3.9.4.1.7
		topPerfStatThrIdx OBJECT-TYPE
			SYNTAX INTEGER
			MAX-ACCESS not-accessible
			STATUS current
			DESCRIPTION
				"Statistics index:1-44;temperature index:1."
			::= { topPerfStatThresholdEntry 7 }

		

		-- 1.3.6.1.4.1.32285.11.2.3.9.4.1.8
		topPerfStatThrUpper OBJECT-TYPE
			SYNTAX Counter64
			MAX-ACCESS read-write
			STATUS current
			DESCRIPTION
				"Statistics or temperature upper threshold."
			::= { topPerfStatThresholdEntry 8 }

		

		-- 1.3.6.1.4.1.32285.11.2.3.9.4.1.9
		topPerfStatThrLower OBJECT-TYPE
			SYNTAX Counter64
			MAX-ACCESS read-write
			STATUS current
			DESCRIPTION
				"Statistics or temperature lower threshold."
			::= { topPerfStatThresholdEntry 9 }

		
		-- 1.3.6.1.4.1.32285.11.2.3.9.5
		topCurStatsTable OBJECT-TYPE
			SYNTAX SEQUENCE OF TopCurStatsEntry
			MAX-ACCESS not-accessible
			STATUS current
			DESCRIPTION
				"Description."
			::= { topPerfStatObjects 5 }

		
		-- 1.3.6.1.4.1.32285.11.2.3.9.5.1
		topCurStatsEntry OBJECT-TYPE
			SYNTAX TopCurStatsEntry
			MAX-ACCESS not-accessible
			STATUS current
			DESCRIPTION
				"Description."
			INDEX { topCurStatsDeviceIndex, topCurStatsCardIndex, topCurStatsPortIndex }
			::= { topCurStatsTable 1 }

		
		TopCurStatsEntry ::=
			SEQUENCE { 
				topCurStatsDeviceIndex
					Unsigned32,
				topCurStatsCardIndex
					Unsigned32,
				topCurStatsPortIndex
					INTEGER,
				topCurStatsInOctets
					Counter64,
				topCurStatsInPkts
					Counter64,
				topCurStatsInBroadcastPkts
					Counter64,
				topCurStatsInMulticastPkts
					Counter64,
				topCurStatsInPkts64Octets
					Counter64,
				topCurStatsInPkts65to127Octets
					Counter64,
				topCurStatsInPkts128to255Octets
					Counter64,
				topCurStatsInPkts256to511Octets
					Counter64,
				topCurStatsInPkts512to1023Octets
					Counter64,
				topCurStatsInPkts1024to1518Octets
					Counter64,
				topCurStatsInPkts1519to1522Octets
					Counter64,
				topCurStatsInUndersizePkts
					Counter64,
				topCurStatsInOversizePkts
					Counter64,
				topCurStatsInFragments
					Counter64,
				topCurStatsInMpcpFrames
					Counter64,
				topCurStatsInMpcpOctets
					Counter64,
				topCurStatsInOAMFrames
					Counter64,
				topCurStatsInOAMOctets
					Counter64,
				topCurStatsInCRCErrorPkts
					Counter64,
				topCurStatsInDropEvents
					Counter64,
				topCurStatsInJabbers
					Counter64,
				topCurStatsInCollision
					Counter64,
				topCurStatsOutOctets
					Counter64,
				topCurStatsOutPkts
					Counter64,
				topCurStatsOutBroadcastPkts
					Counter64,
				topCurStatsOutMulticastPkts
					Counter64,
				topCurStatsOutPkts64Octets
					Counter64,
				topCurStatsOutPkts65to127Octets
					Counter64,
				topCurStatsOutPkts128to255Octets
					Counter64,
				topCurStatsOutPkts256to511Octets
					Counter64,
				topCurStatsOutPkts512to1023Octets
					Counter64,
				topCurStatsOutPkts1024to1518Octets
					Counter64,
				topCurStatsOutPkts1519o1522Octets
					Counter64,
				topCurStatsOutUndersizePkts
					Counter64,
				topCurStatsOutOversizePkts
					Counter64,
				topCurStatsOutFragments
					Counter64,
				topCurStatsOutMpcpFrames
					Counter64,
				topCurStatsOutMpcpOctets
					Counter64,
				topCurStatsOutOAMFrames
					Counter64,
				topCurStatsOutOAMOctets
					Counter64,
				topCurStatsOutCRCErrorPkts
					Counter64,
				topCurStatsOutDropEvents
					Counter64,
				topCurStatsOutJabbers
					Counter64,
				topCurStatsOutCollision
					Counter64,
				topCurStatsStatusAndAction
					INTEGER,
				topCurStatsInBandWidthUseRatio
					Counter64,
				topCurStatsOutBandWidthUseRatio
					Counter64,
				topCurStatsInBandWidth
					Counter64,
				topCurStatsOutBandWidth
					Counter64
			 }

		-- 1.3.6.1.4.1.32285.11.2.3.9.5.1.1
		topCurStatsDeviceIndex OBJECT-TYPE
			SYNTAX Unsigned32
			MAX-ACCESS not-accessible
			STATUS current
			DESCRIPTION
				"Description."
			::= { topCurStatsEntry 1 }

		
		-- 1.3.6.1.4.1.32285.11.2.3.9.5.1.2
		topCurStatsCardIndex OBJECT-TYPE
			SYNTAX Unsigned32
			MAX-ACCESS not-accessible
			STATUS current
			DESCRIPTION
				"Description."
			::= { topCurStatsEntry 2 }

		
		-- 1.3.6.1.4.1.32285.11.2.3.9.5.1.3
		topCurStatsPortIndex OBJECT-TYPE
			SYNTAX INTEGER
			MAX-ACCESS not-accessible
			STATUS current
			DESCRIPTION
				"Description."
			::= { topCurStatsEntry 3 }

		
		-- 1.3.6.1.4.1.32285.11.2.3.9.5.1.4
		topCurStatsInOctets OBJECT-TYPE
			SYNTAX Counter64
			MAX-ACCESS read-only
			STATUS current
			DESCRIPTION
				"Description."
			::= { topCurStatsEntry 4 }

		
		-- 1.3.6.1.4.1.32285.11.2.3.9.5.1.5
		topCurStatsInPkts OBJECT-TYPE
			SYNTAX Counter64
			MAX-ACCESS read-only
			STATUS current
			DESCRIPTION
				"Description."
			::= { topCurStatsEntry 5 }

		
		-- 1.3.6.1.4.1.32285.11.2.3.9.5.1.6
		topCurStatsInBroadcastPkts OBJECT-TYPE
			SYNTAX Counter64
			MAX-ACCESS read-only
			STATUS current
			DESCRIPTION
				"Description."
			::= { topCurStatsEntry 6 }

		
		-- 1.3.6.1.4.1.32285.11.2.3.9.5.1.7
		topCurStatsInMulticastPkts OBJECT-TYPE
			SYNTAX Counter64
			MAX-ACCESS read-only
			STATUS current
			DESCRIPTION
				"Description."
			::= { topCurStatsEntry 7 }

		
		-- 1.3.6.1.4.1.32285.11.2.3.9.5.1.8
		topCurStatsInPkts64Octets OBJECT-TYPE
			SYNTAX Counter64
			MAX-ACCESS read-only
			STATUS current
			DESCRIPTION
				"Description."
			::= { topCurStatsEntry 8 }

		
		-- 1.3.6.1.4.1.32285.11.2.3.9.5.1.9
		topCurStatsInPkts65to127Octets OBJECT-TYPE
			SYNTAX Counter64
			MAX-ACCESS read-only
			STATUS current
			DESCRIPTION
				"Description."
			::= { topCurStatsEntry 9 }

		
		-- 1.3.6.1.4.1.32285.11.2.3.9.5.1.10
		topCurStatsInPkts128to255Octets OBJECT-TYPE
			SYNTAX Counter64
			MAX-ACCESS read-only
			STATUS current
			DESCRIPTION
				"Description."
			::= { topCurStatsEntry 10 }

		
		-- 1.3.6.1.4.1.32285.11.2.3.9.5.1.11
		topCurStatsInPkts256to511Octets OBJECT-TYPE
			SYNTAX Counter64
			MAX-ACCESS read-only
			STATUS current
			DESCRIPTION
				"Description."
			::= { topCurStatsEntry 11 }

		
		-- 1.3.6.1.4.1.32285.11.2.3.9.5.1.12
		topCurStatsInPkts512to1023Octets OBJECT-TYPE
			SYNTAX Counter64
			MAX-ACCESS read-only
			STATUS current
			DESCRIPTION
				"Description."
			::= { topCurStatsEntry 12 }

		
		-- 1.3.6.1.4.1.32285.11.2.3.9.5.1.13
		topCurStatsInPkts1024to1518Octets OBJECT-TYPE
			SYNTAX Counter64
			MAX-ACCESS read-only
			STATUS current
			DESCRIPTION
				"Description."
			::= { topCurStatsEntry 13 }

		
		-- 1.3.6.1.4.1.32285.11.2.3.9.5.1.14
		topCurStatsInPkts1519to1522Octets OBJECT-TYPE
			SYNTAX Counter64
			MAX-ACCESS read-only
			STATUS current
			DESCRIPTION
				"Description."
			::= { topCurStatsEntry 14 }

		
		-- 1.3.6.1.4.1.32285.11.2.3.9.5.1.15
		topCurStatsInUndersizePkts OBJECT-TYPE
			SYNTAX Counter64
			MAX-ACCESS read-only
			STATUS current
			DESCRIPTION
				"Description."
			::= { topCurStatsEntry 15 }

		
		-- 1.3.6.1.4.1.32285.11.2.3.9.5.1.16
		topCurStatsInOversizePkts OBJECT-TYPE
			SYNTAX Counter64
			MAX-ACCESS read-only
			STATUS current
			DESCRIPTION
				"Description."
			::= { topCurStatsEntry 16 }

		
		-- 1.3.6.1.4.1.32285.11.2.3.9.5.1.17
		topCurStatsInFragments OBJECT-TYPE
			SYNTAX Counter64
			MAX-ACCESS read-only
			STATUS current
			DESCRIPTION
				"Description."
			::= { topCurStatsEntry 17 }

		
		-- 1.3.6.1.4.1.32285.11.2.3.9.5.1.18
		topCurStatsInMpcpFrames OBJECT-TYPE
			SYNTAX Counter64
			MAX-ACCESS read-only
			STATUS current
			DESCRIPTION
				"Description."
			::= { topCurStatsEntry 18 }

		
		-- 1.3.6.1.4.1.32285.11.2.3.9.5.1.19
		topCurStatsInMpcpOctets OBJECT-TYPE
			SYNTAX Counter64
			MAX-ACCESS read-only
			STATUS current
			DESCRIPTION
				"Description."
			::= { topCurStatsEntry 19 }

		
		-- 1.3.6.1.4.1.32285.11.2.3.9.5.1.20
		topCurStatsInOAMFrames OBJECT-TYPE
			SYNTAX Counter64
			MAX-ACCESS read-only
			STATUS current
			DESCRIPTION
				"Description."
			::= { topCurStatsEntry 20 }

		
		-- 1.3.6.1.4.1.32285.11.2.3.9.5.1.21
		topCurStatsInOAMOctets OBJECT-TYPE
			SYNTAX Counter64
			MAX-ACCESS read-only
			STATUS current
			DESCRIPTION
				"Description."
			::= { topCurStatsEntry 21 }

		
		-- 1.3.6.1.4.1.32285.11.2.3.9.5.1.22
		topCurStatsInCRCErrorPkts OBJECT-TYPE
			SYNTAX Counter64
			MAX-ACCESS read-only
			STATUS current
			DESCRIPTION
				"Description."
			::= { topCurStatsEntry 22 }

		
		-- 1.3.6.1.4.1.32285.11.2.3.9.5.1.23
		topCurStatsInDropEvents OBJECT-TYPE
			SYNTAX Counter64
			MAX-ACCESS read-only
			STATUS current
			DESCRIPTION
				"Description."
			::= { topCurStatsEntry 23 }

		
		-- 1.3.6.1.4.1.32285.11.2.3.9.5.1.24
		topCurStatsInJabbers OBJECT-TYPE
			SYNTAX Counter64
			MAX-ACCESS read-only
			STATUS current
			DESCRIPTION
				"Description."
			::= { topCurStatsEntry 24 }

		
		-- 1.3.6.1.4.1.32285.11.2.3.9.5.1.25
		topCurStatsInCollision OBJECT-TYPE
			SYNTAX Counter64
			MAX-ACCESS read-only
			STATUS current
			DESCRIPTION
				"Description."
			::= { topCurStatsEntry 25 }

		
		-- 1.3.6.1.4.1.32285.11.2.3.9.5.1.26
		topCurStatsOutOctets OBJECT-TYPE
			SYNTAX Counter64
			MAX-ACCESS read-only
			STATUS current
			DESCRIPTION
				"Description."
			::= { topCurStatsEntry 26 }

		
		-- 1.3.6.1.4.1.32285.11.2.3.9.5.1.27
		topCurStatsOutPkts OBJECT-TYPE
			SYNTAX Counter64
			MAX-ACCESS read-only
			STATUS current
			DESCRIPTION
				"Description."
			::= { topCurStatsEntry 27 }

		
		-- 1.3.6.1.4.1.32285.11.2.3.9.5.1.28
		topCurStatsOutBroadcastPkts OBJECT-TYPE
			SYNTAX Counter64
			MAX-ACCESS read-only
			STATUS current
			DESCRIPTION
				"Description."
			::= { topCurStatsEntry 28 }

		
		-- 1.3.6.1.4.1.32285.11.2.3.9.5.1.29
		topCurStatsOutMulticastPkts OBJECT-TYPE
			SYNTAX Counter64
			MAX-ACCESS read-only
			STATUS current
			DESCRIPTION
				"Description."
			::= { topCurStatsEntry 29 }

		
		-- 1.3.6.1.4.1.32285.11.2.3.9.5.1.30
		topCurStatsOutPkts64Octets OBJECT-TYPE
			SYNTAX Counter64
			MAX-ACCESS read-only
			STATUS current
			DESCRIPTION
				"Description."
			::= { topCurStatsEntry 30 }

		
		-- 1.3.6.1.4.1.32285.11.2.3.9.5.1.31
		topCurStatsOutPkts65to127Octets OBJECT-TYPE
			SYNTAX Counter64
			MAX-ACCESS read-only
			STATUS current
			DESCRIPTION
				"Description."
			::= { topCurStatsEntry 31 }

		
		-- 1.3.6.1.4.1.32285.11.2.3.9.5.1.32
		topCurStatsOutPkts128to255Octets OBJECT-TYPE
			SYNTAX Counter64
			MAX-ACCESS read-only
			STATUS current
			DESCRIPTION
				"Description."
			::= { topCurStatsEntry 32 }

		
		-- 1.3.6.1.4.1.32285.11.2.3.9.5.1.33
		topCurStatsOutPkts256to511Octets OBJECT-TYPE
			SYNTAX Counter64
			MAX-ACCESS read-only
			STATUS current
			DESCRIPTION
				"Description."
			::= { topCurStatsEntry 33 }

		
		-- 1.3.6.1.4.1.32285.11.2.3.9.5.1.34
		topCurStatsOutPkts512to1023Octets OBJECT-TYPE
			SYNTAX Counter64
			MAX-ACCESS read-only
			STATUS current
			DESCRIPTION
				"Description."
			::= { topCurStatsEntry 34 }

		
		-- 1.3.6.1.4.1.32285.11.2.3.9.5.1.35
		topCurStatsOutPkts1024to1518Octets OBJECT-TYPE
			SYNTAX Counter64
			MAX-ACCESS read-only
			STATUS current
			DESCRIPTION
				"Description."
			::= { topCurStatsEntry 35 }

		
		-- 1.3.6.1.4.1.32285.11.2.3.9.5.1.36
		topCurStatsOutPkts1519o1522Octets OBJECT-TYPE
			SYNTAX Counter64
			MAX-ACCESS read-only
			STATUS current
			DESCRIPTION
				"Description."
			::= { topCurStatsEntry 36 }

		
		-- 1.3.6.1.4.1.32285.11.2.3.9.5.1.37
		topCurStatsOutUndersizePkts OBJECT-TYPE
			SYNTAX Counter64
			MAX-ACCESS read-only
			STATUS current
			DESCRIPTION
				"Description."
			::= { topCurStatsEntry 37 }

		
		-- 1.3.6.1.4.1.32285.11.2.3.9.5.1.38
		topCurStatsOutOversizePkts OBJECT-TYPE
			SYNTAX Counter64
			MAX-ACCESS read-only
			STATUS current
			DESCRIPTION
				"Description."
			::= { topCurStatsEntry 38 }

		
		-- 1.3.6.1.4.1.32285.11.2.3.9.5.1.39
		topCurStatsOutFragments OBJECT-TYPE
			SYNTAX Counter64
			MAX-ACCESS read-only
			STATUS current
			DESCRIPTION
				"Description."
			::= { topCurStatsEntry 39 }

		
		-- 1.3.6.1.4.1.32285.11.2.3.9.5.1.40
		topCurStatsOutMpcpFrames OBJECT-TYPE
			SYNTAX Counter64
			MAX-ACCESS read-only
			STATUS current
			DESCRIPTION
				"Description."
			::= { topCurStatsEntry 40 }

		
		-- 1.3.6.1.4.1.32285.11.2.3.9.5.1.41
		topCurStatsOutMpcpOctets OBJECT-TYPE
			SYNTAX Counter64
			MAX-ACCESS read-only
			STATUS current
			DESCRIPTION
				"Description."
			::= { topCurStatsEntry 41 }

		
		-- 1.3.6.1.4.1.32285.11.2.3.9.5.1.42
		topCurStatsOutOAMFrames OBJECT-TYPE
			SYNTAX Counter64
			MAX-ACCESS read-only
			STATUS current
			DESCRIPTION
				"Description."
			::= { topCurStatsEntry 42 }

		
		-- 1.3.6.1.4.1.32285.11.2.3.9.5.1.43
		topCurStatsOutOAMOctets OBJECT-TYPE
			SYNTAX Counter64
			MAX-ACCESS read-only
			STATUS current
			DESCRIPTION
				"Description."
			::= { topCurStatsEntry 43 }

		
		-- 1.3.6.1.4.1.32285.11.2.3.9.5.1.44
		topCurStatsOutCRCErrorPkts OBJECT-TYPE
			SYNTAX Counter64
			MAX-ACCESS read-only
			STATUS current
			DESCRIPTION
				"Description."
			::= { topCurStatsEntry 44 }

		
		-- 1.3.6.1.4.1.32285.11.2.3.9.5.1.45
		topCurStatsOutDropEvents OBJECT-TYPE
			SYNTAX Counter64
			MAX-ACCESS read-only
			STATUS current
			DESCRIPTION
				"Description."
			::= { topCurStatsEntry 45 }

		
		-- 1.3.6.1.4.1.32285.11.2.3.9.5.1.46
		topCurStatsOutJabbers OBJECT-TYPE
			SYNTAX Counter64
			MAX-ACCESS read-only
			STATUS current
			DESCRIPTION
				"Description."
			::= { topCurStatsEntry 46 }

		
		-- 1.3.6.1.4.1.32285.11.2.3.9.5.1.47
		topCurStatsOutCollision OBJECT-TYPE
			SYNTAX Counter64
			MAX-ACCESS read-only
			STATUS current
			DESCRIPTION
				"Description."
			::= { topCurStatsEntry 47 }

		
		-- 1.3.6.1.4.1.32285.11.2.3.9.5.1.48
		topCurStatsStatusAndAction OBJECT-TYPE
			SYNTAX INTEGER
				{
				none(1),
				clean(2)
				}
			MAX-ACCESS read-write
			STATUS current
			DESCRIPTION
				"Description."
			::= { topCurStatsEntry 48 }

		
		-- 1.3.6.1.4.1.32285.11.2.3.9.5.1.49
		topCurStatsInBandWidthUseRatio OBJECT-TYPE
			SYNTAX Counter64
			MAX-ACCESS read-only
			STATUS current
			DESCRIPTION
				"Description."
			::= { topCurStatsEntry 49 }

		
		-- 1.3.6.1.4.1.32285.11.2.3.9.5.1.50
		topCurStatsOutBandWidthUseRatio OBJECT-TYPE
			SYNTAX Counter64
			MAX-ACCESS read-only
			STATUS current
			DESCRIPTION
				"Description."
			::= { topCurStatsEntry 50 }

		
		-- 1.3.6.1.4.1.32285.11.2.3.9.5.1.51
		topCurStatsInBandWidth OBJECT-TYPE
			SYNTAX Counter64
			UNITS "Mbps"
			MAX-ACCESS read-only
			STATUS current
			DESCRIPTION
				"Description."
			::= { topCurStatsEntry 51 }

		
		-- 1.3.6.1.4.1.32285.11.2.3.9.5.1.52
		topCurStatsOutBandWidth OBJECT-TYPE
			SYNTAX Counter64
			UNITS "Mbps"
			MAX-ACCESS read-only
			STATUS current
			DESCRIPTION
				"Description."
			::= { topCurStatsEntry 52 }

		
		-- 1.3.6.1.4.1.32285.11.2.3.9.6
		topStats15Table OBJECT-TYPE
			SYNTAX SEQUENCE OF TopStats15Entry
			MAX-ACCESS not-accessible
			STATUS current
			DESCRIPTION
				"Description."
			::= { topPerfStatObjects 6 }

		
		-- 1.3.6.1.4.1.32285.11.2.3.9.6.1
		topStats15Entry OBJECT-TYPE
			SYNTAX TopStats15Entry
			MAX-ACCESS not-accessible
			STATUS current
			DESCRIPTION
				"Description."
			INDEX { topStats15DeviceIndex, topStats15CardIndex, topStats15PortIndex, topStats15Index }
			::= { topStats15Table 1 }

		
		TopStats15Entry ::=
			SEQUENCE { 
				topStats15DeviceIndex
					Unsigned32,
				topStats15CardIndex
					Unsigned32,
				topStats15PortIndex
					INTEGER,
				topStats15Index
					INTEGER,
				topStats15InOctets
					Counter64,
				topStats15InPkts
					Counter64,
				topStats15InBroadcastPkts
					Counter64,
				topStats15InMulticastPkts
					Counter64,
				topStats15InPkts64Octets
					Counter64,
				topStats15InPkts65to127Octets
					Counter64,
				topStats15InPkts128to255Octets
					Counter64,
				topStats15InPkts256to511Octets
					Counter64,
				topStats15InPkts512to1023Octets
					Counter64,
				topStats15InPkts1024to1518Octets
					Counter64,
				topStats15InPkts1519to1522Octets
					Counter64,
				topStats15InUndersizePkts
					Counter64,
				topStats15InOversizePkts
					Counter64,
				topStats15InFragments
					Counter64,
				topStats15InMpcpFrames
					Counter64,
				topStats15InMpcpOctets
					Counter64,
				topStats15InOAMFrames
					Counter64,
				topStats15InOAMOctets
					Counter64,
				topStats15InCRCErrorPkts
					Counter64,
				topStats15InDropEvents
					Counter64,
				topStats15InJabbers
					Counter64,
				topStats15InCollision
					Counter64,
				topStats15OutOctets
					Counter64,
				topStats15OutPkts
					Counter64,
				topStats15OutBroadcastPkts
					Counter64,
				topStats15OutMulticastPkts
					Counter64,
				topStats15OutPkts64Octets
					Counter64,
				topStats15OutPkts65to127Octets
					Counter64,
				topStats15OutPkts128to255Octets
					Counter64,
				topStats15OutPkts256to511Octets
					Counter64,
				topStats15OutPkts512to1023Octets
					Counter64,
				topStats15OutPkts1024to1518Octets
					Counter64,
				topStats15OutPkts1519o1522Octets
					Counter64,
				topStats15OutUndersizePkts
					Counter64,
				topStats15OutOversizePkts
					Counter64,
				topStats15OutFragments
					Counter64,
				topStats15OutMpcpFrames
					Counter64,
				topStats15OutMpcpOctets
					Counter64,
				topStats15OutOAMFrames
					Counter64,
				topStats15OutOAMOctets
					Counter64,
				topStats15OutCRCErrorPkts
					Counter64,
				topStats15OutDropEvents
					Counter64,
				topStats15OutJabbers
					Counter64,
				topStats15OutCollision
					Counter64,
				topStats15StatusAndAction
					INTEGER,
				topStats15ValidityTag
					INTEGER,
				topStats15ElapsedTime
					Unsigned32,
				topStats15EndTime
					DateAndTime,
				topStats15InBandWidthUseRatio
					Counter64,
				topStats15OutBandWidthUseRatio
					Counter64,
				topStats15InBandWidth
					Counter64,
				topStats15OutBandWidth
					Counter64
			 }

		-- 1.3.6.1.4.1.32285.11.2.3.9.6.1.1
		topStats15DeviceIndex OBJECT-TYPE
			SYNTAX Unsigned32
			MAX-ACCESS not-accessible
			STATUS current
			DESCRIPTION
				"Description."
			::= { topStats15Entry 1 }

		
		-- 1.3.6.1.4.1.32285.11.2.3.9.6.1.2
		topStats15CardIndex OBJECT-TYPE
			SYNTAX Unsigned32
			MAX-ACCESS not-accessible
			STATUS current
			DESCRIPTION
				"Description."
			::= { topStats15Entry 2 }

		
		-- 1.3.6.1.4.1.32285.11.2.3.9.6.1.3
		topStats15PortIndex OBJECT-TYPE
			SYNTAX INTEGER
			MAX-ACCESS not-accessible
			STATUS current
			DESCRIPTION
				"Description."
			::= { topStats15Entry 3 }

		
		-- 1.3.6.1.4.1.32285.11.2.3.9.6.1.4
		topStats15Index OBJECT-TYPE
			SYNTAX INTEGER
			MAX-ACCESS not-accessible
			STATUS current
			DESCRIPTION
				"Description."
			::= { topStats15Entry 4 }

		
		-- 1.3.6.1.4.1.32285.11.2.3.9.6.1.5
		topStats15InOctets OBJECT-TYPE
			SYNTAX Counter64
			MAX-ACCESS read-only
			STATUS current
			DESCRIPTION
				"Description."
			::= { topStats15Entry 5 }

		
		-- 1.3.6.1.4.1.32285.11.2.3.9.6.1.6
		topStats15InPkts OBJECT-TYPE
			SYNTAX Counter64
			MAX-ACCESS read-only
			STATUS current
			DESCRIPTION
				"Description."
			::= { topStats15Entry 6 }

		
		-- 1.3.6.1.4.1.32285.11.2.3.9.6.1.7
		topStats15InBroadcastPkts OBJECT-TYPE
			SYNTAX Counter64
			MAX-ACCESS read-only
			STATUS current
			DESCRIPTION
				"Description."
			::= { topStats15Entry 7 }

		
		-- 1.3.6.1.4.1.32285.11.2.3.9.6.1.8
		topStats15InMulticastPkts OBJECT-TYPE
			SYNTAX Counter64
			MAX-ACCESS read-only
			STATUS current
			DESCRIPTION
				"Description."
			::= { topStats15Entry 8 }

		
		-- 1.3.6.1.4.1.32285.11.2.3.9.6.1.9
		topStats15InPkts64Octets OBJECT-TYPE
			SYNTAX Counter64
			MAX-ACCESS read-only
			STATUS current
			DESCRIPTION
				"Description."
			::= { topStats15Entry 9 }

		
		-- 1.3.6.1.4.1.32285.11.2.3.9.6.1.10
		topStats15InPkts65to127Octets OBJECT-TYPE
			SYNTAX Counter64
			MAX-ACCESS read-only
			STATUS current
			DESCRIPTION
				"Description."
			::= { topStats15Entry 10 }

		
		-- 1.3.6.1.4.1.32285.11.2.3.9.6.1.11
		topStats15InPkts128to255Octets OBJECT-TYPE
			SYNTAX Counter64
			MAX-ACCESS read-only
			STATUS current
			DESCRIPTION
				"Description."
			::= { topStats15Entry 11 }

		
		-- 1.3.6.1.4.1.32285.11.2.3.9.6.1.12
		topStats15InPkts256to511Octets OBJECT-TYPE
			SYNTAX Counter64
			MAX-ACCESS read-only
			STATUS current
			DESCRIPTION
				"Description."
			::= { topStats15Entry 12 }

		
		-- 1.3.6.1.4.1.32285.11.2.3.9.6.1.13
		topStats15InPkts512to1023Octets OBJECT-TYPE
			SYNTAX Counter64
			MAX-ACCESS read-only
			STATUS current
			DESCRIPTION
				"Description."
			::= { topStats15Entry 13 }

		
		-- 1.3.6.1.4.1.32285.11.2.3.9.6.1.14
		topStats15InPkts1024to1518Octets OBJECT-TYPE
			SYNTAX Counter64
			MAX-ACCESS read-only
			STATUS current
			DESCRIPTION
				"Description."
			::= { topStats15Entry 14 }

		
		-- 1.3.6.1.4.1.32285.11.2.3.9.6.1.15
		topStats15InPkts1519to1522Octets OBJECT-TYPE
			SYNTAX Counter64
			MAX-ACCESS read-only
			STATUS current
			DESCRIPTION
				"Description."
			::= { topStats15Entry 15 }

		
		-- 1.3.6.1.4.1.32285.11.2.3.9.6.1.16
		topStats15InUndersizePkts OBJECT-TYPE
			SYNTAX Counter64
			MAX-ACCESS read-only
			STATUS current
			DESCRIPTION
				"Description."
			::= { topStats15Entry 16 }

		
		-- 1.3.6.1.4.1.32285.11.2.3.9.6.1.17
		topStats15InOversizePkts OBJECT-TYPE
			SYNTAX Counter64
			MAX-ACCESS read-only
			STATUS current
			DESCRIPTION
				"Description."
			::= { topStats15Entry 17 }

		
		-- 1.3.6.1.4.1.32285.11.2.3.9.6.1.18
		topStats15InFragments OBJECT-TYPE
			SYNTAX Counter64
			MAX-ACCESS read-only
			STATUS current
			DESCRIPTION
				"Description."
			::= { topStats15Entry 18 }

		
		-- 1.3.6.1.4.1.32285.11.2.3.9.6.1.19
		topStats15InMpcpFrames OBJECT-TYPE
			SYNTAX Counter64
			MAX-ACCESS read-only
			STATUS current
			DESCRIPTION
				"Description."
			::= { topStats15Entry 19 }

		
		-- 1.3.6.1.4.1.32285.11.2.3.9.6.1.20
		topStats15InMpcpOctets OBJECT-TYPE
			SYNTAX Counter64
			MAX-ACCESS read-only
			STATUS current
			DESCRIPTION
				"Description."
			::= { topStats15Entry 20 }

		
		-- 1.3.6.1.4.1.32285.11.2.3.9.6.1.21
		topStats15InOAMFrames OBJECT-TYPE
			SYNTAX Counter64
			MAX-ACCESS read-only
			STATUS current
			DESCRIPTION
				"Description."
			::= { topStats15Entry 21 }

		
		-- 1.3.6.1.4.1.32285.11.2.3.9.6.1.22
		topStats15InOAMOctets OBJECT-TYPE
			SYNTAX Counter64
			MAX-ACCESS read-only
			STATUS current
			DESCRIPTION
				"Description."
			::= { topStats15Entry 22 }

		
		-- 1.3.6.1.4.1.32285.11.2.3.9.6.1.23
		topStats15InCRCErrorPkts OBJECT-TYPE
			SYNTAX Counter64
			MAX-ACCESS read-only
			STATUS current
			DESCRIPTION
				"Description."
			::= { topStats15Entry 23 }

		
		-- 1.3.6.1.4.1.32285.11.2.3.9.6.1.24
		topStats15InDropEvents OBJECT-TYPE
			SYNTAX Counter64
			MAX-ACCESS read-only
			STATUS current
			DESCRIPTION
				"Description."
			::= { topStats15Entry 24 }

		
		-- 1.3.6.1.4.1.32285.11.2.3.9.6.1.25
		topStats15InJabbers OBJECT-TYPE
			SYNTAX Counter64
			MAX-ACCESS read-only
			STATUS current
			DESCRIPTION
				"Description."
			::= { topStats15Entry 25 }

		
		-- 1.3.6.1.4.1.32285.11.2.3.9.6.1.26
		topStats15InCollision OBJECT-TYPE
			SYNTAX Counter64
			MAX-ACCESS read-only
			STATUS current
			DESCRIPTION
				"Description."
			::= { topStats15Entry 26 }

		
		-- 1.3.6.1.4.1.32285.11.2.3.9.6.1.27
		topStats15OutOctets OBJECT-TYPE
			SYNTAX Counter64
			MAX-ACCESS read-only
			STATUS current
			DESCRIPTION
				"Description."
			::= { topStats15Entry 27 }

		
		-- 1.3.6.1.4.1.32285.11.2.3.9.6.1.28
		topStats15OutPkts OBJECT-TYPE
			SYNTAX Counter64
			MAX-ACCESS read-only
			STATUS current
			DESCRIPTION
				"Description."
			::= { topStats15Entry 28 }

		
		-- 1.3.6.1.4.1.32285.11.2.3.9.6.1.29
		topStats15OutBroadcastPkts OBJECT-TYPE
			SYNTAX Counter64
			MAX-ACCESS read-only
			STATUS current
			DESCRIPTION
				"Description."
			::= { topStats15Entry 29 }

		
		-- 1.3.6.1.4.1.32285.11.2.3.9.6.1.30
		topStats15OutMulticastPkts OBJECT-TYPE
			SYNTAX Counter64
			MAX-ACCESS read-only
			STATUS current
			DESCRIPTION
				"Description."
			::= { topStats15Entry 30 }

		
		-- 1.3.6.1.4.1.32285.11.2.3.9.6.1.31
		topStats15OutPkts64Octets OBJECT-TYPE
			SYNTAX Counter64
			MAX-ACCESS read-only
			STATUS current
			DESCRIPTION
				"Description."
			::= { topStats15Entry 31 }

		
		-- 1.3.6.1.4.1.32285.11.2.3.9.6.1.32
		topStats15OutPkts65to127Octets OBJECT-TYPE
			SYNTAX Counter64
			MAX-ACCESS read-only
			STATUS current
			DESCRIPTION
				"Description."
			::= { topStats15Entry 32 }

		
		-- 1.3.6.1.4.1.32285.11.2.3.9.6.1.33
		topStats15OutPkts128to255Octets OBJECT-TYPE
			SYNTAX Counter64
			MAX-ACCESS read-only
			STATUS current
			DESCRIPTION
				"Description."
			::= { topStats15Entry 33 }

		
		-- 1.3.6.1.4.1.32285.11.2.3.9.6.1.34
		topStats15OutPkts256to511Octets OBJECT-TYPE
			SYNTAX Counter64
			MAX-ACCESS read-only
			STATUS current
			DESCRIPTION
				"Description."
			::= { topStats15Entry 34 }

		
		-- 1.3.6.1.4.1.32285.11.2.3.9.6.1.35
		topStats15OutPkts512to1023Octets OBJECT-TYPE
			SYNTAX Counter64
			MAX-ACCESS read-only
			STATUS current
			DESCRIPTION
				"Description."
			::= { topStats15Entry 35 }

		
		-- 1.3.6.1.4.1.32285.11.2.3.9.6.1.36
		topStats15OutPkts1024to1518Octets OBJECT-TYPE
			SYNTAX Counter64
			MAX-ACCESS read-only
			STATUS current
			DESCRIPTION
				"Description."
			::= { topStats15Entry 36 }

		
		-- 1.3.6.1.4.1.32285.11.2.3.9.6.1.37
		topStats15OutPkts1519o1522Octets OBJECT-TYPE
			SYNTAX Counter64
			MAX-ACCESS read-only
			STATUS current
			DESCRIPTION
				"Description."
			::= { topStats15Entry 37 }

		
		-- 1.3.6.1.4.1.32285.11.2.3.9.6.1.38
		topStats15OutUndersizePkts OBJECT-TYPE
			SYNTAX Counter64
			MAX-ACCESS read-only
			STATUS current
			DESCRIPTION
				"Description."
			::= { topStats15Entry 38 }

		
		-- 1.3.6.1.4.1.32285.11.2.3.9.6.1.39
		topStats15OutOversizePkts OBJECT-TYPE
			SYNTAX Counter64
			MAX-ACCESS read-only
			STATUS current
			DESCRIPTION
				"Description."
			::= { topStats15Entry 39 }

		
		-- 1.3.6.1.4.1.32285.11.2.3.9.6.1.40
		topStats15OutFragments OBJECT-TYPE
			SYNTAX Counter64
			MAX-ACCESS read-only
			STATUS current
			DESCRIPTION
				"Description."
			::= { topStats15Entry 40 }

		
		-- 1.3.6.1.4.1.32285.11.2.3.9.6.1.41
		topStats15OutMpcpFrames OBJECT-TYPE
			SYNTAX Counter64
			MAX-ACCESS read-only
			STATUS current
			DESCRIPTION
				"Description."
			::= { topStats15Entry 41 }

		
		-- 1.3.6.1.4.1.32285.11.2.3.9.6.1.42
		topStats15OutMpcpOctets OBJECT-TYPE
			SYNTAX Counter64
			MAX-ACCESS read-only
			STATUS current
			DESCRIPTION
				"Description."
			::= { topStats15Entry 42 }

		
		-- 1.3.6.1.4.1.32285.11.2.3.9.6.1.43
		topStats15OutOAMFrames OBJECT-TYPE
			SYNTAX Counter64
			MAX-ACCESS read-only
			STATUS current
			DESCRIPTION
				"Description."
			::= { topStats15Entry 43 }

		
		-- 1.3.6.1.4.1.32285.11.2.3.9.6.1.44
		topStats15OutOAMOctets OBJECT-TYPE
			SYNTAX Counter64
			MAX-ACCESS read-only
			STATUS current
			DESCRIPTION
				"Description."
			::= { topStats15Entry 44 }

		
		-- 1.3.6.1.4.1.32285.11.2.3.9.6.1.45
		topStats15OutCRCErrorPkts OBJECT-TYPE
			SYNTAX Counter64
			MAX-ACCESS read-only
			STATUS current
			DESCRIPTION
				"Description."
			::= { topStats15Entry 45 }

		
		-- 1.3.6.1.4.1.32285.11.2.3.9.6.1.46
		topStats15OutDropEvents OBJECT-TYPE
			SYNTAX Counter64
			MAX-ACCESS read-only
			STATUS current
			DESCRIPTION
				"Description."
			::= { topStats15Entry 46 }

		
		-- 1.3.6.1.4.1.32285.11.2.3.9.6.1.47
		topStats15OutJabbers OBJECT-TYPE
			SYNTAX Counter64
			MAX-ACCESS read-only
			STATUS current
			DESCRIPTION
				"Description."
			::= { topStats15Entry 47 }

		
		-- 1.3.6.1.4.1.32285.11.2.3.9.6.1.48
		topStats15OutCollision OBJECT-TYPE
			SYNTAX Counter64
			MAX-ACCESS read-only
			STATUS current
			DESCRIPTION
				"Description."
			::= { topStats15Entry 48 }

		
		-- 1.3.6.1.4.1.32285.11.2.3.9.6.1.49
		topStats15StatusAndAction OBJECT-TYPE
			SYNTAX INTEGER
				{
				none(1),
				clean(2)
				}
			MAX-ACCESS read-write
			STATUS current
			DESCRIPTION
				"Description."
			::= { topStats15Entry 49 }

		
		-- 1.3.6.1.4.1.32285.11.2.3.9.6.1.50
		topStats15ValidityTag OBJECT-TYPE
			SYNTAX INTEGER
				{
				true(1),
				false(2)
				}
			MAX-ACCESS read-only
			STATUS current
			DESCRIPTION
				"Whether or not the current 15 min PM data is valid"
			::= { topStats15Entry 50 }

		
		-- 1.3.6.1.4.1.32285.11.2.3.9.6.1.51
		topStats15ElapsedTime OBJECT-TYPE
			SYNTAX Unsigned32
			UNITS "seconds"
			MAX-ACCESS read-only
			STATUS current
			DESCRIPTION
				"It is elapsed time, since start of this 15-min interval.
				 	It is only valid for current PM data. For history PM data, set to 0.
				"
			::= { topStats15Entry 51 }

		
		-- 1.3.6.1.4.1.32285.11.2.3.9.6.1.52
		topStats15EndTime OBJECT-TYPE
			SYNTAX DateAndTime
			MAX-ACCESS read-only
			STATUS current
			DESCRIPTION
				"It is time, when the PM history data is created.
				 	It is only valid for history PM data.
				"
			::= { topStats15Entry 52 }

		
		-- 1.3.6.1.4.1.32285.11.2.3.9.6.1.53
		topStats15InBandWidthUseRatio OBJECT-TYPE
			SYNTAX Counter64
			MAX-ACCESS read-only
			STATUS current
			DESCRIPTION
				"Description."
			::= { topStats15Entry 53 }

		
		-- 1.3.6.1.4.1.32285.11.2.3.9.6.1.54
		topStats15OutBandWidthUseRatio OBJECT-TYPE
			SYNTAX Counter64
			MAX-ACCESS read-only
			STATUS current
			DESCRIPTION
				"Description."
			::= { topStats15Entry 54 }

		
		-- 1.3.6.1.4.1.32285.11.2.3.9.6.1.55
		topStats15InBandWidth OBJECT-TYPE
			SYNTAX Counter64
			MAX-ACCESS read-only
			STATUS current
			DESCRIPTION
				"Description."
			::= { topStats15Entry 55 }

		
		-- 1.3.6.1.4.1.32285.11.2.3.9.6.1.56
		topStats15OutBandWidth OBJECT-TYPE
			SYNTAX Counter64
			MAX-ACCESS read-only
			STATUS current
			DESCRIPTION
				"Description."
			::= { topStats15Entry 56 }

		
		-- 1.3.6.1.4.1.32285.11.2.3.10
		topEponEoCMgmtObjects OBJECT IDENTIFIER ::= { topvisionEponTree 10 }

		

		-- 1.3.6.1.4.1.32285.11.2.3.11
		topLayer3MgmtObjects OBJECT IDENTIFIER ::= { topvisionEponTree 11 }

		
		-- 1.3.6.1.4.1.32285.11.2.3.11.1
		topDhcpMgmtObjects OBJECT IDENTIFIER ::= { topLayer3MgmtObjects 1 }

	-- ---------------------------------------------
-- nodes for topDhcpMgmtObjects
-- ---------------------------------------------
		-- 1.3.6.1.4.1.32285.11.2.3.11.1.1
		topOltDHCPCFGTable OBJECT-TYPE
			SYNTAX SEQUENCE OF TopOltDHCPCFGEntry
			MAX-ACCESS not-accessible
			STATUS current
			DESCRIPTION
				"Describe OLT DHCPRelay Configure."
			::= { topDhcpMgmtObjects 1 }

		
		-- 1.3.6.1.4.1.32285.11.2.3.11.1.1.1
		topOltDHCPCFGEntry OBJECT-TYPE
			SYNTAX TopOltDHCPCFGEntry
			MAX-ACCESS not-accessible
			STATUS current
			DESCRIPTION
				"Define Olt DHCP Relay Configure."
			INDEX { topOltDeviceId }
			::= { topOltDHCPCFGTable 1 }

		
		TopOltDHCPCFGEntry ::=
			SEQUENCE { 
				topOltDeviceId
					INTEGER,
				topOltPPPOEPlusEnable
					INTEGER,
				topOltDHCPRelayMode
					INTEGER,
				topOltDHCPDyncIPMACBind
					INTEGER
			 }

		-- 1.3.6.1.4.1.32285.11.2.3.11.1.1.1.1
		topOltDeviceId OBJECT-TYPE
			SYNTAX INTEGER
			MAX-ACCESS not-accessible
			STATUS current
			DESCRIPTION
				"DHCP Server ID."
			::= { topOltDHCPCFGEntry 1 }

		
		-- 1.3.6.1.4.1.32285.11.2.3.11.1.1.1.2
		topOltPPPOEPlusEnable OBJECT-TYPE
			SYNTAX INTEGER
				{
				enable(1),
				disable(2)
				}
			MAX-ACCESS read-write
			STATUS current
			DESCRIPTION
				"PPPOE Plus status, enable(1) or disable(2)."
			::= { topOltDHCPCFGEntry 2 }

		
		-- 1.3.6.1.4.1.32285.11.2.3.11.1.1.1.3
		topOltDHCPRelayMode OBJECT-TYPE
			SYNTAX INTEGER
				{
				none(0),
				l2mode(1),
				l3mode(2)
				}
			MAX-ACCESS read-write
			STATUS current
			DESCRIPTION
				"DHCPRelay mode, none(0),L2-mode(1),L3-mode(2)."
			::= { topOltDHCPCFGEntry 3 }

		
		-- 1.3.6.1.4.1.32285.11.2.3.11.1.1.1.4
		topOltDHCPDyncIPMACBind OBJECT-TYPE
			SYNTAX INTEGER
				{
				enable(1),
				disable(2)
				}
			MAX-ACCESS read-write
			STATUS current
			DESCRIPTION
				"Dynamic ip-mac bind,enable(1) or disable(2)."
			::= { topOltDHCPCFGEntry 4 }

		
								
		-- 1.3.6.1.4.1.32285.11.2.3.11.1.2
		topOltDHCPServerTable OBJECT-TYPE
			SYNTAX SEQUENCE OF TopOltDHCPServerEntry
			MAX-ACCESS not-accessible
			STATUS current
			DESCRIPTION
				"Describe OLT DHCP Server."
			::= { topDhcpMgmtObjects 2 }


		-- 1.3.6.1.4.1.32285.11.2.3.11.1.2.1
		topOltDHCPServerEntry OBJECT-TYPE
			SYNTAX TopOltDHCPServerEntry
			MAX-ACCESS not-accessible
			STATUS current
			DESCRIPTION
				"Define Olt DHCP Server property."
			INDEX { topOltDHCPServerIndex }
			::= { topOltDHCPServerTable 1 }

		
		TopOltDHCPServerEntry ::=
			SEQUENCE { 
				topOltDHCPServerIndex
					INTEGER,
				topOltDHCPServerVid
					INTEGER,
				topOltDHCPServerIpAddr
					IpAddress,
				topOltDHCPServerIpMask
					IpAddress,
				topOltDHCPServRowStatus
					RowStatus
			 }

		-- 1.3.6.1.4.1.32285.11.2.3.11.1.2.1.1
		topOltDHCPServerIndex OBJECT-TYPE
			SYNTAX INTEGER
			MAX-ACCESS not-accessible
			STATUS current
			DESCRIPTION
				"DHCP Server ID."
			::= { topOltDHCPServerEntry 1 }

		
		-- 1.3.6.1.4.1.32285.11.2.3.11.1.2.1.2
		topOltDHCPServerVid OBJECT-TYPE
			SYNTAX INTEGER (1..4094)
			MAX-ACCESS read-create
			STATUS current
			DESCRIPTION
				"VLAN ID"
			::= { topOltDHCPServerEntry 2 }

		
		-- 1.3.6.1.4.1.32285.11.2.3.11.1.2.1.3
		topOltDHCPServerIpAddr OBJECT-TYPE
			SYNTAX IpAddress
			MAX-ACCESS read-create
			STATUS current
			DESCRIPTION
				"DHCP Server IP Address."
			::= { topOltDHCPServerEntry 3 }

		
		-- 1.3.6.1.4.1.32285.11.2.3.11.1.2.1.4
		topOltDHCPServerIpMask OBJECT-TYPE
			SYNTAX IpAddress
			MAX-ACCESS read-create
			STATUS current
			DESCRIPTION
				"DHCP Server IP Mask."
			::= { topOltDHCPServerEntry 4 }

		
		-- 1.3.6.1.4.1.32285.11.2.3.11.1.2.1.5
		topOltDHCPServRowStatus OBJECT-TYPE
			SYNTAX RowStatus
			MAX-ACCESS read-create
			STATUS current
			DESCRIPTION
				"RowStatus."
			::= { topOltDHCPServerEntry 5 }

																		
		-- 1.3.6.1.4.1.32285.11.2.3.11.1.3
		topOltDHCPGiaddrTable OBJECT-TYPE
			SYNTAX SEQUENCE OF TopOltDHCPGiaddrEntry
			MAX-ACCESS not-accessible
			STATUS current
			DESCRIPTION
				"Describe OLT DHCP Relay GIADDR."
			::= { topDhcpMgmtObjects 3 }


		-- 1.3.6.1.4.1.32285.11.2.3.11.1.3.1
		topOltDHCPGiaddrEntry OBJECT-TYPE
			SYNTAX TopOltDHCPGiaddrEntry
			MAX-ACCESS not-accessible
			STATUS current
			DESCRIPTION
				"Define Olt DHCP GIADDR property."
			INDEX { topOltDHCPGiaddrIndex }
			::= { topOltDHCPGiaddrTable 1 }

		
		TopOltDHCPGiaddrEntry ::=
			SEQUENCE { 
				topOltDHCPGiaddrIndex
					INTEGER,
				topOltDHCPGiaddrVid
					INTEGER,
				topOltDHCPGiaddrIpAddr
					IpAddress,
				topOltDHCPGiaddrRowStatus
					RowStatus
			 }
					
		-- 1.3.6.1.4.1.32285.11.2.3.11.1.3.1.1
		topOltDHCPGiaddrIndex OBJECT-TYPE
			SYNTAX INTEGER
			MAX-ACCESS not-accessible
			STATUS current
			DESCRIPTION
				"DHCP GIADDR ID."
			::= { topOltDHCPGiaddrEntry 1 }

		
		-- 1.3.6.1.4.1.32285.11.2.3.11.1.3.1.2
		topOltDHCPGiaddrVid OBJECT-TYPE
			SYNTAX INTEGER (1..4094)
			MAX-ACCESS read-create
			STATUS current
			DESCRIPTION
				"GIADDR VLAN ID"
			::= { topOltDHCPGiaddrEntry 2 }

		
		-- 1.3.6.1.4.1.32285.11.2.3.11.1.3.1.3
		topOltDHCPGiaddrIpAddr OBJECT-TYPE
			SYNTAX IpAddress
			MAX-ACCESS read-create
			STATUS current
			DESCRIPTION
				"DHCP GIADDR IP Address."
			::= { topOltDHCPGiaddrEntry 3 }

		
		-- 1.3.6.1.4.1.32285.11.2.3.11.1.3.1.4
		topOltDHCPGiaddrRowStatus OBJECT-TYPE
			SYNTAX RowStatus
			MAX-ACCESS read-create
			STATUS current
			DESCRIPTION
				"RowStatus."
			::= { topOltDHCPGiaddrEntry 4 }


		-- 1.3.6.1.4.1.32285.11.2.3.11.1.4
		topOltDHCPIpMacTable OBJECT-TYPE
			SYNTAX SEQUENCE OF TopOltDHCPIpMacEntry
			MAX-ACCESS not-accessible
			STATUS current
			DESCRIPTION
				"static ip-mac bind."
			::= { topDhcpMgmtObjects 4 }


		-- 1.3.6.1.4.1.32285.11.2.3.11.1.4.1
		topOltDHCPIpMacEntry OBJECT-TYPE
			SYNTAX TopOltDHCPIpMacEntry
			MAX-ACCESS not-accessible
			STATUS current
			DESCRIPTION
				"Define Olt DHCP Server property."
			INDEX { topOltDHCPIpMacIdx }
			::= { topOltDHCPIpMacTable 1 }

		
		TopOltDHCPIpMacEntry ::=
			SEQUENCE { 
				topOltDHCPIpMacIdx
					INTEGER,
				topOltDHCPIpAddr
					IpAddress,
				topOltDHCPMacAddr
					MacAddress,
				topOltDHCPOnuMacAddr
					MacAddress,
				topOltDHCPIpMacRowStatus
					RowStatus
			 }

		-- 1.3.6.1.4.1.32285.11.2.3.11.1.4.1.1
		topOltDHCPIpMacIdx OBJECT-TYPE
			SYNTAX INTEGER
			MAX-ACCESS not-accessible
			STATUS current
			DESCRIPTION
				"ip-mac entry ID."
			::= { topOltDHCPIpMacEntry 1 }

		
		-- 1.3.6.1.4.1.32285.11.2.3.11.1.4.1.2
		topOltDHCPIpAddr OBJECT-TYPE
			SYNTAX IpAddress
			MAX-ACCESS read-write
			STATUS current
			DESCRIPTION
				"IP Address."
			::= { topOltDHCPIpMacEntry 2 }

		
		-- 1.3.6.1.4.1.32285.11.2.3.11.1.4.1.3
		topOltDHCPMacAddr OBJECT-TYPE
			SYNTAX MacAddress
			MAX-ACCESS read-write
			STATUS current
			DESCRIPTION
				"MAC Address."
			::= { topOltDHCPIpMacEntry 3 }

		
		-- 1.3.6.1.4.1.32285.11.2.3.11.1.4.1.4
		topOltDHCPOnuMacAddr OBJECT-TYPE
			SYNTAX MacAddress
			MAX-ACCESS read-write
			STATUS current
			DESCRIPTION
				"ONU MAC Address"
			::= { topOltDHCPIpMacEntry 4 }

		
		-- 1.3.6.1.4.1.32285.11.2.3.11.1.4.1.5
		topOltDHCPIpMacRowStatus OBJECT-TYPE
			SYNTAX RowStatus
			MAX-ACCESS read-write
			STATUS current
			DESCRIPTION
				"RowStatus."
			::= { topOltDHCPIpMacEntry 5 }

		
		-- 1.3.6.1.4.1.32285.11.2.3.11.1.5
		topOltDHCPDynIpMacTable OBJECT-TYPE
			SYNTAX SEQUENCE OF TopOltDHCPDynIpMacEntry
			MAX-ACCESS not-accessible
			STATUS current
			DESCRIPTION
				"static ip-mac bind."
			::= { topDhcpMgmtObjects 5 }


		-- 1.3.6.1.4.1.32285.11.2.3.11.1.5.1
		topOltDHCPDynIpMacEntry OBJECT-TYPE
			SYNTAX TopOltDHCPDynIpMacEntry
			MAX-ACCESS not-accessible
			STATUS current
			DESCRIPTION
				"Define Olt DHCP Server property."
			INDEX { topOltDHCPDynIpMacIdx }
			::= { topOltDHCPDynIpMacTable 1 }

		
		TopOltDHCPDynIpMacEntry ::=
			SEQUENCE { 
				topOltDHCPDynIpMacIdx
					INTEGER,
				topOltDHCPDynIpAddr
					IpAddress,
				topOltDHCPDynMacAddr
					MacAddress,
				topOltDHCPDynOnuMacAddr
					MacAddress
			 }

		-- 1.3.6.1.4.1.32285.11.2.3.11.1.5.1.1
		topOltDHCPDynIpMacIdx OBJECT-TYPE
			SYNTAX INTEGER
			MAX-ACCESS not-accessible
			STATUS current
			DESCRIPTION
				"ip-mac entry ID."
			::= { topOltDHCPDynIpMacEntry 1 }

		
		-- 1.3.6.1.4.1.32285.11.2.3.11.1.5.1.2
		topOltDHCPDynIpAddr OBJECT-TYPE
			SYNTAX IpAddress
			MAX-ACCESS read-only
			STATUS current
			DESCRIPTION
				"IP Address."
			::= { topOltDHCPDynIpMacEntry 2 }

		
		-- 1.3.6.1.4.1.32285.11.2.3.11.1.5.1.3
		topOltDHCPDynMacAddr OBJECT-TYPE
			SYNTAX MacAddress
			MAX-ACCESS read-only
			STATUS current
			DESCRIPTION
				"MAC Address."
			::= { topOltDHCPDynIpMacEntry 3 }

		
		-- 1.3.6.1.4.1.32285.11.2.3.11.1.5.1.4
		topOltDHCPDynOnuMacAddr OBJECT-TYPE
			SYNTAX MacAddress
			MAX-ACCESS read-only
			STATUS current
			DESCRIPTION
				"ONU Dynamic MAC Address"
			::= { topOltDHCPDynIpMacEntry 4 }

		
		-- 1.3.6.1.4.1.32285.11.2.3.10.2
		topLogicInterfaceObjects OBJECT IDENTIFIER ::= { topLayer3MgmtObjects 2 }

		
		-- 1.3.6.1.4.1.32285.11.2.3.10.2.1
		topLogicIntfMgmtTable OBJECT-TYPE
			SYNTAX SEQUENCE OF TopLogicIntfMgmtEntry
			MAX-ACCESS not-accessible
			STATUS current
			DESCRIPTION
				"Description."
			::= { topLogicInterfaceObjects 1 }

		
		-- 1.3.6.1.4.1.32285.11.2.3.10.2.1.1
		topLogicIntfMgmtEntry OBJECT-TYPE
			SYNTAX TopLogicIntfMgmtEntry
			MAX-ACCESS not-accessible
			STATUS current
			DESCRIPTION
				"Description."
			INDEX { topLogicIntfType, topLogicIntfId }
			::= { topLogicIntfMgmtTable 1 }

		
		TopLogicIntfMgmtEntry ::=
			SEQUENCE { 
				topLogicIntfType
					INTEGER,
				topLogicIntfId
					INTEGER,
				topLogicIntfIfindex
					INTEGER,
				topLogicIntfName
					OCTET STRING,
				topLogicIntfDesc
					OCTET STRING,
				topLogicIntfAdminStatus
					INTEGER,
				topLogicIntfOperateStatus
					INTEGER,
				topLogicIntfMac
					MacAddress,
				topLogicIntfRowStatus
					RowStatus
			 }

		-- 1.3.6.1.4.1.32285.11.2.3.10.2.1.1.1
		topLogicIntfType OBJECT-TYPE
			SYNTAX INTEGER (1..2)
			MAX-ACCESS read-only
			STATUS current
			DESCRIPTION
				"Interface type:1->vlanif,2->loopback,3->outband"
			::= { topLogicIntfMgmtEntry 1 }

		
		-- 1.3.6.1.4.1.32285.11.2.3.10.2.1.1.2
		topLogicIntfId OBJECT-TYPE
			SYNTAX INTEGER
			MAX-ACCESS read-only
			STATUS current
			DESCRIPTION
				"Interface ID,vlanif ID from 1 to 4096 and loopback ID from 1 to 8 and outband id is 0."
			::= { topLogicIntfMgmtEntry 2 }

		
		-- 1.3.6.1.4.1.32285.11.2.3.10.2.1.1.3
		topLogicIntfIfindex OBJECT-TYPE
			SYNTAX INTEGER
			MAX-ACCESS read-only
			STATUS current
			DESCRIPTION
				"Interface Ifindex:for vlanif,from 3073 to 7169,total 4096,
				for loopback,form 11265 to 11273,total 8."
			::= { topLogicIntfMgmtEntry 3 }

		
		-- 1.3.6.1.4.1.32285.11.2.3.10.2.1.1.4
		topLogicIntfName OBJECT-TYPE
			SYNTAX OCTET STRING (SIZE (1..15))
			MAX-ACCESS read-only
			STATUS current
			DESCRIPTION
				"Interface Name."
			::= { topLogicIntfMgmtEntry 4 }
			
		-- 1.3.6.1.4.1.32285.11.2.3.10.2.1.1.5
		topLogicIntfDesc OBJECT-TYPE
			SYNTAX OCTET STRING (SIZE (1..31))
			MAX-ACCESS read-create
			STATUS current
			DESCRIPTION
				"Interface Description."
			::= { topLogicIntfMgmtEntry 5 }
		
		-- 1.3.6.1.4.1.32285.11.2.3.10.2.1.1.6
		topLogicIntfAdminStatus OBJECT-TYPE
			SYNTAX INTEGER
				{
				up(1),
				down(2)
				}
			MAX-ACCESS read-create
			STATUS current
			DESCRIPTION
				"Admin status."
			::= { topLogicIntfMgmtEntry 6 }

		
		-- 1.3.6.1.4.1.32285.11.2.3.10.2.1.1.7
		topLogicIntfOperateStatus OBJECT-TYPE
			SYNTAX INTEGER
				{
				up(1),
				down(2)
				}
			MAX-ACCESS read-only
			STATUS current
			DESCRIPTION
				"Operation Status."
			::= { topLogicIntfMgmtEntry 7 }

		
		-- 1.3.6.1.4.1.32285.11.2.3.10.2.1.1.8
		topLogicIntfMac OBJECT-TYPE
			SYNTAX MacAddress
			MAX-ACCESS read-only
			STATUS current
			DESCRIPTION
				"Mac Address."
			::= { topLogicIntfMgmtEntry 8 }

		
		-- 1.3.6.1.4.1.32285.11.2.3.10.2.1.1.9
		topLogicIntfRowStatus OBJECT-TYPE
			SYNTAX RowStatus
			MAX-ACCESS read-create
			STATUS current
			DESCRIPTION
				"RowStatus."
			::= { topLogicIntfMgmtEntry 9 }

		
		-- 1.3.6.1.4.1.32285.11.2.3.10.3
		topIntfIpv4Objects OBJECT IDENTIFIER ::= { topLayer3MgmtObjects 3 }

		
		-- 1.3.6.1.4.1.32285.11.2.3.10.3.1
		topIntfIpv4CfgTable OBJECT-TYPE
			SYNTAX SEQUENCE OF TopIntfIpv4CfgEntry
			MAX-ACCESS not-accessible
			STATUS current
			DESCRIPTION
				"Description."
			::= { topIntfIpv4Objects 1 }

		
		-- 1.3.6.1.4.1.32285.11.2.3.10.3.1.1
		topIntfIpv4CfgEntry OBJECT-TYPE
			SYNTAX TopIntfIpv4CfgEntry
			MAX-ACCESS not-accessible
			STATUS current
			DESCRIPTION
				"Description."
			INDEX { topIpv4CfgIfindex, topIpv4CfgAddress }
			::= { topIntfIpv4CfgTable 1 }

		
		TopIntfIpv4CfgEntry ::=
			SEQUENCE { 
				topIpv4CfgIfindex
					INTEGER,
				topIpv4CfgAddress
					IpAddress,
				topIpv4CfgNetmask
					IpAddress,
				topIpv4CfgAddressType
					INTEGER,
				topIpv4CfgRowStatus
					RowStatus
			 }

		-- 1.3.6.1.4.1.32285.11.2.3.10.3.1.1.1
		topIpv4CfgIfindex OBJECT-TYPE
			SYNTAX INTEGER
			MAX-ACCESS read-only
			STATUS current
			DESCRIPTION
				"Interface Index."
			::= { topIntfIpv4CfgEntry 1 }

		
		-- 1.3.6.1.4.1.32285.11.2.3.10.3.1.1.2
		topIpv4CfgAddress OBJECT-TYPE
			SYNTAX IpAddress
			MAX-ACCESS read-only
			STATUS current
			DESCRIPTION
				"Ip Address."
			::= { topIntfIpv4CfgEntry 2 }

		
		-- 1.3.6.1.4.1.32285.11.2.3.10.3.1.1.3
		topIpv4CfgNetmask OBJECT-TYPE
			SYNTAX IpAddress
			MAX-ACCESS read-create
			STATUS current
			DESCRIPTION
				"Ip Address Mask."
			::= { topIntfIpv4CfgEntry 3 }

		
		-- 1.3.6.1.4.1.32285.11.2.3.10.3.1.1.4
		topIpv4CfgAddressType OBJECT-TYPE
			SYNTAX INTEGER
		    {
			 pri(0),
			 sub(1),
			 inband(2)
		    }
			MAX-ACCESS read-create
			STATUS current
			DESCRIPTION
				"Address Type,0-pri ip,0-sub ip,2-inband ip."
			::= { topIntfIpv4CfgEntry 4 }

		
		-- 1.3.6.1.4.1.32285.11.2.3.10.3.1.1.5
		topIpv4CfgRowStatus OBJECT-TYPE
			SYNTAX RowStatus
			MAX-ACCESS read-create
			STATUS current
			DESCRIPTION
				"RowStatus."
			::= { topIntfIpv4CfgEntry 5 }

		
--  1.3.6.1.4.1.32285.11.2.3.12
		topIPRouting OBJECT IDENTIFIER ::= { topvisionEponTree 12 }

		
		-- 1.3.6.1.4.1.32285.11.2.3.12.1
		 topIsIsObjects OBJECT IDENTIFIER ::= { topIPRouting 1 }
	
		
		-- 1.3.6.1.4.1.32285.11.2.3.12.2
		 topIPRouteInfoObjects OBJECT IDENTIFIER ::= { topIPRouting 2 }

					
		-- 1.3.6.1.4.1.32285.11.2.3.12.3
		 topOspfObjects OBJECT IDENTIFIER ::= { topIPRouting 3 }

		
		-- 1.3.6.1.4.1.32285.11.2.3.12.4
		 topTrackMgmtObjects OBJECT IDENTIFIER ::= { topIPRouting 4 }

		
		-- 1.3.6.1.4.1.32285.11.2.3.12.5
		 topVRF OBJECT IDENTIFIER ::= { topIPRouting 5 }

		
		-- 1.3.6.1.4.1.32285.11.2.3.12.6
		topPingMIB OBJECT IDENTIFIER ::= { topIPRouting 6 }


		-- 1.3.6.1.4.1.32285.11.2.3.13
		 topAAA OBJECT IDENTIFIER ::= { topvisionEponTree 13 }

		
		-- 1.3.6.1.4.1.32285.11.2.3.14
		topQosMgmtObjects OBJECT IDENTIFIER ::= { topvisionEponTree 14 }

		
		-- 1.3.6.1.4.1.32285.11.2.3.14.1
		topQosRuleObjects OBJECT IDENTIFIER ::= { topQosMgmtObjects 1 }

		
		-- 1.3.6.1.4.1.32285.11.2.3.14.1.1
		topSlaProfileTable OBJECT-TYPE
			SYNTAX SEQUENCE OF TopSlaProfileEntry
			MAX-ACCESS not-accessible
			STATUS current
			DESCRIPTION
				"Description."
			::= { topQosRuleObjects 1 }

		
		-- 1.3.6.1.4.1.32285.11.2.3.14.1.1.1
		topSlaProfileEntry OBJECT-TYPE
			SYNTAX TopSlaProfileEntry
			MAX-ACCESS not-accessible
			STATUS current
			DESCRIPTION
				"Description."
			INDEX { topSlaProfileIndex }
			::= { topSlaProfileTable 1 }

		
		TopSlaProfileEntry ::=
			SEQUENCE { 
				topSlaProfileIndex
					INTEGER,
				topSlaProfileDesc
					OCTET STRING,
				topSlaProfileCir
					INTEGER,
				topSlaProfilePir
					INTEGER,
				topSlaProfileLevel
					INTEGER,
				topSlaProfileWeight
					INTEGER,
				topSlaProfileRefCount
					INTEGER,
				topSlaProfileRowStatus
					RowStatus
			 }

		-- 1.3.6.1.4.1.32285.11.2.3.14.1.1.1.1
		topSlaProfileIndex OBJECT-TYPE
			SYNTAX INTEGER (1..128)
			MAX-ACCESS not-accessible
			STATUS current
			DESCRIPTION
				"Description."
			::= { topSlaProfileEntry 1 }

		
		-- 1.3.6.1.4.1.32285.11.2.3.14.1.1.1.2
		topSlaProfileDesc OBJECT-TYPE
			SYNTAX OCTET STRING (SIZE (1..32))
			MAX-ACCESS read-write
			STATUS current
			DESCRIPTION
				"Description."
			::= { topSlaProfileEntry 2 }

		
		-- 1.3.6.1.4.1.32285.11.2.3.14.1.1.1.3
		topSlaProfileCir OBJECT-TYPE
			SYNTAX INTEGER (0..1000000)
			MAX-ACCESS read-write
			STATUS current
			DESCRIPTION
				"Units:  Kbps."
			::= { topSlaProfileEntry 3 }

		
		-- 1.3.6.1.4.1.32285.11.2.3.14.1.1.1.4
		topSlaProfilePir OBJECT-TYPE
			SYNTAX INTEGER (0..1000000)
			MAX-ACCESS read-write
			STATUS current
			DESCRIPTION
				"Units: Kbps."
			::= { topSlaProfileEntry 4 }

		
		-- 1.3.6.1.4.1.32285.11.2.3.14.1.1.1.5
		topSlaProfileLevel OBJECT-TYPE
			SYNTAX INTEGER (0..5)
			MAX-ACCESS read-write
			STATUS current
			DESCRIPTION
				"Description."
			::= { topSlaProfileEntry 5 }

		
		-- 1.3.6.1.4.1.32285.11.2.3.14.1.1.1.6
		topSlaProfileWeight OBJECT-TYPE
			SYNTAX INTEGER (0..15)
			MAX-ACCESS read-write
			STATUS current
			DESCRIPTION
				"Description."
			::= { topSlaProfileEntry 6 }

		
		-- 1.3.6.1.4.1.32285.11.2.3.14.1.1.1.7
		topSlaProfileRefCount OBJECT-TYPE
			SYNTAX INTEGER
			MAX-ACCESS read-only
			STATUS current
			DESCRIPTION
				"Description."
			::= { topSlaProfileEntry 7 }

		
		-- 1.3.6.1.4.1.32285.11.2.3.14.1.1.1.8
		topSlaProfileRowStatus OBJECT-TYPE
			SYNTAX RowStatus
			MAX-ACCESS read-create
			STATUS current
			DESCRIPTION
				"Description."
			::= { topSlaProfileEntry 8 }

		
		-- 1.3.6.1.4.1.32285.11.2.3.14.1.2
		topUscProfileTable OBJECT-TYPE
			SYNTAX SEQUENCE OF TopUscProfileEntry
			MAX-ACCESS not-accessible
			STATUS current
			DESCRIPTION
				"Description."
			::= { topQosRuleObjects 2 }

		
		-- 1.3.6.1.4.1.32285.11.2.3.14.1.2.1
		topUscProfileEntry OBJECT-TYPE
			SYNTAX TopUscProfileEntry
			MAX-ACCESS not-accessible
			STATUS current
			DESCRIPTION
				"Description."
			INDEX { topUscProfileIndex }
			::= { topUscProfileTable 1 }

		
		TopUscProfileEntry ::=
			SEQUENCE { 
				topUscProfileIndex
					INTEGER,
				topUscProfileDesc
					OCTET STRING,
				topUscProfileRuleCount
					INTEGER,
				topUscProfileRefCount
					INTEGER,
				topUscProfileRowStatus
					RowStatus
			 }

		-- 1.3.6.1.4.1.32285.11.2.3.14.1.2.1.1
		topUscProfileIndex OBJECT-TYPE
			SYNTAX INTEGER (1..128)
			MAX-ACCESS not-accessible
			STATUS current
			DESCRIPTION
				"Description."
			::= { topUscProfileEntry 1 }

		
		-- 1.3.6.1.4.1.32285.11.2.3.14.1.2.1.2
		topUscProfileDesc OBJECT-TYPE
			SYNTAX OCTET STRING (SIZE (1..32))
			MAX-ACCESS read-write
			STATUS current
			DESCRIPTION
				"Description."
			::= { topUscProfileEntry 2 }

		
		-- 1.3.6.1.4.1.32285.11.2.3.14.1.2.1.3
		topUscProfileRuleCount OBJECT-TYPE
			SYNTAX INTEGER
			MAX-ACCESS read-only
			STATUS current
			DESCRIPTION
				"Description."
			::= { topUscProfileEntry 3 }

		
		-- 1.3.6.1.4.1.32285.11.2.3.14.1.2.1.4
		topUscProfileRefCount OBJECT-TYPE
			SYNTAX INTEGER
			MAX-ACCESS read-only
			STATUS current
			DESCRIPTION
				"Description."
			::= { topUscProfileEntry 4 }

		
		-- 1.3.6.1.4.1.32285.11.2.3.14.1.2.1.5
		topUscProfileRowStatus OBJECT-TYPE
			SYNTAX RowStatus
			MAX-ACCESS read-create
			STATUS current
			DESCRIPTION
				"Description."
			::= { topUscProfileEntry 5 }

		
		-- 1.3.6.1.4.1.32285.11.2.3.14.1.3
		topUscProfileRuleTable OBJECT-TYPE
			SYNTAX SEQUENCE OF TopUscProfileRuleEntry
			MAX-ACCESS not-accessible
			STATUS current
			DESCRIPTION
				"Description."
			::= { topQosRuleObjects 3 }

		
		-- 1.3.6.1.4.1.32285.11.2.3.14.1.3.1
		topUscProfileRuleEntry OBJECT-TYPE
			SYNTAX TopUscProfileRuleEntry
			MAX-ACCESS not-accessible
			STATUS current
			DESCRIPTION
				"Description."
			INDEX { topUscRuleProfileIndex, topUscRuleRuleIndex }
			::= { topUscProfileRuleTable 1 }

		
		TopUscProfileRuleEntry ::=
			SEQUENCE { 
				topUscRuleProfileIndex
					INTEGER,
				topUscRuleRuleIndex
					INTEGER,
				topUscRuleMatchBitmap
					BITS,
				topUscRuleDstMac
					MacAddress,
				topUscRuleSrcMac
					MacAddress,
				topUscRuleVlanId
					INTEGER,
				topUscRuleVlanCos
					INTEGER,
				topUscRuleEtherType
					INTEGER,
				topUscRuleIpv4Tos
					INTEGER,
				topUscRuleIpv4Dscp
					INTEGER,
				topUscRuleIpv4Type
					INTEGER,
				topUscRuleIpv4Da
					INTEGER,
				topUscRuleIpv4Sa
					INTEGER,
				topUscRuleIpv6Tc
					INTEGER,
				topUscRuleIpv6Fl
					INTEGER,
				topUscRuleIpv6Nh
					INTEGER,
				topUscRuleIpv6DaPre
					OCTET STRING,
				topUscRuleIpv6DaSuf
					OCTET STRING,
				topUscRuleIpv6SaPre
					OCTET STRING,
				topUscRuleIpv6SaSuf
					OCTET STRING,
				topUscRuleSrcL4Port
					INTEGER,
				topUscRuleDstL4Port
					INTEGER,
				topUscRuleActionBitmap
					BITS,
				topUscRuleQueueId
					INTEGER,
				topUscRuleSlaProfileId
					INTEGER,
				topUscRuleCos
					INTEGER,
				topUscRuleRateLimit
					Unsigned32,
				topUscProfileRuleAddDelFlag
					INTEGER,
				topUscRuleRowStatus
					RowStatus
			 }

		-- 1.3.6.1.4.1.32285.11.2.3.14.1.3.1.1
		topUscRuleProfileIndex OBJECT-TYPE
			SYNTAX INTEGER (1..128)
			MAX-ACCESS not-accessible
			STATUS current
			DESCRIPTION
				"Description."
			::= { topUscProfileRuleEntry 1 }

		
		-- 1.3.6.1.4.1.32285.11.2.3.14.1.3.1.2
		topUscRuleRuleIndex OBJECT-TYPE
			SYNTAX INTEGER (1..8)
			MAX-ACCESS not-accessible
			STATUS current
			DESCRIPTION
				"Description."
			::= { topUscProfileRuleEntry 2 }

		
		-- 1.3.6.1.4.1.32285.11.2.3.14.1.3.1.3
		topUscRuleMatchBitmap OBJECT-TYPE
			SYNTAX BITS
				{
				dstMac(0),
				srcMac(1),
				cvlanId(2),
				cvlanCos(3),
				etherType(4),
				ipv4Tos(5),
				ipv4Dscp(6),
				ipv4Type(7),
				ipv4Da(8),
				ipv4Sa(9),
				ipv6Tc(10),
				ipv6Fl(11),
				ipv6Nh(12),
				ipv6DaPrefix(13),
				ipv6Da(14),
				ipv6SaPrefix(15),
				ipv6Sa(16),
				srcL4Port(17),
				dstL4Port(18)
				}
			MAX-ACCESS read-write
			STATUS current
			DESCRIPTION
				"Description."
			::= { topUscProfileRuleEntry 3 }

		
		-- 1.3.6.1.4.1.32285.11.2.3.14.1.3.1.4
		topUscRuleDstMac OBJECT-TYPE
			SYNTAX MacAddress
			MAX-ACCESS read-write
			STATUS current
			DESCRIPTION
				"Description."
			::= { topUscProfileRuleEntry 4 }

		
		-- 1.3.6.1.4.1.32285.11.2.3.14.1.3.1.5
		topUscRuleSrcMac OBJECT-TYPE
			SYNTAX MacAddress
			MAX-ACCESS read-write
			STATUS current
			DESCRIPTION
				"Description."
			::= { topUscProfileRuleEntry 5 }

		
		-- 1.3.6.1.4.1.32285.11.2.3.14.1.3.1.6
		topUscRuleVlanId OBJECT-TYPE
			SYNTAX INTEGER (0..4094)
			MAX-ACCESS read-write
			STATUS current
			DESCRIPTION
				"Description."
			::= { topUscProfileRuleEntry 6 }

		
		-- 1.3.6.1.4.1.32285.11.2.3.14.1.3.1.7
		topUscRuleVlanCos OBJECT-TYPE
			SYNTAX INTEGER (0..7)
			MAX-ACCESS read-write
			STATUS current
			DESCRIPTION
				"Description."
			::= { topUscProfileRuleEntry 7 }

		
		-- 1.3.6.1.4.1.32285.11.2.3.14.1.3.1.8
		topUscRuleEtherType OBJECT-TYPE
			SYNTAX INTEGER
			MAX-ACCESS read-write
			STATUS current
			DESCRIPTION
				"Description."
			::= { topUscProfileRuleEntry 8 }

		
		-- 1.3.6.1.4.1.32285.11.2.3.14.1.3.1.9
		topUscRuleIpv4Tos OBJECT-TYPE
			SYNTAX INTEGER (0..15)
			MAX-ACCESS read-write
			STATUS current
			DESCRIPTION
				"Description."
			::= { topUscProfileRuleEntry 9 }

		
		-- 1.3.6.1.4.1.32285.11.2.3.14.1.3.1.10
		topUscRuleIpv4Dscp OBJECT-TYPE
			SYNTAX INTEGER (0..63)
			MAX-ACCESS read-write
			STATUS current
			DESCRIPTION
				"Description."
			::= { topUscProfileRuleEntry 10 }

		
		-- 1.3.6.1.4.1.32285.11.2.3.14.1.3.1.11
		topUscRuleIpv4Type OBJECT-TYPE
			SYNTAX INTEGER
			MAX-ACCESS read-write
			STATUS current
			DESCRIPTION
				"Description."
			::= { topUscProfileRuleEntry 11 }

		
		-- 1.3.6.1.4.1.32285.11.2.3.14.1.3.1.12
		topUscRuleIpv4Da OBJECT-TYPE
			SYNTAX INTEGER
			MAX-ACCESS read-write
			STATUS current
			DESCRIPTION
				"Description."
			::= { topUscProfileRuleEntry 12 }

		
		-- 1.3.6.1.4.1.32285.11.2.3.14.1.3.1.13
		topUscRuleIpv4Sa OBJECT-TYPE
			SYNTAX INTEGER
			MAX-ACCESS read-write
			STATUS current
			DESCRIPTION
				"Description."
			::= { topUscProfileRuleEntry 13 }

		
		-- 1.3.6.1.4.1.32285.11.2.3.14.1.3.1.14
		topUscRuleIpv6Tc OBJECT-TYPE
			SYNTAX INTEGER (0..255)
			MAX-ACCESS read-write
			STATUS current
			DESCRIPTION
				"Description."
			::= { topUscProfileRuleEntry 14 }

		
		-- 1.3.6.1.4.1.32285.11.2.3.14.1.3.1.15
		topUscRuleIpv6Fl OBJECT-TYPE
			SYNTAX INTEGER (0..1048575)
			MAX-ACCESS read-write
			STATUS current
			DESCRIPTION
				"Description."
			::= { topUscProfileRuleEntry 15 }

		
		-- 1.3.6.1.4.1.32285.11.2.3.14.1.3.1.16
		topUscRuleIpv6Nh OBJECT-TYPE
			SYNTAX INTEGER
			MAX-ACCESS read-write
			STATUS current
			DESCRIPTION
				"Description."
			::= { topUscProfileRuleEntry 16 }

		
		-- 1.3.6.1.4.1.32285.11.2.3.14.1.3.1.17
		topUscRuleIpv6DaPre OBJECT-TYPE
			SYNTAX OCTET STRING (SIZE (8))
			MAX-ACCESS read-write
			STATUS current
			DESCRIPTION
				"Description."
			::= { topUscProfileRuleEntry 17 }

		
		-- 1.3.6.1.4.1.32285.11.2.3.14.1.3.1.18
		topUscRuleIpv6DaSuf OBJECT-TYPE
			SYNTAX OCTET STRING (SIZE (8))
			MAX-ACCESS read-write
			STATUS current
			DESCRIPTION
				"Description."
			::= { topUscProfileRuleEntry 18 }

		
		-- 1.3.6.1.4.1.32285.11.2.3.14.1.3.1.19
		topUscRuleIpv6SaPre OBJECT-TYPE
			SYNTAX OCTET STRING (SIZE (8))
			MAX-ACCESS read-write
			STATUS current
			DESCRIPTION
				"Description."
			::= { topUscProfileRuleEntry 19 }

		
		-- 1.3.6.1.4.1.32285.11.2.3.14.1.3.1.20
		topUscRuleIpv6SaSuf OBJECT-TYPE
			SYNTAX OCTET STRING (SIZE (8))
			MAX-ACCESS read-write
			STATUS current
			DESCRIPTION
				"Description."
			::= { topUscProfileRuleEntry 20 }

		
		-- 1.3.6.1.4.1.32285.11.2.3.14.1.3.1.21
		topUscRuleSrcL4Port OBJECT-TYPE
			SYNTAX INTEGER
			MAX-ACCESS read-write
			STATUS current
			DESCRIPTION
				"Description."
			::= { topUscProfileRuleEntry 21 }

		
		-- 1.3.6.1.4.1.32285.11.2.3.14.1.3.1.22
		topUscRuleDstL4Port OBJECT-TYPE
			SYNTAX INTEGER
			MAX-ACCESS read-write
			STATUS current
			DESCRIPTION
				"Description."
			::= { topUscProfileRuleEntry 22 }

		
		-- 1.3.6.1.4.1.32285.11.2.3.14.1.3.1.23
		topUscRuleActionBitmap OBJECT-TYPE
			SYNTAX BITS
				{
				setQueue(0),
				setQueueSla(1),
				setCos(2),
				setRsv(3),
				setDeny(4)
				}
			MAX-ACCESS read-write
			STATUS current
			DESCRIPTION
				"Description."
			::= { topUscProfileRuleEntry 23 }

		
		-- 1.3.6.1.4.1.32285.11.2.3.14.1.3.1.24
		topUscRuleQueueId OBJECT-TYPE
			SYNTAX INTEGER (0..7)
			MAX-ACCESS read-write
			STATUS current
			DESCRIPTION
				"Description."
			::= { topUscProfileRuleEntry 24 }

		
		-- 1.3.6.1.4.1.32285.11.2.3.14.1.3.1.25
		topUscRuleSlaProfileId OBJECT-TYPE
			SYNTAX INTEGER (0..128)
			MAX-ACCESS read-write
			STATUS current
			DESCRIPTION
				"Description."
			::= { topUscProfileRuleEntry 25 }

		
		-- 1.3.6.1.4.1.32285.11.2.3.14.1.3.1.26
		topUscRuleCos OBJECT-TYPE
			SYNTAX INTEGER (0..7)
			MAX-ACCESS read-write
			STATUS current
			DESCRIPTION
				"Description."
			::= { topUscProfileRuleEntry 26 }

		
		-- 1.3.6.1.4.1.32285.11.2.3.14.1.3.1.27
		topUscRuleRateLimit OBJECT-TYPE
			SYNTAX Unsigned32
			MAX-ACCESS read-write
			STATUS current
			DESCRIPTION
				"Description."
			::= { topUscProfileRuleEntry 27 }

		
        	-- 1.3.6.1.4.1.32285.11.2.3.14.1.3.1.28
		topUscProfileRuleAddDelFlag OBJECT-TYPE
			SYNTAX INTEGER
				{
				add(1),
				delete(2)
				}
			MAX-ACCESS read-write
			STATUS current
			DESCRIPTION
				"Description."
			::= { topUscProfileRuleEntry 28 }

		
		-- 1.3.6.1.4.1.32285.11.2.3.14.1.3.1.29
		topUscRuleRowStatus OBJECT-TYPE
			SYNTAX RowStatus
			MAX-ACCESS read-create
			STATUS current
			DESCRIPTION
				"Description."
			::= { topUscProfileRuleEntry 29 }

		
		-- 1.3.6.1.4.1.32285.11.2.3.14.2
		topQosBindObjects OBJECT IDENTIFIER ::= { topQosMgmtObjects 2 }

		
		-- 1.3.6.1.4.1.32285.11.2.3.14.2.1
		topUscBindOnuTable OBJECT-TYPE
			SYNTAX SEQUENCE OF TopUscBindOnuEntry
			MAX-ACCESS not-accessible
			STATUS current
			DESCRIPTION
				"Description."
			::= { topQosBindObjects 1 }

		
		-- 1.3.6.1.4.1.32285.11.2.3.14.2.1.1
		topUscBindOnuEntry OBJECT-TYPE
			SYNTAX TopUscBindOnuEntry
			MAX-ACCESS not-accessible
			STATUS current
			DESCRIPTION
				"Description."
			INDEX { topUscBindOnuSlotIndex, topUscBindOnuPortIndex, topUscBindOnuLlidIndex, topUscBindOnuDrctIndex }
			::= { topUscBindOnuTable 1 }

		
		TopUscBindOnuEntry ::=
			SEQUENCE { 
				topUscBindOnuSlotIndex
					TopEPonSlotIndex,
				topUscBindOnuPortIndex
					TopEPonPonIndex,
				topUscBindOnuLlidIndex
					INTEGER,
				topUscBindOnuDrctIndex
					INTEGER,
				topUscBindOnuProfileId
					INTEGER,
				topUscBindOnuScheMode
					INTEGER
			 }

		-- 1.3.6.1.4.1.32285.11.2.3.14.2.1.1.1
		topUscBindOnuSlotIndex OBJECT-TYPE
			SYNTAX TopEPonSlotIndex
			MAX-ACCESS not-accessible
			STATUS current
			DESCRIPTION
				"Description."
			::= { topUscBindOnuEntry 1 }

		
		-- 1.3.6.1.4.1.32285.11.2.3.14.2.1.1.2
		topUscBindOnuPortIndex OBJECT-TYPE
			SYNTAX TopEPonPonIndex
			MAX-ACCESS not-accessible
			STATUS current
			DESCRIPTION
				"Description."
			::= { topUscBindOnuEntry 2 }

		
		-- 1.3.6.1.4.1.32285.11.2.3.14.2.1.1.3
		topUscBindOnuLlidIndex OBJECT-TYPE
			SYNTAX INTEGER
			MAX-ACCESS not-accessible
			STATUS current
			DESCRIPTION
				"Description."
			::= { topUscBindOnuEntry 3 }

		
		-- 1.3.6.1.4.1.32285.11.2.3.14.2.1.1.4
		topUscBindOnuDrctIndex OBJECT-TYPE
			SYNTAX INTEGER
			MAX-ACCESS not-accessible
			STATUS current
			DESCRIPTION
				"Description."
			::= { topUscBindOnuEntry 4 }

		
		-- 1.3.6.1.4.1.32285.11.2.3.14.2.1.1.5
		topUscBindOnuProfileId OBJECT-TYPE
			SYNTAX INTEGER
			MAX-ACCESS read-write
			STATUS current
			DESCRIPTION
				"Description."
			::= { topUscBindOnuEntry 5 }

		
		-- 1.3.6.1.4.1.32285.11.2.3.14.2.1.1.6
		topUscBindOnuScheMode OBJECT-TYPE
			SYNTAX INTEGER
				{
				llid-based(1),
				service-based(2)
				}
			MAX-ACCESS read-write
			STATUS current
			DESCRIPTION
				"Description."
			::= { topUscBindOnuEntry 6 }

		
		-- 1.3.6.1.4.1.32285.11.2.3.14.2.2
		topUscBindUniTable OBJECT-TYPE
			SYNTAX SEQUENCE OF TopUscBindUniEntry
			MAX-ACCESS not-accessible
			STATUS current
			DESCRIPTION
				"Description."
			::= { topQosBindObjects 2 }

		
		-- 1.3.6.1.4.1.32285.11.2.3.14.2.2.1
		topUscBindUniEntry OBJECT-TYPE
			SYNTAX TopUscBindUniEntry
			MAX-ACCESS not-accessible
			STATUS current
			DESCRIPTION
				"Description."
			INDEX { topUscBindUniSlotIndex, topUscBindUniPortIndex, topUscBindUniLlidIndex, topUscBindUniUniIndex, topUscBindUniDrctIndex
				 }
			::= { topUscBindUniTable 1 }

		
		TopUscBindUniEntry ::=
			SEQUENCE { 
				topUscBindUniSlotIndex
					TopEPonSlotIndex,
				topUscBindUniPortIndex
					TopEPonPonIndex,
				topUscBindUniLlidIndex
					INTEGER,
				topUscBindUniUniIndex
					INTEGER,
				topUscBindUniDrctIndex
					INTEGER,
				topUscBindUniProfileId
					INTEGER
			 }

		-- 1.3.6.1.4.1.32285.11.2.3.14.2.2.1.1
		topUscBindUniSlotIndex OBJECT-TYPE
			SYNTAX TopEPonSlotIndex
			MAX-ACCESS not-accessible
			STATUS current
			DESCRIPTION
				"Description."
			::= { topUscBindUniEntry 1 }

		
		-- 1.3.6.1.4.1.32285.11.2.3.14.2.2.1.2
		topUscBindUniPortIndex OBJECT-TYPE
			SYNTAX TopEPonPonIndex
			MAX-ACCESS not-accessible
			STATUS current
			DESCRIPTION
				"Description."
			::= { topUscBindUniEntry 2 }

		
		-- 1.3.6.1.4.1.32285.11.2.3.14.2.2.1.3
		topUscBindUniLlidIndex OBJECT-TYPE
			SYNTAX INTEGER
			MAX-ACCESS not-accessible
			STATUS current
			DESCRIPTION
				"Description."
			::= { topUscBindUniEntry 3 }

		
		-- 1.3.6.1.4.1.32285.11.2.3.14.2.2.1.4
		topUscBindUniUniIndex OBJECT-TYPE
			SYNTAX INTEGER
			MAX-ACCESS not-accessible
			STATUS current
			DESCRIPTION
				"Description."
			::= { topUscBindUniEntry 4 }

		
		-- 1.3.6.1.4.1.32285.11.2.3.14.2.2.1.5
		topUscBindUniDrctIndex OBJECT-TYPE
			SYNTAX INTEGER
			MAX-ACCESS not-accessible
			STATUS current
			DESCRIPTION
				"Description."
			::= { topUscBindUniEntry 5 }

		
		-- 1.3.6.1.4.1.32285.11.2.3.14.2.2.1.6
		topUscBindUniProfileId OBJECT-TYPE
			SYNTAX INTEGER (0..128)
			MAX-ACCESS read-write
			STATUS current
			DESCRIPTION
				"Description."
			::= { topUscBindUniEntry 6 }

		
		-- 1.3.6.1.4.1.32285.11.2.3.15
		topNtpMgmtObjects OBJECT IDENTIFIER ::= { topvisionEponTree 15 }

		
		-- 1.3.6.1.4.1.32285.11.2.3.15.1
		topNtpConfigObjects OBJECT IDENTIFIER ::= { topNtpMgmtObjects 1 }

		
		-- 1.3.6.1.4.1.32285.11.2.3.15.1.1
		topNtpSwitch OBJECT-TYPE
			SYNTAX INTEGER
				{
				on(1),
				off(2)
				}
			MAX-ACCESS read-write
			STATUS current
			DESCRIPTION
				"Description."
			::= { topNtpConfigObjects 1 }

		
		-- 1.3.6.1.4.1.32285.11.2.3.15.1.2
		topNtpServerIp OBJECT-TYPE
			SYNTAX IpAddress
			MAX-ACCESS read-write
			STATUS current
			DESCRIPTION
				"Description."
			::= { topNtpConfigObjects 2 }

		
		-- 1.3.6.1.4.1.32285.11.2.3.15.1.3
		topNtpSyncInterval OBJECT-TYPE
			SYNTAX INTEGER (10..86400)
			UNITS "s"
			MAX-ACCESS read-write
			STATUS current
			DESCRIPTION
				"Description."
			::= { topNtpConfigObjects 3 }

		
		-- 1.3.6.1.4.1.32285.11.2.3.15.1.4
		topNtpSyncTimeOut OBJECT-TYPE
			SYNTAX INTEGER (1..5)
			UNITS "second"
			MAX-ACCESS read-write
			STATUS current
			DESCRIPTION
				"Description."
			DEFVAL { 3 }
			::= { topNtpConfigObjects 4 }

		
		-- 1.3.6.1.4.1.32285.11.2.3.15.1.5
		topNtpBroadcastIp OBJECT-TYPE
			SYNTAX IpAddress
			MAX-ACCESS read-write
			STATUS current
			DESCRIPTION
				"Description."
			::= { topNtpConfigObjects 5 }

		
		-- 1.3.6.1.4.1.32285.11.2.3.16
		topPortIsolationMgmtObjects OBJECT IDENTIFIER ::= { topvisionEponTree 16 }

		
		-- 1.3.6.1.4.1.32285.11.2.3.16.1
		topPortIsolationGroupConfigTable OBJECT-TYPE
			SYNTAX SEQUENCE OF TopPortIsolationGroupConfigEntry
			MAX-ACCESS not-accessible
			STATUS current
			DESCRIPTION
				"Description."
			::= { topPortIsolationMgmtObjects 1 }

		
		-- 1.3.6.1.4.1.32285.11.2.3.16.1.1
		topPortIsolationGroupConfigEntry OBJECT-TYPE
			SYNTAX TopPortIsolationGroupConfigEntry
			MAX-ACCESS not-accessible
			STATUS current
			DESCRIPTION
				"Description."
			INDEX { topPortIsolationGrpIdIndex }
			::= { topPortIsolationGroupConfigTable 1 }

		
		TopPortIsolationGroupConfigEntry ::=
			SEQUENCE { 
				topPortIsolationGrpIdIndex
					INTEGER,
				topPortIsolationGrpDesc
					OCTET STRING,
				topPortIsolationGrpMember
					OCTET STRING,
				topPortIsolationGrpRowStatus
					RowStatus
			 }

		-- 1.3.6.1.4.1.32285.11.2.3.16.1.1.1
		topPortIsolationGrpIdIndex OBJECT-TYPE
			SYNTAX INTEGER (1..32)
			MAX-ACCESS not-accessible
			STATUS current
			DESCRIPTION
				"Port-isolation group id. valid value:1-32"
			::= { topPortIsolationGroupConfigEntry 1 }

		
		-- 1.3.6.1.4.1.32285.11.2.3.16.1.1.2
		topPortIsolationGrpDesc OBJECT-TYPE
			SYNTAX OCTET STRING (SIZE (1..31))
			MAX-ACCESS read-write
			STATUS current
			DESCRIPTION
				"Description group info:1-31 bytes."
			::= { topPortIsolationGroupConfigEntry 2 }

		
		-- 1.3.6.1.4.1.32285.11.2.3.16.1.1.3
		topPortIsolationGrpMember OBJECT-TYPE
			SYNTAX OCTET STRING (SIZE (608))
			MAX-ACCESS read-only
			STATUS current
			DESCRIPTION
				"Port-isolation group include port info."
			::= { topPortIsolationGroupConfigEntry 3 }

		
		-- 1.3.6.1.4.1.32285.11.2.3.16.1.1.4
		topPortIsolationGrpRowStatus OBJECT-TYPE
			SYNTAX RowStatus
			MAX-ACCESS read-create
			STATUS current
			DESCRIPTION
				"Row Status. This object indicates the row status of this table:
				createAndGo(4): indicates that a row is created.
				destroy(6): indicates that a row is deleted."
			::= { topPortIsolationGroupConfigEntry 4 }

		
		-- 1.3.6.1.4.1.32285.11.2.3.16.2
		topPortIsolationMemberConfigTable OBJECT-TYPE
			SYNTAX SEQUENCE OF TopPortIsolationMemberConfigEntry
			MAX-ACCESS not-accessible
			STATUS current
			DESCRIPTION
				"Description."
			::= { topPortIsolationMgmtObjects 2 }

		
		-- 1.3.6.1.4.1.32285.11.2.3.16.2.1
		topPortIsolationMemberConfigEntry OBJECT-TYPE
			SYNTAX TopPortIsolationMemberConfigEntry
			MAX-ACCESS not-accessible
			STATUS current
			DESCRIPTION
				"Description."
			INDEX { topPortIsolationCardIndex, topPortIsolationPortIndex, topPortIsolationGroupIndex }
			::= { topPortIsolationMemberConfigTable 1 }

		
		TopPortIsolationMemberConfigEntry ::=
			SEQUENCE { 
				topPortIsolationCardIndex
					INTEGER,
				topPortIsolationPortIndex
					INTEGER,
				topPortIsolationGroupIndex
					INTEGER,
				topPortIsolationMemberRowStatus
					RowStatus
			 }

		-- 1.3.6.1.4.1.32285.11.2.3.16.2.1.1
		topPortIsolationCardIndex OBJECT-TYPE
			SYNTAX INTEGER (0..18)
			MAX-ACCESS not-accessible
			STATUS current
			DESCRIPTION
				"Description."
			::= { topPortIsolationMemberConfigEntry 1 }

		
		-- 1.3.6.1.4.1.32285.11.2.3.16.2.1.2
		topPortIsolationPortIndex OBJECT-TYPE
			SYNTAX INTEGER (1..32)
			MAX-ACCESS not-accessible
			STATUS current
			DESCRIPTION
				"Description."
			::= { topPortIsolationMemberConfigEntry 2 }

		
		-- 1.3.6.1.4.1.32285.11.2.3.16.2.1.3
		topPortIsolationGroupIndex OBJECT-TYPE
			SYNTAX INTEGER (1..32)
			MAX-ACCESS not-accessible
			STATUS current
			DESCRIPTION
				"Description."
			::= { topPortIsolationMemberConfigEntry 3 }

		
		-- 1.3.6.1.4.1.32285.11.2.3.16.2.1.4
		topPortIsolationMemberRowStatus OBJECT-TYPE
			SYNTAX RowStatus
			MAX-ACCESS read-create
			STATUS current
			DESCRIPTION
				"Description."
			::= { topPortIsolationMemberConfigEntry 4 }

		
		-- 1.3.6.1.4.1.32285.11.2.4
		topExpPonTree OBJECT IDENTIFIER ::= { topvisionEponEocTree 4 }

		
		
		-- 1.3.6.1.4.1.32285.11.3
		topvisionEocTree OBJECT IDENTIFIER ::= { topvisionRoot 3 }

		
		-- 1.3.6.1.4.1.32285.11.3.1
		eocPropertyIdent OBJECT IDENTIFIER ::= { topvisionEocTree 1 }

		
		-- 1.3.6.1.4.1.32285.11.3.2
		eocAlarmsIdent OBJECT IDENTIFIER ::= { topvisionEocTree 2 }

		
		-- 1.3.6.1.4.1.32285.11.3.3
		eocManagementTree OBJECT IDENTIFIER ::= { topvisionEocTree 3 }

		
		-- 1.3.6.1.4.1.32285.11.4
		topvisionWlanTree OBJECT IDENTIFIER ::= { topvisionRoot 4 }

		
		-- 1.3.6.1.4.1.32285.11.4.1
		wlanPropertyIdent OBJECT IDENTIFIER ::= { topvisionWlanTree 1 }

		
		-- 1.3.6.1.4.1.32285.11.4.2
		wlanAlarmsIdent OBJECT IDENTIFIER ::= { topvisionWlanTree 2 }

		
		-- 1.3.6.1.4.1.32285.11.4.3
		wlanManagementTree OBJECT IDENTIFIER ::= { topvisionWlanTree 3 }

		
	
	END

	
--
-- SUMA-EPONEOC-EPON-MIB.mib
--
