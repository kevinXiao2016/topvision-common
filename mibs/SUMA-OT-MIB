--
-- SUMA-OT-MIB.my
-- MIB generated by MG-SOFT Visual MIB Builder Version 4.0 Build 349
-- Wednesday, August 23, 2017 at 16:32:17
--

--  SUMA-OT-MIB.mib
-- MIB generated by MG-SOFT Visual MIB Builder Version 4.0 Build 349
-- Wednesday, October 19, 2011 at 15:54:31
-- 

	SUMA-OT-MIB DEFINITIONS ::= BEGIN
 
		IMPORTS
			enterprises, TimeTicks, IpAddress, Unsigned32, 
			Counter32, Counter64, OBJECT-TYPE, OBJECT-IDENTITY			
				FROM SNMPv2-SMI			
			MacAddress, DisplayString, RowStatus, DateAndTime, TEXTUAL-CONVENTION			
				FROM SNMPv2-TC;
	

--
-- Node definitions
--
	
--  Node definitions
-- 
-- 1.3.6.1.4.1.32285
		-- 1.3.6.1.4.1.32285
		sumaRoot OBJECT IDENTIFIER ::= { enterprises 32285 }

		
--  1.3.6.1.4.1.32285.11
		-- 1.3.6.1.4.1.32285.11
		topvisionRoot OBJECT IDENTIFIER ::= { sumaRoot 11 }
		
		-- 1.3.6.1.4.1.32285.11.9
		topOTTree OBJECT IDENTIFIER ::= { topvisionRoot 9 }

		
		-- 1.3.6.1.4.1.32285.11.9.1
		topOFABasicInfoTable OBJECT-TYPE
			SYNTAX SEQUENCE OF TopOFABasicInfoEntry
			MAX-ACCESS not-accessible
			STATUS current
			DESCRIPTION
				"Description."
			::= { topOTTree 1 }

		
		-- 1.3.6.1.4.1.32285.11.9.1.1
		topOFABasicInfoEntry OBJECT-TYPE
			SYNTAX TopOFABasicInfoEntry
			MAX-ACCESS not-accessible
			STATUS current
			DESCRIPTION
				"Description."
			INDEX { topOFAOptiDeviceIndex }
			::= { topOFABasicInfoTable 1 }

		
		TopOFABasicInfoEntry ::=
			SEQUENCE { 
				topOFAOptiDeviceIndex
					INTEGER,
				topOFAOptiPlatSN
					OCTET STRING,
				topOFAOptiHWVer
					OCTET STRING,
				topOFAOptiSWVer
					OCTET STRING,
				topOFAOptiModuleType
					OCTET STRING,
				topOFAOptiInputPower
					INTEGER,
				topOFAOptiOutputPower
					INTEGER,
				topOFAOptiPump1BiasCurr
					INTEGER,
				topOFAOptiPump1Temp
					INTEGER,
				topOFAOptiPump1Tec
					INTEGER,
				topOFAOptiPump2BiasCurr
					INTEGER,
				topOFAOptiPump2Temp
					INTEGER,
				topOFAOptiPump2Tec
					INTEGER,
				topOFAOptiVoltage5v
					INTEGER,
				topOFAOptiVoltage12v
					INTEGER,
				topOFAOptiSystemTemp
					INTEGER,
				topOFAOutputAtt
					INTEGER
			 }

		-- 1.3.6.1.4.1.32285.11.9.1.1.1
		topOFAOptiDeviceIndex OBJECT-TYPE
			SYNTAX INTEGER
			MAX-ACCESS not-accessible
			STATUS current
			DESCRIPTION
				"Device Index ,always 1."
			::= { topOFABasicInfoEntry 1 }

		
		-- 1.3.6.1.4.1.32285.11.9.1.1.2
		topOFAOptiPlatSN OBJECT-TYPE
			SYNTAX OCTET STRING (SIZE (1..20))
			MAX-ACCESS read-only
			STATUS current
			DESCRIPTION
				"The Plat SN info of OFA."
			::= { topOFABasicInfoEntry 2 }

		
		-- 1.3.6.1.4.1.32285.11.9.1.1.3
		topOFAOptiHWVer OBJECT-TYPE
			SYNTAX  OCTET STRING (SIZE (1..8))
			MAX-ACCESS read-only
			STATUS current
			DESCRIPTION
				"Hardware Version."
			::= { topOFABasicInfoEntry 3 }

		
		-- 1.3.6.1.4.1.32285.11.9.1.1.4
		topOFAOptiSWVer OBJECT-TYPE
			SYNTAX OCTET STRING (SIZE (1..8))
			MAX-ACCESS read-only
			STATUS current
			DESCRIPTION
				"Software Version."
			::= { topOFABasicInfoEntry 4 }

		
		-- 1.3.6.1.4.1.32285.11.9.1.1.5
		topOFAOptiModuleType OBJECT-TYPE
			SYNTAX OCTET STRING (SIZE (1..8))
			MAX-ACCESS read-only
			STATUS current
			DESCRIPTION
				"Module Type ."
			::= { topOFABasicInfoEntry 5 }

		
		-- 1.3.6.1.4.1.32285.11.9.1.1.6
		topOFAOptiInputPower OBJECT-TYPE
			SYNTAX INTEGER
			MAX-ACCESS read-only
			STATUS current
			DESCRIPTION
				"Input Power,unit by 0.1dBm."
			::= { topOFABasicInfoEntry 6 }

		
		-- 1.3.6.1.4.1.32285.11.9.1.1.7
		topOFAOptiOutputPower OBJECT-TYPE
			SYNTAX INTEGER
			MAX-ACCESS read-only
			STATUS current
			DESCRIPTION
				"Output Power,unit by 0.1dBm."
			::= { topOFABasicInfoEntry 7 }

		
		-- 1.3.6.1.4.1.32285.11.9.1.1.8
		topOFAOptiPump1BiasCurr OBJECT-TYPE
			SYNTAX INTEGER
			MAX-ACCESS read-only
			STATUS current
			DESCRIPTION
				"Bias current of Pump1,unit by mA."
			::= { topOFABasicInfoEntry 8 }

		
		-- 1.3.6.1.4.1.32285.11.9.1.1.9
		topOFAOptiPump1Temp OBJECT-TYPE
			SYNTAX INTEGER
			MAX-ACCESS read-only
			STATUS current
			DESCRIPTION
				"Temperature of Pump1,unit by 0.1C."
			::= { topOFABasicInfoEntry 9 }

		
		-- 1.3.6.1.4.1.32285.11.9.1.1.10
		topOFAOptiPump1Tec OBJECT-TYPE
			SYNTAX INTEGER
			MAX-ACCESS read-only
			STATUS current
			DESCRIPTION
				"Temperature current of Pump1,unit by mA."
			::= { topOFABasicInfoEntry 10 }

		
		-- 1.3.6.1.4.1.32285.11.9.1.1.11
		topOFAOptiPump2BiasCurr OBJECT-TYPE
			SYNTAX INTEGER
			MAX-ACCESS read-only
			STATUS current
			DESCRIPTION
				"Bias current of Pump2,unit by mA."
			::= { topOFABasicInfoEntry 11 }

		
		-- 1.3.6.1.4.1.32285.11.9.1.1.12
		topOFAOptiPump2Temp OBJECT-TYPE
			SYNTAX INTEGER
			MAX-ACCESS read-only
			STATUS current
			DESCRIPTION
				"Temperature of Pump2,unit by 0.1C."
			::= { topOFABasicInfoEntry 12 }

		
		-- 1.3.6.1.4.1.32285.11.9.1.1.13
		topOFAOptiPump2Tec OBJECT-TYPE
			SYNTAX INTEGER
			MAX-ACCESS read-only
			STATUS current
			DESCRIPTION
				"Temperature current of Pump2,unit by mA."
			::= { topOFABasicInfoEntry 13 }

		
		-- 1.3.6.1.4.1.32285.11.9.1.1.14
		topOFAOptiVoltage5v OBJECT-TYPE
			SYNTAX INTEGER
			MAX-ACCESS read-only
			STATUS current
			DESCRIPTION
				"5V voltage,unit by 0.1V."
			::= { topOFABasicInfoEntry 14 }

		
		-- 1.3.6.1.4.1.32285.11.9.1.1.15
		topOFAOptiVoltage12v OBJECT-TYPE
			SYNTAX INTEGER
			MAX-ACCESS read-only
			STATUS current
			DESCRIPTION
				"12V voltage,unit by 0.1V."
			::= { topOFABasicInfoEntry 15 }

		
		-- 1.3.6.1.4.1.32285.11.9.1.1.16
		topOFAOptiSystemTemp OBJECT-TYPE
			SYNTAX INTEGER
			MAX-ACCESS read-only
			STATUS current
			DESCRIPTION
				"System tempature."
			::= { topOFABasicInfoEntry 16 }
			
			
		-- 1.3.6.1.4.1.32285.11.9.1.1.17
		topOFAOutputAtt OBJECT-TYPE
			SYNTAX INTEGER
			MAX-ACCESS read-write
			STATUS current
			DESCRIPTION
				"Output attenuation,unit by 0.1dB."
			::= { topOFABasicInfoEntry 17 }

		
		-- 1.3.6.1.4.1.32285.11.9.2
		topOFAAlarmThresholdTable OBJECT-TYPE
			SYNTAX SEQUENCE OF TopOFAAlarmThresholdEntry
			MAX-ACCESS not-accessible
			STATUS current
			DESCRIPTION
				"Description."
			::= { topOTTree 2 }

		
		-- 1.3.6.1.4.1.32285.11.9.2.1
		topOFAAlarmThresholdEntry OBJECT-TYPE
			SYNTAX TopOFAAlarmThresholdEntry
			MAX-ACCESS not-accessible
			STATUS current
			DESCRIPTION
				"Description."
			INDEX { topOFAAlarmThresholdIndex }
			::= { topOFAAlarmThresholdTable 1 }

		
		TopOFAAlarmThresholdEntry ::=
			SEQUENCE { 
				topOFAAlarmThresholdIndex
					INTEGER,
				topOFAInputAlarmThresholdUpper
					INTEGER,
				topOFAInputAlarmThresholdLower
					INTEGER,
				topOFAOutputAlarmThresholdUpper
					INTEGER,
				topOFAOutputAlarmThresholdLower
					INTEGER,
				topOFAPump1BiasAlarmThresholdUpper
					INTEGER,
				topOFAPump1BiasAlarmThresholdLower
					INTEGER,
				topOFAPump1TempAlarmThresholdUpper
					INTEGER,
				topOFAPump1TempAlarmThresholdLower
					INTEGER,
				topOFAPump1TecAlarmThresholdUpper
					INTEGER,
				topOFAPump1TecAlarmThresholdLower
					INTEGER,
				topOFAPump2BiasAlarmThresholdUpper
					INTEGER,
				topOFAPump2BiasAlarmThresholdLower
					INTEGER,
				topOFAPump2TempAlarmThresholdUpper
					INTEGER,
				topOFAPump2TempAlarmThresholdLower
					INTEGER,
				topOFAVoltage5AlarmThresholdUpper
					INTEGER,
				topOFAVoltage5AlarmThresholdLower
					INTEGER,
				topOFAVoltage12AlarmThresholdUpper
					INTEGER,
				topOFAVoltage12AlarmThresholdLower
					INTEGER
			 }

		-- 1.3.6.1.4.1.32285.11.9.2.1.1
		topOFAAlarmThresholdIndex OBJECT-TYPE
			SYNTAX INTEGER
			MAX-ACCESS read-write
			STATUS current
			DESCRIPTION
				"Index."
			::= { topOFAAlarmThresholdEntry 1 }

		
		-- 1.3.6.1.4.1.32285.11.9.2.1.2
		topOFAInputAlarmThresholdUpper OBJECT-TYPE
			SYNTAX INTEGER
			MAX-ACCESS read-write
			STATUS current
			DESCRIPTION
				"Input power Upper Threshold,unit by 0.1dBm."
			::= { topOFAAlarmThresholdEntry 2 }

		
		-- 1.3.6.1.4.1.32285.11.9.2.1.3
		topOFAInputAlarmThresholdLower OBJECT-TYPE
			SYNTAX INTEGER
			MAX-ACCESS read-write
			STATUS current
			DESCRIPTION
				"Input power Lower Threshold,unit by 0.1dBm."
			::= { topOFAAlarmThresholdEntry 3 }

		
		-- 1.3.6.1.4.1.32285.11.9.2.1.4
		topOFAOutputAlarmThresholdUpper OBJECT-TYPE
			SYNTAX INTEGER
			MAX-ACCESS read-write
			STATUS current
			DESCRIPTION
				"Output power Upper Threshold,unit by 0.1dBm."
			::= { topOFAAlarmThresholdEntry 4 }

		
		-- 1.3.6.1.4.1.32285.11.9.2.1.5
		topOFAOutputAlarmThresholdLower OBJECT-TYPE
			SYNTAX INTEGER
			MAX-ACCESS read-write
			STATUS current
			DESCRIPTION
				"Output power Lower Threshold,unit by 0.1dBm."
			::= { topOFAAlarmThresholdEntry 5 }

		
		-- 1.3.6.1.4.1.32285.11.9.2.1.6
		topOFAPump1BiasAlarmThresholdUpper OBJECT-TYPE
			SYNTAX INTEGER
			MAX-ACCESS read-write
			STATUS current
			DESCRIPTION
				"Pump1 bias current Upper Threshold,unit by mA."
			::= { topOFAAlarmThresholdEntry 6 }

		
		-- 1.3.6.1.4.1.32285.11.9.2.1.7
		topOFAPump1BiasAlarmThresholdLower OBJECT-TYPE
			SYNTAX INTEGER
			MAX-ACCESS read-write
			STATUS current
			DESCRIPTION
				"Pump1 bias current Lower Threshold,unit by mA."
			::= { topOFAAlarmThresholdEntry 7 }

		
		-- 1.3.6.1.4.1.32285.11.9.2.1.8
		topOFAPump1TempAlarmThresholdUpper OBJECT-TYPE
			SYNTAX INTEGER
			MAX-ACCESS read-write
			STATUS current
			DESCRIPTION
				"Pump1 tempature Upper Threshold,unit by 0.1C."
			::= { topOFAAlarmThresholdEntry 8 }

		
		-- 1.3.6.1.4.1.32285.11.9.2.1.9
		topOFAPump1TempAlarmThresholdLower OBJECT-TYPE
			SYNTAX INTEGER
			MAX-ACCESS read-write
			STATUS current
			DESCRIPTION
				"Pump1 tempature Lower Threshold,unit by 0.1C."
			::= { topOFAAlarmThresholdEntry 9 }

		
		-- 1.3.6.1.4.1.32285.11.9.2.1.10
		topOFAPump1TecAlarmThresholdUpper OBJECT-TYPE
			SYNTAX INTEGER
			MAX-ACCESS read-write
			STATUS current
			DESCRIPTION
				"Pump1 tempature current Upper Threshold,unit by mA."
			::= { topOFAAlarmThresholdEntry 10 }

		
		-- 1.3.6.1.4.1.32285.11.9.2.1.11
		topOFAPump1TecAlarmThresholdLower OBJECT-TYPE
			SYNTAX INTEGER
			MAX-ACCESS read-write
			STATUS current
			DESCRIPTION
				"Pump1 tempature current Lower Threshold,unit by mA."
			::= { topOFAAlarmThresholdEntry 11 }

		
		-- 1.3.6.1.4.1.32285.11.9.2.1.12
		topOFAPump2BiasAlarmThresholdUpper OBJECT-TYPE
			SYNTAX INTEGER
			MAX-ACCESS read-write
			STATUS current
			DESCRIPTION
				"Pump2 bias current Upper Threshold,unit by mA."
			::= { topOFAAlarmThresholdEntry 12 }

		
		-- 1.3.6.1.4.1.32285.11.9.2.1.13
		topOFAPump2BiasAlarmThresholdLower OBJECT-TYPE
			SYNTAX INTEGER
			MAX-ACCESS read-write
			STATUS current
			DESCRIPTION
				"Pump2 bias current Lower Threshold,unit by mA."
			::= { topOFAAlarmThresholdEntry 13 }

		
		-- 1.3.6.1.4.1.32285.11.9.2.1.14
		topOFAPump2TempAlarmThresholdUpper OBJECT-TYPE
			SYNTAX INTEGER
			MAX-ACCESS read-write
			STATUS current
			DESCRIPTION
				"Pump2 tempature Upper Threshold,unit by 0.1C."
			::= { topOFAAlarmThresholdEntry 14 }

		
		-- 1.3.6.1.4.1.32285.11.9.2.1.15
		topOFAPump2TempAlarmThresholdLower OBJECT-TYPE
			SYNTAX INTEGER
			MAX-ACCESS read-write
			STATUS current
			DESCRIPTION
				"Pump2 tempature Lower Threshold,unit by 0.1C."
			::= { topOFAAlarmThresholdEntry 15 }

		
		-- 1.3.6.1.4.1.32285.11.9.2.1.16
		topOFAVoltage5AlarmThresholdUpper OBJECT-TYPE
			SYNTAX INTEGER
			MAX-ACCESS read-write
			STATUS current
			DESCRIPTION
				"5V voltage Upper Threshold."
			::= { topOFAAlarmThresholdEntry 16 }

		
		-- 1.3.6.1.4.1.32285.11.9.2.1.17
		topOFAVoltage5AlarmThresholdLower OBJECT-TYPE
			SYNTAX INTEGER
			MAX-ACCESS read-write
			STATUS current
			DESCRIPTION
				"5V voltage Lower Threshold."
			::= { topOFAAlarmThresholdEntry 17 }

		
		-- 1.3.6.1.4.1.32285.11.9.2.1.18
		topOFAVoltage12AlarmThresholdUpper OBJECT-TYPE
			SYNTAX INTEGER
			MAX-ACCESS read-write
			STATUS current
			DESCRIPTION
				"12V voltage Upper Threshold."
			::= { topOFAAlarmThresholdEntry 18 }

		
		-- 1.3.6.1.4.1.32285.11.9.2.1.19
		topOFAVoltage12AlarmThresholdLower OBJECT-TYPE
			SYNTAX INTEGER
			MAX-ACCESS read-write
			STATUS current
			DESCRIPTION
				"12V voltage Lower Threshold."
			::= { topOFAAlarmThresholdEntry 19 }

		
	
	END

--
-- SUMA-OT-MIB.my
--
