--
-- SUMA-GPON-MIB.mib
-- MIB generated by MG-SOFT Visual MIB Builder Version 4.0 Build 349
-- Thursday, June 22, 2017 at 16:16:24
--

--  SUMA-GPON-MIB.my
-- MIB generated by MG-SOFT Visual MIB Builder Version 4.0 Build 349
-- Tuesday, December 20, 2016 at 09:00:41
-- 
--  SUMA-GPON-MIB.my
-- MIB generated by MG-SOFT Visual MIB Builder Version 4.0 Build 349
-- Monday, December 19, 2016 at 14:05:25
-- 
--  SUMA-GPON-MIB.my
-- MIB generated by MG-SOFT Visual MIB Builder Version 4.0 Build 349
-- Sunday, December 18, 2016 at 14:46:38
-- 
--  SUMA-GPON-MIB.mib
-- MIB generated by MG-SOFT Visual MIB Builder Version 4.0 Build 349
-- Wednesday, October 19, 2011 at 15:54:31
-- 

	SUMA-GPON-MIB DEFINITIONS ::= BEGIN
 
		IMPORTS
			enterprises, Unsigned32, OBJECT-TYPE			
				FROM SNMPv2-SMI			
			MacAddress, RowStatus, TEXTUAL-CONVENTION			
				FROM SNMPv2-TC;
	

-- 
-- Textual conventions
-- 
		TopGPonSlotIndex ::= TEXTUAL-CONVENTION
			STATUS current
			DESCRIPTION 
				"This represents the slot number in the epon shelf."
			SYNTAX INTEGER (1..18)

		TopGPonPonIndex ::= TEXTUAL-CONVENTION
			STATUS current
			DESCRIPTION 
				"This represents the PON number in the epon board."
			SYNTAX INTEGER (1..8)

		TopGPonOnuAuthNum ::= TEXTUAL-CONVENTION
			STATUS current
			DESCRIPTION 
				"This represents the ONU auth number in the epon board."
			SYNTAX INTEGER (1..128)

		TopGPonUniPortIndex ::= TEXTUAL-CONVENTION
			STATUS current
			DESCRIPTION 
				"This represents the ONU uni number in the epon board."
			SYNTAX INTEGER (1..32)

		TopGPonSniIndex ::= TEXTUAL-CONVENTION
			STATUS current
			DESCRIPTION 
				"This represents the sni port number in the uplink board."
			SYNTAX INTEGER (1..8)

		TopGPonDeviceIndex ::= TEXTUAL-CONVENTION
			STATUS current
			DESCRIPTION 
				"From MSB on, OLT slot index-8bits, PON/SNI port-8bits, 
				OnuNUM-8bits and UNI port-8bits.
				OLT PON/SNI Port - OnuNum and UNI port shall be set to 0."
			SYNTAX Unsigned32


-- Textual conventions
-- 
-- Node definitions
-- 1.3.6.1.4.1.32285
		-- 1.3.6.1.4.1.32285
		sumaRoot OBJECT IDENTIFIER ::= { enterprises 32285 }

		
--  1.3.6.1.4.1.32285.11
		-- 1.3.6.1.4.1.32285.11
		topvisionRoot OBJECT IDENTIFIER ::= { sumaRoot 11 }

		
--  1.3.6.1.4.1.32285.11.5
		-- 1.3.6.1.4.1.32285.11.5
		topvisionGponTree OBJECT IDENTIFIER ::= { topvisionRoot 5 }

		
--  1.3.6.1.4.1.32285.11.5.1
		-- 1.3.6.1.4.1.32285.11.5.1
		topGponOnuObjects OBJECT IDENTIFIER ::= { topvisionGponTree 1 }

		
--  1.3.6.1.4.1.32285.11.5.1.1
		-- 1.3.6.1.4.1.32285.11.5.1.1
		topGponOnuModifyTable OBJECT-TYPE
			SYNTAX SEQUENCE OF TopGponOnuModifyEntry
			MAX-ACCESS not-accessible
			STATUS current
			DESCRIPTION
				"ONU replace table"
			::= { topGponOnuObjects 1 }

		
--  1.3.6.1.4.1.32285.11.5.1.1.1
		-- 1.3.6.1.4.1.32285.11.5.1.1.1
		topGponOnuModifyEntry OBJECT-TYPE
			SYNTAX TopGponOnuModifyEntry
			MAX-ACCESS not-accessible
			STATUS current
			DESCRIPTION
				"ONU replace entry.
				supported mode:MAC only, sn only, password only,sn+password,
				other mode will not be supported at present."
			INDEX { topGponOnuModifyCardIndex, topGponOnuModifyPonIndex, topGponOnuModifyOnuIndex }
			::= { topGponOnuModifyTable 1 }

		
		TopGponOnuModifyEntry ::=
			SEQUENCE { 
				topGponOnuModifyCardIndex
					INTEGER,
				topGponOnuModifyPonIndex
					INTEGER,
				topGponOnuModifyOnuIndex
					INTEGER,
				topGponOnuModifySN
					OCTET STRING,
				topGponOnuModifyPwd
					OCTET STRING,
				topGponOnuModifyLoid
					OCTET STRING
			 }

--  1.3.6.1.4.1.32285.11.5.1.1.1.1
		-- 1.3.6.1.4.1.32285.11.5.1.1.1.1
		topGponOnuModifyCardIndex OBJECT-TYPE
			SYNTAX INTEGER
			MAX-ACCESS not-accessible
			STATUS current
			DESCRIPTION
				"onu slot Index"
			::= { topGponOnuModifyEntry 1 }

		
--  1.3.6.1.4.1.32285.11.5.1.1.1.2
		-- 1.3.6.1.4.1.32285.11.5.1.1.1.2
		topGponOnuModifyPonIndex OBJECT-TYPE
			SYNTAX INTEGER
			MAX-ACCESS not-accessible
			STATUS current
			DESCRIPTION
				"onu pon Index"
			::= { topGponOnuModifyEntry 2 }

		
--  1.3.6.1.4.1.32285.11.5.1.1.1.3
		-- 1.3.6.1.4.1.32285.11.5.1.1.1.3
		topGponOnuModifyOnuIndex OBJECT-TYPE
			SYNTAX INTEGER
			MAX-ACCESS not-accessible
			STATUS current
			DESCRIPTION
				"onu auth Index"
			::= { topGponOnuModifyEntry 3 }

		
--  1.3.6.1.4.1.32285.11.5.1.1.1.4
		-- 1.3.6.1.4.1.32285.11.5.1.1.1.4
		topGponOnuModifySN OBJECT-TYPE
			SYNTAX OCTET STRING (SIZE (8))
			MAX-ACCESS read-write
			STATUS current
			DESCRIPTION
				"Mac Address.
				Filling six bytes with 0x00, means invalid this member."
			::= { topGponOnuModifyEntry 4 }

		
--  1.3.6.1.4.1.32285.11.5.1.1.1.5
		-- 1.3.6.1.4.1.32285.11.5.1.1.1.5
		topGponOnuModifyPwd OBJECT-TYPE
			SYNTAX OCTET STRING (SIZE (0..10))
			MAX-ACCESS read-write
			STATUS current
			DESCRIPTION
				"password"
			::= { topGponOnuModifyEntry 5 }

		
--  1.3.6.1.4.1.32285.11.5.1.1.1.6
		-- 1.3.6.1.4.1.32285.11.5.1.1.1.6
		topGponOnuModifyLoid OBJECT-TYPE
			SYNTAX OCTET STRING (SIZE (0..24))
			MAX-ACCESS read-write
			STATUS current
			DESCRIPTION
				"Description."
			::= { topGponOnuModifyEntry 6 }

		
--  1.3.6.1.4.1.32285.11.5.1.2
		-- 1.3.6.1.4.1.32285.11.5.1.2
		topGponOnuCapabilityTable OBJECT-TYPE
			SYNTAX SEQUENCE OF TopGponOnuCapabilityEntry
			MAX-ACCESS not-accessible
			STATUS current
			DESCRIPTION
				"Description."
			::= { topGponOnuObjects 2 }

		
--  1.3.6.1.4.1.32285.11.5.1.2.1
		-- 1.3.6.1.4.1.32285.11.5.1.2.1
		topGponOnuCapabilityEntry OBJECT-TYPE
			SYNTAX TopGponOnuCapabilityEntry
			MAX-ACCESS not-accessible
			STATUS current
			DESCRIPTION
				"Description."
			INDEX { topGponOnuCapCardIndex, topGponOnuCapPonIndex, topGponOnuCapOnuIndex }
			::= { topGponOnuCapabilityTable 1 }

		
		TopGponOnuCapabilityEntry ::=
			SEQUENCE { 
				topGponOnuCapCardIndex
					INTEGER,
				topGponOnuCapPonIndex
					INTEGER,
				topGponOnuCapOnuIndex
					INTEGER,
				topGponOnuCapOnuPotsNum
					INTEGER
			 }

--  1.3.6.1.4.1.32285.11.5.1.2.1.1
		-- 1.3.6.1.4.1.32285.11.5.1.2.1.1
		topGponOnuCapCardIndex OBJECT-TYPE
			SYNTAX INTEGER
			MAX-ACCESS not-accessible
			STATUS current
			DESCRIPTION
				"Description."
			::= { topGponOnuCapabilityEntry 1 }

		
--  1.3.6.1.4.1.32285.11.5.1.2.1.2
		-- 1.3.6.1.4.1.32285.11.5.1.2.1.2
		topGponOnuCapPonIndex OBJECT-TYPE
			SYNTAX INTEGER
			MAX-ACCESS not-accessible
			STATUS current
			DESCRIPTION
				"Description."
			::= { topGponOnuCapabilityEntry 2 }

		
--  1.3.6.1.4.1.32285.11.5.1.2.1.3
		-- 1.3.6.1.4.1.32285.11.5.1.2.1.3
		topGponOnuCapOnuIndex OBJECT-TYPE
			SYNTAX INTEGER
			MAX-ACCESS not-accessible
			STATUS current
			DESCRIPTION
				"Description."
			::= { topGponOnuCapabilityEntry 3 }

		
--  1.3.6.1.4.1.32285.11.5.1.2.1.4
		-- 1.3.6.1.4.1.32285.11.5.1.2.1.4
		topGponOnuCapOnuPotsNum OBJECT-TYPE
			SYNTAX INTEGER (0..2)
			MAX-ACCESS read-write
			STATUS current
			DESCRIPTION
				"Description."
			::= { topGponOnuCapabilityEntry 4 }

		
--   1.3.6.1.4.1.32285.11.5.2
-- 1.3.6.1.4.1.32285.11.5.2
		-- 1.3.6.1.4.1.32285.11.5.2
		topGponUniObjects OBJECT IDENTIFIER ::= { topvisionGponTree 2 }

		
--  1.3.6.1.4.1.32285.11.5.2.1
		-- 1.3.6.1.4.1.32285.11.5.2.1
		topGponUniAttrTable OBJECT-TYPE
			SYNTAX SEQUENCE OF TopGponUniAttrEntry
			MAX-ACCESS not-accessible
			STATUS current
			DESCRIPTION
				"A list of topUniAttrTable entries."
			::= { topGponUniObjects 1 }

		
--  1.3.6.1.4.1.32285.11.5.2.1.1
		-- 1.3.6.1.4.1.32285.11.5.2.1.1
		topGponUniAttrEntry OBJECT-TYPE
			SYNTAX TopGponUniAttrEntry
			MAX-ACCESS not-accessible
			STATUS current
			DESCRIPTION
				"Description."
			INDEX { topGponUniAttrCardIndex, topGponUniAttrPonIndex, topGponUniAttrOnuIndex, topGponUniAttrUniIndex }
			::= { topGponUniAttrTable 1 }

		
		TopGponUniAttrEntry ::=
			SEQUENCE { 
				topGponUniAttrCardIndex
					INTEGER,
				topGponUniAttrPonIndex
					INTEGER,
				topGponUniAttrOnuIndex
					INTEGER,
				topGponUniAttrUniIndex
					INTEGER,
				topGponUniAttrPvid
					INTEGER,
				topGponUniAttrPvidPriority
					INTEGER
			 }

--  1.3.6.1.4.1.32285.11.5.2.1.1.1
		-- 1.3.6.1.4.1.32285.11.5.2.1.1.1
		topGponUniAttrCardIndex OBJECT-TYPE
			SYNTAX INTEGER
			MAX-ACCESS not-accessible
			STATUS current
			DESCRIPTION
				"Description."
			::= { topGponUniAttrEntry 1 }

		
--  1.3.6.1.4.1.32285.11.5.2.1.1.2
		-- 1.3.6.1.4.1.32285.11.5.2.1.1.2
		topGponUniAttrPonIndex OBJECT-TYPE
			SYNTAX INTEGER
			MAX-ACCESS not-accessible
			STATUS current
			DESCRIPTION
				"Description."
			::= { topGponUniAttrEntry 2 }

		
--  1.3.6.1.4.1.32285.11.5.2.1.1.3
		-- 1.3.6.1.4.1.32285.11.5.2.1.1.3
		topGponUniAttrOnuIndex OBJECT-TYPE
			SYNTAX INTEGER
			MAX-ACCESS not-accessible
			STATUS current
			DESCRIPTION
				"Description."
			::= { topGponUniAttrEntry 3 }

		
--  1.3.6.1.4.1.32285.11.5.2.1.1.4
		-- 1.3.6.1.4.1.32285.11.5.2.1.1.4
		topGponUniAttrUniIndex OBJECT-TYPE
			SYNTAX INTEGER
			MAX-ACCESS not-accessible
			STATUS current
			DESCRIPTION
				"Description."
			::= { topGponUniAttrEntry 4 }

		
--  1.3.6.1.4.1.32285.11.5.2.1.1.5
		-- 1.3.6.1.4.1.32285.11.5.2.1.1.5
		topGponUniAttrPvid OBJECT-TYPE
			SYNTAX INTEGER
			MAX-ACCESS read-write
			STATUS current
			DESCRIPTION
				"Description."
			::= { topGponUniAttrEntry 5 }

		
--  1.3.6.1.4.1.32285.11.5.2.1.1.6
		-- 1.3.6.1.4.1.32285.11.5.2.1.1.6
		topGponUniAttrPvidPriority OBJECT-TYPE
			SYNTAX INTEGER
			MAX-ACCESS read-write
			STATUS current
			DESCRIPTION
				"Description."
			::= { topGponUniAttrEntry 6 }

		
--  1.3.6.1.4.1.32285.11.5.2.2
		-- 1.3.6.1.4.1.32285.11.5.2.2
		topGponUniMacAddressObjects OBJECT IDENTIFIER ::= { topGponUniObjects 2 }

		
--  1.3.6.1.4.1.32285.11.5.2.2.1
		-- 1.3.6.1.4.1.32285.11.5.2.2.1
		topGponUniFilterCfgTable OBJECT-TYPE
			SYNTAX SEQUENCE OF TopGponUniFilterCfgEntry
			MAX-ACCESS not-accessible
			STATUS current
			DESCRIPTION
				"Description."
			::= { topGponUniMacAddressObjects 1 }

		
--  1.3.6.1.4.1.32285.11.5.2.2.1.1
		-- 1.3.6.1.4.1.32285.11.5.2.2.1.1
		topGponUniFilterCfgEntry OBJECT-TYPE
			SYNTAX TopGponUniFilterCfgEntry
			MAX-ACCESS not-accessible
			STATUS current
			DESCRIPTION
				"Description."
			INDEX { topGponUniFilterCardIndex, topGponUniFilterPonIndex, topGponUniFilterOnuIndex, topGponUniFilterUniIndex, topGponUniFilterMacIndex
				 }
			::= { topGponUniFilterCfgTable 1 }

		
		TopGponUniFilterCfgEntry ::=
			SEQUENCE { 
				topGponUniFilterCardIndex
					INTEGER,
				topGponUniFilterPonIndex
					INTEGER,
				topGponUniFilterOnuIndex
					INTEGER,
				topGponUniFilterUniIndex
					INTEGER,
				topGponUniFilterMacIndex
					MacAddress,
				topGponUniFilterRowstatus
					RowStatus
			 }

--  1.3.6.1.4.1.32285.11.5.2.2.1.1.1
		-- 1.3.6.1.4.1.32285.11.5.2.2.1.1.1
		topGponUniFilterCardIndex OBJECT-TYPE
			SYNTAX INTEGER
			MAX-ACCESS not-accessible
			STATUS current
			DESCRIPTION
				"Description."
			::= { topGponUniFilterCfgEntry 1 }

		
--  1.3.6.1.4.1.32285.11.5.2.2.1.1.2
		-- 1.3.6.1.4.1.32285.11.5.2.2.1.1.2
		topGponUniFilterPonIndex OBJECT-TYPE
			SYNTAX INTEGER
			MAX-ACCESS not-accessible
			STATUS current
			DESCRIPTION
				"Description."
			::= { topGponUniFilterCfgEntry 2 }

		
--  1.3.6.1.4.1.32285.11.5.2.2.1.1.3
		-- 1.3.6.1.4.1.32285.11.5.2.2.1.1.3
		topGponUniFilterOnuIndex OBJECT-TYPE
			SYNTAX INTEGER
			MAX-ACCESS not-accessible
			STATUS current
			DESCRIPTION
				"Description."
			::= { topGponUniFilterCfgEntry 3 }

		
--  1.3.6.1.4.1.32285.11.5.2.2.1.1.4
		-- 1.3.6.1.4.1.32285.11.5.2.2.1.1.4
		topGponUniFilterUniIndex OBJECT-TYPE
			SYNTAX INTEGER (1..4)
			MAX-ACCESS not-accessible
			STATUS current
			DESCRIPTION
				"Description."
			::= { topGponUniFilterCfgEntry 4 }

		
--  1.3.6.1.4.1.32285.11.5.2.2.1.1.5
		-- 1.3.6.1.4.1.32285.11.5.2.2.1.1.5
		topGponUniFilterMacIndex OBJECT-TYPE
			SYNTAX MacAddress
			MAX-ACCESS not-accessible
			STATUS current
			DESCRIPTION
				"Description."
			::= { topGponUniFilterCfgEntry 5 }

		
--  1.3.6.1.4.1.32285.11.5.2.2.1.1.6
		-- 1.3.6.1.4.1.32285.11.5.2.2.1.1.6
		topGponUniFilterRowstatus OBJECT-TYPE
			SYNTAX RowStatus
			MAX-ACCESS read-create
			STATUS current
			DESCRIPTION
				"Description."
			::= { topGponUniFilterCfgEntry 6 }

		
--  1.3.6.1.4.1.32285.11.5.2.2.2
		-- 1.3.6.1.4.1.32285.11.5.2.2.2
		topGponUniMacInfoTable OBJECT-TYPE
			SYNTAX SEQUENCE OF TopGponUniMacInfoEntry
			MAX-ACCESS not-accessible
			STATUS current
			DESCRIPTION
				"Description."
			::= { topGponUniMacAddressObjects 2 }

		
--  1.3.6.1.4.1.32285.11.5.2.2.2.1
		-- 1.3.6.1.4.1.32285.11.5.2.2.2.1
		topGponUniMacInfoEntry OBJECT-TYPE
			SYNTAX TopGponUniMacInfoEntry
			MAX-ACCESS not-accessible
			STATUS current
			DESCRIPTION
				"Description."
			INDEX { topGponUniMacInfoCardIndex, topGponUniMacInfoPonIndex, topGponUniMacInfoOnuIndex, topGponUniMacInfoUniIndex }
			::= { topGponUniMacInfoTable 1 }

		
		TopGponUniMacInfoEntry ::=
			SEQUENCE { 
				topGponUniMacInfoCardIndex
					INTEGER,
				topGponUniMacInfoPonIndex
					INTEGER,
				topGponUniMacInfoOnuIndex
					INTEGER,
				topGponUniMacInfoUniIndex
					INTEGER,
				topGponUniMacInfoTotal
					OCTET STRING
			 }

--  1.3.6.1.4.1.32285.11.5.2.2.2.1.1
		-- 1.3.6.1.4.1.32285.11.5.2.2.2.1.1
		topGponUniMacInfoCardIndex OBJECT-TYPE
			SYNTAX INTEGER
			MAX-ACCESS not-accessible
			STATUS current
			DESCRIPTION
				"Description."
			::= { topGponUniMacInfoEntry 1 }

		
--  1.3.6.1.4.1.32285.11.5.2.2.2.1.2
		-- 1.3.6.1.4.1.32285.11.5.2.2.2.1.2
		topGponUniMacInfoPonIndex OBJECT-TYPE
			SYNTAX INTEGER
			MAX-ACCESS not-accessible
			STATUS current
			DESCRIPTION
				"Description."
			::= { topGponUniMacInfoEntry 2 }

		
--  1.3.6.1.4.1.32285.11.5.2.2.2.1.3
		-- 1.3.6.1.4.1.32285.11.5.2.2.2.1.3
		topGponUniMacInfoOnuIndex OBJECT-TYPE
			SYNTAX INTEGER
			MAX-ACCESS not-accessible
			STATUS current
			DESCRIPTION
				"Description."
			::= { topGponUniMacInfoEntry 3 }

		
--  1.3.6.1.4.1.32285.11.5.2.2.2.1.4
		-- 1.3.6.1.4.1.32285.11.5.2.2.2.1.4
		topGponUniMacInfoUniIndex OBJECT-TYPE
			SYNTAX INTEGER
			MAX-ACCESS not-accessible
			STATUS current
			DESCRIPTION
				"Description."
			::= { topGponUniMacInfoEntry 4 }

		
--  1.3.6.1.4.1.32285.11.5.2.2.2.1.5
		-- 1.3.6.1.4.1.32285.11.5.2.2.2.1.5
		topGponUniMacInfoTotal OBJECT-TYPE
			SYNTAX OCTET STRING (SIZE (0..2304))
			MAX-ACCESS read-only
			STATUS current
			DESCRIPTION
				"256*9=2304byte. 6byte mac+ 1byte type + 2byte vlan."
			::= { topGponUniMacInfoEntry 5 }

		
--  1.3.6.1.4.1.32285.11.5.3
		-- 1.3.6.1.4.1.32285.11.5.3
		topGponProfileObjects OBJECT IDENTIFIER ::= { topvisionGponTree 3 }

		
		-- 1.3.6.1.4.1.32285.11.5.3.1
		topGponSrvPortNumTable OBJECT-TYPE
			SYNTAX SEQUENCE OF TopGponSrvPortNumEntry
			MAX-ACCESS not-accessible
			STATUS current
			DESCRIPTION
				"Description."
			::= { topGponProfileObjects 1 }

		
		-- 1.3.6.1.4.1.32285.11.5.3.1.1
		topGponSrvPortNumEntry OBJECT-TYPE
			SYNTAX TopGponSrvPortNumEntry
			MAX-ACCESS not-accessible
			STATUS current
			DESCRIPTION
				"Description."
			INDEX { topGponSrvPortNumProfileIndex }
			::= { topGponSrvPortNumTable 1 }

		
		TopGponSrvPortNumEntry ::=
			SEQUENCE { 
				topGponSrvPortNumProfileIndex
					INTEGER,
				topGponSrvProfilePotsNum
					INTEGER
			 }

		-- 1.3.6.1.4.1.32285.11.5.3.1.1.1
		topGponSrvPortNumProfileIndex OBJECT-TYPE
			SYNTAX INTEGER (1..1024)
			MAX-ACCESS not-accessible
			STATUS current
			DESCRIPTION
				"Description. 1 - 10 System reserved"
			::= { topGponSrvPortNumEntry 1 }

		
		-- 1.3.6.1.4.1.32285.11.5.3.1.1.2
		topGponSrvProfilePotsNum OBJECT-TYPE
			SYNTAX INTEGER (-1..2)
			MAX-ACCESS read-write
			STATUS current
			DESCRIPTION
				"Description.-1:unconcern 0:none"
			::= { topGponSrvPortNumEntry 2 }

		
		-- 1.3.6.1.4.1.32285.11.5.3.2
		topGponSrvPotsInfoTable OBJECT-TYPE
			SYNTAX SEQUENCE OF TopGponSrvPotsInfoEntry
			MAX-ACCESS not-accessible
			STATUS current
			DESCRIPTION
				"Description."
			::= { topGponProfileObjects 2 }

		
		-- 1.3.6.1.4.1.32285.11.5.3.2.1
		topGponSrvPotsInfoEntry OBJECT-TYPE
			SYNTAX TopGponSrvPotsInfoEntry
			MAX-ACCESS not-accessible
			STATUS current
			DESCRIPTION
				"Description."
			INDEX { topGponSrvPotsInfoProfIdx, topGponSrvPotsInfoPotsIdx }
			::= { topGponSrvPotsInfoTable 1 }

		
		TopGponSrvPotsInfoEntry ::=
			SEQUENCE { 
				topGponSrvPotsInfoProfIdx
					INTEGER,
				topGponSrvPotsInfoPotsIdx
					INTEGER,
				topGponSrvPotsInfoSIPAgtId
					INTEGER,
				topGponSrvPotsInfoVoipMediaId
					INTEGER,
				topGponSrvPotsInfoIpIdx
					INTEGER
			 }

		-- 1.3.6.1.4.1.32285.11.5.3.2.1.1
		topGponSrvPotsInfoProfIdx OBJECT-TYPE
			SYNTAX INTEGER (1..1024)
			MAX-ACCESS not-accessible
			STATUS current
			DESCRIPTION
				"Description. 1 - 10 System reserved"
			::= { topGponSrvPotsInfoEntry 1 }

		
		-- 1.3.6.1.4.1.32285.11.5.3.2.1.2
		topGponSrvPotsInfoPotsIdx OBJECT-TYPE
			SYNTAX INTEGER (1..2)
			MAX-ACCESS not-accessible
			STATUS current
			DESCRIPTION
				"Description."
			::= { topGponSrvPotsInfoEntry 2 }

		
		-- 1.3.6.1.4.1.32285.11.5.3.2.1.3
		topGponSrvPotsInfoSIPAgtId OBJECT-TYPE
			SYNTAX INTEGER (0..64)
			MAX-ACCESS read-write
			STATUS current
			DESCRIPTION
				"Description.0:none"
			DEFVAL { '0'b }
			::= { topGponSrvPotsInfoEntry 3 }

		
		-- 1.3.6.1.4.1.32285.11.5.3.2.1.4
		topGponSrvPotsInfoVoipMediaId OBJECT-TYPE
			SYNTAX INTEGER (0..64)
			MAX-ACCESS read-write
			STATUS current
			DESCRIPTION
				"Description.0:none"
			DEFVAL { '0'b }
			::= { topGponSrvPotsInfoEntry 4 }

		
		-- 1.3.6.1.4.1.32285.11.5.3.2.1.5
		topGponSrvPotsInfoIpIdx OBJECT-TYPE
			SYNTAX INTEGER (0..64)
			MAX-ACCESS read-write
			STATUS current
			DESCRIPTION
				"Description.0:none"
			DEFVAL { '0'b }
			::= { topGponSrvPotsInfoEntry 5 }

		
	
	END

--
-- SUMA-GPON-MIB.mib
--
