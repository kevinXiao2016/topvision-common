--*******************************************************************
--TOPVISION-CCMTS-MIB.my: DOCSIS Extention MIB file
--
--added at November 2011, Dosion Huang
--
--Topvision      
--
--modified at Dec. 2015
--modify Dhcp object at Apr. 6 2012
--
--*******************************************************************

TOPVISION-CCMTS-MIB DEFINITIONS ::= BEGIN 

IMPORTS                  
	MODULE-IDENTITY,
	IpAddress,           
	OBJECT-TYPE,  
	Unsigned32,
	Integer32,
	TimeTicks,
	Counter64
		FROM SNMPv2-SMI
	TEXTUAL-CONVENTION,
	MacAddress,
	RowStatus,
	DisplayString,
	TruthValue,
	TimeStamp
		FROM SNMPv2-TC  
	TenthdBmV,
	TenthdB,
	docsIfCmtsCmStatusIndex,
	docsIfUpChannelId,
	docsIfDownChannelId
		FROM DOCS-IF-MIB
	docsLoadBalGrpId
    	FROM DOCS-LOADBALANCING-MIB  
	InterfaceIndex
		FROM IF-MIB
    ChannelList
        FROM DOCS-IF3-MIB
        
	OBJECT-GROUP,
	MODULE-COMPLIANCE
		FROM SNMPv2-CONF
	SnmpAdminString
		FROM SNMP-FRAMEWORK-MIB
	ifIndex
		FROM IF-MIB
	docsQosIfDirection
		FROM DOCS-QOS-MIB	
	sumaRoot,
	topvisionRoot,
	topvisionHFCCcmtsTree
		FROM SUMA-EPONEOC-EPON-MIB
	InetAddressIPv6,
	InetAddressType, 
	InetAddress
        FROM INET-ADDRESS-MIB;
		
topCcmtsMIB MODULE-IDENTITY						       --The name need to be discussed.
	LAST-UPDATED "201512020000Z"
	ORGANIZATION "Topvision"
	CONTACT-INFO 
		"	Dosion Huang
			Topvision EMS group.
			Shangdi 5th Street,Haidian,Beijing,
			China,100085
			huangdongsheng@dvt.dvt.com"
	DESCRIPTION
		"The MIB module to describe the topvision CCMTS's information.			
		This MIB was firstly added."
	::={ topvisionHFCCcmtsTree 1}					
		
--Textual conventions
DocsisVersionCcmtsLocal ::= TEXTUAL-CONVENTION
	STATUS          current
	DESCRIPTION
		"Indicates the DOCSIS Radio Frequency specification being
		referenced.
		'unknown'  indicates other
		'docsis10' indicates DOCSIS 1.0.
		'docsis11' indicates DOCSIS 1.1.
		'docsis20' indicates DOCSIS 2.0.
		'docsis30' indicates DOCSIS 3.0.
		'docsis31' indicates DOCSIS 3.1."
	REFERENCE
		"DOCSIS 3.0 MAC and Upper Layer Protocols Interface
		Specification CM-SP-MULPIv3.0-I03-070223, DOCSIS
		Version section of the Common Radio Frequency
		Interface Encodings Annex."
	SYNTAX        INTEGER {
		unknown  (0),
		docsis10 (1),
		docsis11 (2),
		docsis20 (3),
		docsis30 (4),
		docsis31 (5)
	}
--Add by hzh for toploadBalMoveInfoDynamic
ChChgInitTechMap ::= TEXTUAL-CONVENTION
    STATUS          current
    DESCRIPTION
        "This data type enumerates the allowed initialization
        techniques for Dynamic Channel Change (DCC) and Dynamic 
        Bonding Change (DBC) operations. The techniques are represented
        by the 7 most significant bits (MSB). Bits 0 through 7 map to
        initialization techniques 0 through 7.  

        Each bit position represents the internal associated technique 
        as described below:

        'reinitializeMac' Reinitialize the MAC
        'broadcastInitRanging'
          Perform Broadcast initial 
          ranging on new channel before 
          normal operation
        'unicastInitRanging'
          Perform unicast ranging on new
          channel before normal operation
        'initRanging'
          Perform either broadcast or 
          unicast ranging on new channel before
          normal operation
        'direct'
          Use the new channel(s) directly 
          without re-initializing or ranging
        'probeOFDMA'
          (OFDMA channels only) Perform probing on 
          new channel before normal operation
        'unicastInitRangingOFDMA'
          (OFDMA channels only) Perform unicast 
          initial ranging (IUC3) on new channel before normal operation
        'stationRangingOFDMA'
          (OFDMA channels only) Perform station 
          ranging (IUC4) on new channel before normal operation
         Multiple bits may be set to 1 to allow the CMTS to select the 
         most suitable technique in a proprietary manner. 
         An empty value or a value with all bits in '0' means no channel
         changes allowed"

    REFERENCE
        "DOCSIS 3.1 MAC and Uper Layer Protocol Specification, 
        CM-SP-MULPIv3.1-I09-160602, Channel Assignment During 
        Registration section."
    SYNTAX          BITS {
                        reinitializeMac(0),
                        broadcastInitRanging(1),
                        unicastInitRanging(2),
                        initRanging(3),
                        direct(4),
                        probeOFDMA(5),
                        unicastInitRangingOFDMA(6),
                        stationRangingOFDMA(7)
                    }
           
topCcmtsPropertyIdent	OBJECT IDENTIFIER ::={ topCcmtsMIB 1 }

topCcmts8800A		OBJECT IDENTIFIER ::={ topCcmtsPropertyIdent 1 } 
topCcmts8800B		OBJECT IDENTIFIER ::={ topCcmtsPropertyIdent 2 } 
topCcmts8800B-3C		OBJECT IDENTIFIER ::={ topCcmts8800B 1 } 
topCcmts8800C		OBJECT IDENTIFIER ::={ topCcmtsPropertyIdent 3 } 
topCcmts8800C-A			OBJECT IDENTIFIER ::={ topCcmts8800C 1 } 
topCcmts8800C-B			OBJECT IDENTIFIER ::={ topCcmts8800C 2 } 
topCcmts8800C-E			OBJECT IDENTIFIER ::={ topCcmts8800C 3 }
topCcmts8800C-10G		OBJECT IDENTIFIER ::={ topCcmts8800C 4 }
topCcmts8800D		OBJECT IDENTIFIER ::={ topCcmtsPropertyIdent 4 }
topCcmts8800D-E			OBJECT IDENTIFIER ::={ topCcmts8800D 1 }
topCcmts8800D-P2			OBJECT IDENTIFIER ::={ topCcmts8800D 2 }
topCcmts8800D-U2			OBJECT IDENTIFIER ::={ topCcmts8800D 3 } 
topCcmts8800S		OBJECT IDENTIFIER ::={ topCcmtsPropertyIdent 5 } 
topCcmts8800E		OBJECT IDENTIFIER ::={ topCcmtsPropertyIdent 6 } 
topCcmts8800E-1G		OBJECT IDENTIFIER ::={ topCcmts8800E 1 } 
topCcmts8800E-10G		OBJECT IDENTIFIER ::={ topCcmts8800E 2 }
topCcmts8800F		OBJECT IDENTIFIER ::={ topCcmtsPropertyIdent 7 }
topCcmts8810F		OBJECT IDENTIFIER ::={ topCcmts8800F 1 }
topCcmts8820F		OBJECT IDENTIFIER ::={ topCcmts8800F 2 }
topCcmts8820F-P1		OBJECT IDENTIFIER ::={ topCcmts8800F 3 }
topCcmts8820F-P2		OBJECT IDENTIFIER ::={ topCcmts8800F 4 }
topCcmts8820F-U1		OBJECT IDENTIFIER ::={ topCcmts8800F 5 }
topCcmts8820F-U2		OBJECT IDENTIFIER ::={ topCcmts8800F 6 }

topCcmtsMibObject	OBJECT IDENTIFIER ::={ topCcmtsMIB 2 } 
topCcmtsDocs31MibObject   OBJECT IDENTIFIER ::={ topCcmtsMIB 3 } 

topCcmtsSystemObject	OBJECT IDENTIFIER ::={ topCcmtsMibObject 1 } 

--
--topCcmtsSystemObject
--
--modified by Dosion Huang at Apr.24 2012
--Add Status and software version

topCcmtsSysTable OBJECT-TYPE
	SYNTAX		SEQUENCE OF TopCcmtsSysEntry	
	MAX-ACCESS	not-accessible
	STATUS		current
	DESCRIPTION
		""
	::={ topCcmtsSystemObject 1 }

topCcmtsSysEntry OBJECT-TYPE
	SYNTAX		TopCcmtsSysEntry
	MAX-ACCESS	not-accessible
	STATUS		current
	DESCRIPTION
		""
	INDEX { ifIndex }
	::= { topCcmtsSysTable 1 }
TopCcmtsSysEntry ::=SEQUENCE{
	topCcmtsSysDescr		DisplayString,
	topCcmtsSysObjectId		OBJECT IDENTIFIER,
	topCcmtsSysUpTime		TimeTicks,
	topCcmtsSysContact		DisplayString,
	topCcmtsSysName			DisplayString,
	topCcmtsSysLocation		DisplayString,
	topCcmtsSysService		INTEGER,
	topCcmtsSysORLastChange		TimeStamp,
	topCcmtsDocsisBaseCapability	DocsisVersionCcmtsLocal,
	topCcmtsSysRAMRatio		INTEGER,                                   
	topCcmtsSysCPURatio		INTEGER,     	
	topCcmtsSysMacAddr		MacAddress,
	topCcmtsSysFlashRatio		INTEGER,
	topCcmtsSysStatus			INTEGER,
	topCcmtsSysSwVersion		DisplayString,
	topCcmtsSysSerialNumber		DisplayString,
	topCcmtsSysCmRemoteQueryStatus INTEGER,  
	topCcmtsSysHwVersion		DisplayString,
	topCcmtsSysRunTime		    INTEGER,
	topCcmtsSysDorType		    DisplayString,
	topCcmtsSysICSVersion		DisplayString,
	topCcmtsSysIPv4		        DisplayString,
	topCcmtsSysIPv6		        DisplayString,
	topCcmtsSysCmCnt		    INTEGER,
	topCcmtsSysUpstreamScQamCnt	INTEGER,
	topCcmtsSysUpstreamOfdmaCnt	INTEGER,
	topCcmtsSysDownstreamScQamCnt	INTEGER,
	topCcmtsSysDownstreamOfdmaCnt	INTEGER,
	topCcmtsSysRunningMode		INTEGER
	}

topCcmtsSysDescr OBJECT-TYPE
	SYNTAX		DisplayString (SIZE (0..255))
	MAX-ACCESS	read-only
	STATUS		current
	DESCRIPTION
		"A textual description of the entity.  This value should include 
		the full name and version identification of the system's hardware 
		type, software operating-system, and networking software.  
		It is mandatory that this only contain printable ASCII characters."
	::={ topCcmtsSysEntry 1 }

topCcmtsSysObjectId OBJECT-TYPE 
	SYNTAX		OBJECT IDENTIFIER
	MAX-ACCESS	read-only
	STATUS		current
	DESCRIPTION
		"The vendor's authoritative identification of the network 
		management subsystem contained in the entity. 
		E type will reply 1.3.6.1.4.1.32285.11.1.1.1.6.  
		C-E type  reply 1.3.6.1.4.1.32285.11.1.1.1.3.3.
		D type will reply 1.3.6.1.4.1.32285.11.1.1.1.4.
		F type will reply 1.3.6.1.4.1.32285.11.1.1.1.7."
	::={ topCcmtsSysEntry 2}

topCcmtsSysUpTime OBJECT-TYPE 
	SYNTAX		TimeTicks
	MAX-ACCESS	read-only
	STATUS		current
	DESCRIPTION
		"The time (in hundredths of a second) since the network 
		management portion of the system was last re-initialized." 
	::={ topCcmtsSysEntry 3}

topCcmtsSysContact OBJECT-TYPE 
	SYNTAX		DisplayString (SIZE (0..255))
	MAX-ACCESS	read-write
	STATUS		current
	DESCRIPTION
		"The CCMTS's contact."
	::={ topCcmtsSysEntry 4}

topCcmtsSysName OBJECT-TYPE 
	SYNTAX		DisplayString (SIZE (0..64))
	MAX-ACCESS	read-write
	STATUS		current
	DESCRIPTION
		"The CCMTS's name."
	::={ topCcmtsSysEntry 5}

topCcmtsSysLocation OBJECT-TYPE 
	SYNTAX		DisplayString (SIZE (0..255))
	MAX-ACCESS	read-write
	STATUS		current
	DESCRIPTION
		"The CCMTS's location."
	::={ topCcmtsSysEntry 6}

topCcmtsSysService OBJECT-TYPE 
	SYNTAX		INTEGER (0..127)
	MAX-ACCESS	read-only
	STATUS		current
	DESCRIPTION
		"A value which indicates the set of services that 
		this entity primarily offers. The value is a sum."
	::={ topCcmtsSysEntry 7}

topCcmtsSysORLastChange OBJECT-TYPE 
	SYNTAX		TimeStamp
	MAX-ACCESS	read-only
	STATUS		current
	DESCRIPTION
		"The value of sysUpTime at the time of the most recent 
		change in state or value of any instance of sysORID."
	::={ topCcmtsSysEntry 8}

topCcmtsDocsisBaseCapability OBJECT-TYPE 
	SYNTAX		DocsisVersionCcmtsLocal
	---SYNTAX        INTEGER {
	---	docsis10 (1),
	---	docsis11 (2),
	---	docsis20 (3),
	---	docsis30 (4),
	---	docsis31 (5)
	---}
	MAX-ACCESS	read-only
	STATUS		current
	DESCRIPTION
		"Indication of the DOCSIS capability of the device."
	::={ topCcmtsSysEntry 9}  
	
topCcmtsSysRAMRatio OBJECT-TYPE
	SYNTAX		INTEGER(0..100)
	MAX-ACCESS	read-only
	STATUS		current
	DESCRIPTION
		"The CCMTS's RAM ratio. The range is 0-100." 
	::={ topCcmtsSysEntry 10} 
	
topCcmtsSysCPURatio OBJECT-TYPE
	SYNTAX		INTEGER(0..100)
	MAX-ACCESS	read-only
	STATUS		current
	DESCRIPTION
		"The CCMTS's CPU ratio. The range is 0-100." 
	::={ topCcmtsSysEntry 11}

topCcmtsSysMacAddr OBJECT-TYPE 
	SYNTAX		MacAddress
	MAX-ACCESS	read-only
	STATUS		current
	DESCRIPTION
		"The CCMTS's mac address."
	::={ topCcmtsSysEntry 12}

topCcmtsSysFlashRatio OBJECT-TYPE
	SYNTAX		INTEGER(0..100)
	MAX-ACCESS	read-only
	STATUS		current
	DESCRIPTION
		"The CCMTS's Flash ratio. The range is 0-100." 
	::={ topCcmtsSysEntry 13}

topCcmtsSysStatus OBJECT-TYPE
	SYNTAX		INTEGER{  
			unBind(1),
			offline(2),
			inConfig(3),
			online(4),
			configFail(5),
			waitReady(6),
			configTimeOut(7), 
			error(8), 
			resetting(9),
			dhcpcomplete(10),
			loading(11)
			}
	MAX-ACCESS	read-only
	STATUS		current
	DESCRIPTION
		"The CCMTS Status" 
	::={ topCcmtsSysEntry 14}

topCcmtsSysSwVersion OBJECT-TYPE 
	SYNTAX		DisplayString (SIZE (0..255))
	MAX-ACCESS	read-only
	STATUS		current
	DESCRIPTION
		"The CCMTS's software version."
	::={ topCcmtsSysEntry 15}   
	
topCcmtsSysSerialNumber OBJECT-TYPE 
	SYNTAX		DisplayString (SIZE (0..255))
	MAX-ACCESS	read-only
	STATUS		current
	DESCRIPTION
		"The CCMTS's serial number."
	::={ topCcmtsSysEntry 16}

 topCcmtsSysCmRemoteQueryStatus OBJECT-TYPE
	SYNTAX		INTEGER{   
			enable(1),
	            	disable(2)
				}
	MAX-ACCESS	read-write
	STATUS		current
	DESCRIPTION
		"enable(1):the remotequery effect is on at this Ccmts
		 disable(2):the remotequery effect is off at this Ccmts"
	::={ topCcmtsSysEntry 17 }
 topCcmtsSysHwVersion OBJECT-TYPE 
	SYNTAX		DisplayString (SIZE (0..255))
	MAX-ACCESS	read-only
	STATUS		current
	DESCRIPTION
		"The CCMTS's hardware version."
	::={ topCcmtsSysEntry 18}   
	
topCcmtsSysRunTime OBJECT-TYPE
	SYNTAX		INTEGER
	MAX-ACCESS	read-only
	STATUS		current
	DESCRIPTION
		"The ccmts system running time since online." 
	::={ topCcmtsSysEntry 19}
    
 topCcmtsSysDorType OBJECT-TYPE 
	SYNTAX		DisplayString (SIZE (0..31))
	MAX-ACCESS	read-only
	STATUS		current
	DESCRIPTION
		"The CCMTS's Optical Machine Type. 
		if the CCMTS has optical machine, it will return the optical machine type string,
		such as 'CFA', 'CFB', 'CFC', 'CFD', 'EF', 'FFA', 'FFB', 'EP06', 'EP09'.
		If there is no optical machine, this object returns zero-length string."
	::={ topCcmtsSysEntry 20}

 topCcmtsSysICSVersion OBJECT-TYPE 
	SYNTAX		DisplayString (SIZE (0..2))
	MAX-ACCESS	read-only
	STATUS		current
	DESCRIPTION
		"The ICS version."
	::={ topCcmtsSysEntry 21}
	
 topCcmtsSysIPv4 OBJECT-TYPE 
	SYNTAX		DisplayString (SIZE (0..2))
	MAX-ACCESS	read-only
	STATUS		current
	DESCRIPTION
		"The CMTS IPv4 address."
	::={ topCcmtsSysEntry 22}

topCcmtsSysIPv6 OBJECT-TYPE 
	SYNTAX		DisplayString (SIZE (0..2))
	MAX-ACCESS	read-only
	STATUS		current
	DESCRIPTION
		"The CMTS IPv6 address."
	::={ topCcmtsSysEntry 23}

topCcmtsSysCmCnt OBJECT-TYPE 
	SYNTAX		INTEGER (0..512)
	MAX-ACCESS	read-only
	STATUS		current
	DESCRIPTION
		"The CMTS Max cm cnt."
	::={ topCcmtsSysEntry 24}

topCcmtsSysUpstreamScQamCnt OBJECT-TYPE 
	SYNTAX		INTEGER (0..512)
	MAX-ACCESS	read-only
	STATUS		current
	DESCRIPTION
		"The CMTS ScQam upstream"
	::={ topCcmtsSysEntry 25}
	
topCcmtsSysUpstreamOfdmaCnt OBJECT-TYPE 
	SYNTAX		INTEGER (0..512)
	MAX-ACCESS	read-only
	STATUS		current
	DESCRIPTION
		"The CMTS Ofdma upstream"
	::={ topCcmtsSysEntry 26}
	
topCcmtsSysDownstreamScQamCnt OBJECT-TYPE 
	SYNTAX		INTEGER (0..512)
	MAX-ACCESS	read-only
	STATUS		current
	DESCRIPTION
		"The CMTS ScQam downstream"
	::={ topCcmtsSysEntry 27}
	
topCcmtsSysDownstreamOfdmaCnt OBJECT-TYPE 
	SYNTAX		INTEGER (0..512)
	MAX-ACCESS	read-only
	STATUS		current
	DESCRIPTION
		"The CMTS Ofdm downstream"
	::={ topCcmtsSysEntry 28}

topCcmtsSysRunningMode OBJECT-TYPE
	SYNTAX		INTEGER {
				standalone(0),
				centralized(1)
			}
	MAX-ACCESS	read-only
	STATUS		current
	DESCRIPTION
		"The running mode of system.
The enumerations are:
	0: standalone (0)
	1: centralized (1)"

	::={ topCcmtsSysEntry 29}
	
topCcmtsSysControlTable OBJECT-TYPE
	SYNTAX		SEQUENCE OF TopCcmtsSysControlEntry	
	MAX-ACCESS	not-accessible
	STATUS		current
	DESCRIPTION
		""
	::={ topCcmtsSystemObject 2 }

topCcmtsSysControlEntry OBJECT-TYPE
	SYNTAX		TopCcmtsSysControlEntry
	MAX-ACCESS	not-accessible
	STATUS		current
	DESCRIPTION
		""
	INDEX { ifIndex }
	::= { topCcmtsSysControlTable 1 }

TopCcmtsSysControlEntry ::=SEQUENCE{
	topCcmtsSysResetNow		TruthValue,
	topCcmtsSysTrapControl		BITS,
	topCcmtsSysNoMacBind	TruthValue,
	topCcmtsSysReconfig		TruthValue
}

topCcmtsSysResetNow OBJECT-TYPE 
	SYNTAX		TruthValue
	MAX-ACCESS	read-write
	STATUS		current
	DESCRIPTION
		""
	::={ topCcmtsSysControlEntry 1}

topCcmtsSysTrapControl OBJECT-TYPE 
	SYNTAX		BITS{
		cmtsInitRegReqFailTrap(0),
		cmtsInitRegRspFailTrap(1),
		cmtsInitRegAckFailTrap(2),
		cmtsDynServReqFailTrap(3),
		cmtsDynServRspFailTrap(4),
		cmtsDynServAckFailTrap(5),
		cmtsBpiInitTrap(6),
		cmtsBPKMTrap(7),
		cmtsDynamicSATrap(8),
		cmtsDCCReqFailTrap(9),
		cmtsDCCRspFailTrap(10),
		cmtsDCCAckFailTrap(11)
	}
	MAX-ACCESS	read-write
	STATUS		current
	DESCRIPTION
		""
	DEFVAL {{}}
	::={ topCcmtsSysControlEntry 2}
  
topCcmtsSysNoMacBind OBJECT-TYPE 
	SYNTAX		TruthValue
	MAX-ACCESS	read-write
	STATUS		current
	DESCRIPTION
		""
	::={ topCcmtsSysControlEntry 3}
	
topCcmtsSysReconfig OBJECT-TYPE 
	SYNTAX		TruthValue
	MAX-ACCESS	read-write
	STATUS		current
	DESCRIPTION
		""
	::={ topCcmtsSysControlEntry 4}
  
topCcmtsLocationTable OBJECT-TYPE
	SYNTAX		SEQUENCE OF TopCcmtsLocationEntry
	MAX-ACCESS	not-accessible
	STATUS		current
	DESCRIPTION
		""
	::={ topCcmtsSystemObject 3 }

topCcmtsLocationEntry OBJECT-TYPE
	SYNTAX		TopCcmtsLocationEntry
	MAX-ACCESS	not-accessible
	STATUS		current
	DESCRIPTION
		""
	INDEX { topCcmtsLocationIndex }
	::={ topCcmtsLocationTable 1 }

TopCcmtsLocationEntry ::=SEQUENCE {
	topCcmtsLocationIndex	Unsigned32,
	topCcmtsLocationSlot	INTEGER,
	topCcmtsLocationPon	    INTEGER,
	topCcmtsLocationCmcId   INTEGER
}

topCcmtsLocationIndex OBJECT-TYPE
	SYNTAX		Unsigned32
	MAX-ACCESS	read-only
	STATUS		current
	DESCRIPTION
		"The index of CCMTS."
	::={ topCcmtsLocationEntry 1 }

topCcmtsLocationSlot OBJECT-TYPE
	SYNTAX		INTEGER(1..18)
	MAX-ACCESS	read-only
	STATUS		current
	DESCRIPTION
		"The identifier of slot where the CCMTS belongs."
	::={ topCcmtsLocationEntry 2 }

topCcmtsLocationPon OBJECT-TYPE
	SYNTAX		INTEGER(1..8)
	MAX-ACCESS	read-only
	STATUS		current
	DESCRIPTION
		"The identifier of pon where the CCMTS belongs"
	::={ topCcmtsLocationEntry 3 }

topCcmtsLocationCmcId OBJECT-TYPE
	SYNTAX		INTEGER(1..128)
	MAX-ACCESS	read-only
	STATUS		current
	DESCRIPTION
		"The identifier of CCMTS"
	::={ topCcmtsLocationEntry 4 }
--------------------------------------
--
--Extends IP Object
--
--------------------------------------      
topCcmtsSystemIpObject		OBJECT IDENTIFIER ::={ topCcmtsSystemObject 4 }

topCcmtsEthIpAddr OBJECT-TYPE
	SYNTAX		IpAddress
	MAX-ACCESS	read-write
	STATUS		current
	DESCRIPTION
		"The IP address of the uplink port on the CCMTS."
	::={topCcmtsSystemIpObject 1}

topCcmtsEthIpMask OBJECT-TYPE
	SYNTAX		IpAddress
	MAX-ACCESS	read-write
	STATUS		current
	DESCRIPTION
		"The MASK of the topCcmtsExtEthIp."
	::={topCcmtsSystemIpObject 2}

topCcmtsEthGateway OBJECT-TYPE
	SYNTAX		IpAddress
	MAX-ACCESS	read-write
	STATUS		current
	DESCRIPTION
		"The Gateway of the topCcmtsExtEthIp."
	::={topCcmtsSystemIpObject 3}

topCcmtsEthVlanId OBJECT-TYPE
	SYNTAX		Integer32
	MAX-ACCESS	read-write
	STATUS		current
	DESCRIPTION
		"The ID of the CCMTS's management VLAN."
	::={topCcmtsSystemIpObject 4}

topCcmtsEthVlanIpAddr OBJECT-TYPE
	SYNTAX		IpAddress
	MAX-ACCESS	read-write
	STATUS		current
	DESCRIPTION
		"The IP address of the CCMTS's management VLAN."
	::={topCcmtsSystemIpObject 5}

topCcmtsEthVlanIpMask OBJECT-TYPE
	SYNTAX		IpAddress
	MAX-ACCESS	read-write
	STATUS		current
	DESCRIPTION
		"The Mask of the topCcmtsExtEthVlanIp."
	::={topCcmtsSystemIpObject 6}
topCcmtsEthVlanGateway OBJECT-TYPE
	SYNTAX		IpAddress
	MAX-ACCESS	read-write
	STATUS		current
	DESCRIPTION
		"The Gateway of the topCcmtsExtEthVlanIp."
	::={topCcmtsSystemIpObject 7}      
	
topCcmtsOutbandIpAddr OBJECT-TYPE
	SYNTAX		IpAddress
	MAX-ACCESS	read-write
	STATUS		current
	DESCRIPTION
		"The IP address of the CCMTS's outband."
	::={topCcmtsSystemIpObject 8}

topCcmtsOutbandIpMask OBJECT-TYPE
	SYNTAX		IpAddress
	MAX-ACCESS	read-write
	STATUS		current
	DESCRIPTION
		"The Mask of the CCMTS's outband."
	::={topCcmtsSystemIpObject 9}

topCcmtsDevOutbandIpTable OBJECT-TYPE
	SYNTAX SEQUENCE OF TopCcmtsDevOutbandIpEntry
	MAX-ACCESS not-accessible
	STATUS current
	DESCRIPTION
		"CCMTS outband ip config table."
	::={topCcmtsSystemIpObject 10}
	
topCcmtsDevOutbandIpEntry OBJECT-TYPE
	SYNTAX TopCcmtsDevOutbandIpEntry
	MAX-ACCESS not-accessible
	STATUS current
	DESCRIPTION
		" "
	INDEX {topCcmtsDevOutbandIpIndex}
	::={topCcmtsDevOutbandIpTable 1}
	
TopCcmtsDevOutbandIpEntry ::= SEQUENCE {
		topCcmtsDevOutbandIpIndex		INTEGER,
		topCcmtsDevOutbandIpAddress		IpAddress,
		topCcmtsDevOutbandIpSubnetMask	IpAddress,
		topCcmtsDevOutbandIpStatus		RowStatus
	}
	
topCcmtsDevOutbandIpIndex OBJECT-TYPE
	SYNTAX		INTEGER(1..500)
	MAX-ACCESS	not-accessible
	STATUS		current
	DESCRIPTION
		"RMD ID"
	::={topCcmtsDevOutbandIpEntry 1}
	
topCcmtsDevOutbandIpAddress OBJECT-TYPE
	SYNTAX		IpAddress
	MAX-ACCESS	read-create
	STATUS		current
	DESCRIPTION
		"The outband IP address of RMD."
	::={topCcmtsDevOutbandIpEntry 2}
	
topCcmtsDevOutbandIpSubnetMask OBJECT-TYPE
	SYNTAX		IpAddress
	MAX-ACCESS	read-create
	STATUS		current
	DESCRIPTION
		"The outband IP mask of RMD."
	::={topCcmtsDevOutbandIpEntry 3}
	
topCcmtsDevOutbandIpStatus OBJECT-TYPE
	SYNTAX		RowStatus
	MAX-ACCESS	read-create
	STATUS		current
	DESCRIPTION
		"create/delete/set"
	::={topCcmtsDevOutbandIpEntry 4}
	
------------------------------------------------
-- topCcmtsSniObject
------------------------------------------------
topCcmtsSniObject	OBJECT IDENTIFIER ::={ topCcmtsSystemObject 5 }

topCcmtsSniEthInt  OBJECT-TYPE
        SYNTAX      INTEGER {
		main(1) ,
		backup(2) ,
		autoMainPreferred(3) ,
		autoBackupPreferred(4)
		}
        MAX-ACCESS  read-write
        STATUS      current         
        DESCRIPTION
            "The object is used to set main physical interface or 
	    backup physical interface which is preferd to." 
	    DEFVAL		{3}
        ::= { topCcmtsSniObject 1 }
        
 topCcmtsSniMainInt OBJECT-TYPE
        SYNTAX      INTEGER {
		copper(1) ,
		fiber(2) ,
		autoCopperPreferred (3) ,
		autoFiberPreferred(4),
		autoAnyPreferred(5)
		}

        MAX-ACCESS  read-write
        STATUS      deprecated            
        DESCRIPTION
            "The object is used to set main physical interface's 
	    transmision mode.For example,setting 1 means the Main
	    Interface use copper to transfer its PDUs."  
	    DEFVAL		{ 5 }
        ::= { topCcmtsSniObject 2 }

topCcmtsSniBackupInt OBJECT-TYPE
        SYNTAX      INTEGER {
		copper(1) ,
		fiber(2) ,
		autoCopperPreferred (3) ,
		autoFiberPreferred(4) ,
		autoAnyPreferred(5)
		}
        MAX-ACCESS  read-write
        STATUS      deprecated       
        DESCRIPTION
            "The object is used to set backup physical interface's 
	    transmision mode.For example,setting 1 means the Main
	    Interface use copper to transfer its PDUs."   
	    DEFVAL		{ 5 }
        ::= { topCcmtsSniObject 3 }    
        
 topCcmtsSniUplinkLoopbackStatus OBJECT-TYPE
	SYNTAX	INTEGER{   
			enable(1),
			disable(2)
			}
	MAX-ACCESS	read-write
	STATUS		current
	DESCRIPTION
		"enable(1): enable downstream traffic loopback to another uplinks.
		 disable(2):disable downstream traffic loopback to another uplinks."   
   DEFVAL{ disable }
	::={ topCcmtsSniObject 4 }

topCcmtsSniTable OBJECT-TYPE
	SYNTAX		SEQUENCE OF TopCcmtsSniEntry
	MAX-ACCESS	not-accessible
	STATUS		current
	DESCRIPTION
		""
	::={ topCcmtsSniObject 5 }

topCcmtsSniEntry OBJECT-TYPE
	SYNTAX		TopCcmtsSniEntry
	MAX-ACCESS	not-accessible
	STATUS		current
	DESCRIPTION	
		""
	INDEX  { topCcmtsSniIndex }
	::={ topCcmtsSniTable 1 }
	
TopCcmtsSniEntry ::=SEQUENCE{
	topCcmtsSniIndex		INTEGER,
	topCcmtsSniInt	    	INTEGER,
	topCcmtsSniCurrentMedia	INTEGER,
	topCcmtsSniDuplexMod	INTEGER,
	topCcmtsSniClearStatistic	INTEGER, 
	topCcmtsSniDuplexSetting  INTEGER,
	topCcmtsSniSpeedSetting   INTEGER
}

topCcmtsSniIndex OBJECT-TYPE
	SYNTAX		INTEGER
	MAX-ACCESS	read-only
	STATUS		current
	DESCRIPTION
		"The index of the uplink interface"
	::={ topCcmtsSniEntry 1 }
 
 topCcmtsSniInt OBJECT-TYPE
    SYNTAX      INTEGER {
	copper(1) ,
	fiber(2) ,
	autoCopperPreferred (3) ,
	autoFiberPreferred(4),
	autoAnyPreferred(5),
	epon(6),
	gpon(8)
	}

       MAX-ACCESS  read-write
       STATUS      current            
       DESCRIPTION
           "The object is used to set physical interface's 
    transmision mode.For example,setting 1 means the Interface 
    use copper to transfer its PDUs. The writed value will work 
	after system reboot, and it will return current running 
	mode when reading this object."
    ::= { topCcmtsSniEntry 2 }
                                
 topCcmtsSniCurrentMedia OBJECT-TYPE
    SYNTAX      INTEGER {
	copper(1) ,
	fiber(2) ,
	epon(3),
	gpon(4)
	}

       MAX-ACCESS  read-only
       STATUS      current            
       DESCRIPTION
           "The object is used to display the current Media"  
    ::= { topCcmtsSniEntry 3 }  
                                             
 topCcmtsSniDuplexMod OBJECT-TYPE
    SYNTAX      INTEGER {
	full(1) ,
	half(2)
	}

       MAX-ACCESS  read-only
       STATUS      current            
       DESCRIPTION
           "The object is used to display the current DuplexMod"  
    ::= { topCcmtsSniEntry 4 }   
                  
 topCcmtsSniClearStatistic OBJECT-TYPE
    SYNTAX      INTEGER {
	true(1) ,
	false(2)
	}

       MAX-ACCESS  read-write
       STATUS      current            
       DESCRIPTION
           "The object is used to clear UpLink Statistic"  
    ::= { topCcmtsSniEntry 5 }
    
 topCcmtsSniDuplexSetting OBJECT-TYPE
    SYNTAX      INTEGER {
	auto(1) ,
	full(2) ,
	half(3)
	}

       MAX-ACCESS  read-write
       STATUS      current            
       DESCRIPTION
		"The object is used to show and set duplex config.
		only support set when topCcmtsSniInt is copper or fiber"  
    ::= { topCcmtsSniEntry 6 }
 topCcmtsSniSpeedSetting OBJECT-TYPE
    SYNTAX      INTEGER {
	speedAuto(1) ,
	speed10Mbps(2) ,
	speed100Mbps(3) ,
	speed1000Mbps(4)
	}

       MAX-ACCESS  read-write
       STATUS      current            
       DESCRIPTION
		"The object is used to show and set speed config
		only support set when topCcmtsSniInt is copper or fiber
		and only support set speedAuto(1) or speed1000Mbps(4) 
		when topCcmtsSniInt is fiber"  
    ::= { topCcmtsSniEntry 7 } 
    
topCcmtsSniStatisticsTable OBJECT-TYPE
	SYNTAX		SEQUENCE OF TopCcmtsSniStatisticsEntry
	MAX-ACCESS	not-accessible
	STATUS		current
	DESCRIPTION
		""
	::={ topCcmtsSniObject 6 }  

topCcmtsSniStatisticsEntry OBJECT-TYPE
	SYNTAX		TopCcmtsSniStatisticsEntry
	MAX-ACCESS	not-accessible
	STATUS		current
	DESCRIPTION	
		""
	INDEX  { ifIndex }
	::={ topCcmtsSniStatisticsTable 1 }

TopCcmtsSniStatisticsEntry ::=SEQUENCE{
	topCcmtsSniTxCurrentSpeed	INTEGER,
	topCcmtsSniRxCurrentSpeed	INTEGER,
	topCcmtsSniTxHistoryMaxSpeed	INTEGER,
	topCcmtsSniRxHistoryMaxSpeed	INTEGER
}

topCcmtsSniTxCurrentSpeed OBJECT-TYPE
	SYNTAX		INTEGER
	UNITS "Kbps"
	MAX-ACCESS	read-only
	STATUS		current
	DESCRIPTION
		"Current send speed of the port"  
	::= { topCcmtsSniStatisticsEntry 1 } 
topCcmtsSniRxCurrentSpeed OBJECT-TYPE
	SYNTAX		INTEGER
	UNITS "Kbps"
	MAX-ACCESS	read-only
	STATUS		current
	DESCRIPTION
		"Current receive speed of the port"
	::= { topCcmtsSniStatisticsEntry 2 } 
topCcmtsSniTxHistoryMaxSpeed OBJECT-TYPE
	SYNTAX		INTEGER 
	UNITS "Kbps"
	MAX-ACCESS	read-only
	STATUS		current
	DESCRIPTION
		"Max send speed that the port reached"
	::= { topCcmtsSniStatisticsEntry 3 } 
topCcmtsSniRxHistoryMaxSpeed OBJECT-TYPE
	SYNTAX		INTEGER 
	UNITS "Kbps"
	MAX-ACCESS	read-only
	STATUS		current
	DESCRIPTION
		"Max receive speed that the port reached"
	::= { topCcmtsSniStatisticsEntry 4 } 

topCcmtsSniUtilThresholdObject	OBJECT IDENTIFIER ::={ topCcmtsSniObject 7 }

topCcmtsSniTxUtilMinorAlarmThreshold  OBJECT-TYPE
	SYNTAX	INTEGER(0..100)
	UNITS "Pencent(%)"
	MAX-ACCESS	read-write
	STATUS		current
	DESCRIPTION
		"The threshold for uplink send utilization to trigger minor alarm." 
	DEFVAL		{0}
	::= { topCcmtsSniUtilThresholdObject 1 }
topCcmtsSniTxUtilMinorRecoveryThreshold  OBJECT-TYPE
	SYNTAX	INTEGER(0..100)
	UNITS "Pencent(%)"
	MAX-ACCESS	read-write
	STATUS		current
	DESCRIPTION
		"The threshold for uplink send utilization to trigger minor recovery alarm." 
	DEFVAL		{0}
	::= { topCcmtsSniUtilThresholdObject 2 }
topCcmtsSniTxUtilMajorAlarmThreshold  OBJECT-TYPE
	SYNTAX		INTEGER(0..100)
	UNITS "Pencent(%)"
	MAX-ACCESS	read-write
	STATUS		current
	DESCRIPTION
		"The threshold for uplink send utilization to trigger major alarm." 
	DEFVAL		{70}
	::= { topCcmtsSniUtilThresholdObject 3 }
topCcmtsSniTxUtilMajorRecoveryThreshold  OBJECT-TYPE
	SYNTAX		INTEGER(0..100)
	UNITS "Pencent(%)"
	MAX-ACCESS	read-write
	STATUS		current
	DESCRIPTION
		"The threshold for uplink send utilization to trigger major recovery alarm." 
	DEFVAL		{65}
	::= { topCcmtsSniUtilThresholdObject 4 }
topCcmtsSniTxUtilCriticalAlarmThreshold  OBJECT-TYPE
	SYNTAX		INTEGER(0..100)
	UNITS "Pencent(%)"
	MAX-ACCESS	read-write
	STATUS		current
	DESCRIPTION
		"The threshold for uplink send utilization to trigger critical alarm." 
	DEFVAL		{90}
	::= { topCcmtsSniUtilThresholdObject 5 }
topCcmtsSniTxUtilCriticalRecoveryThreshold  OBJECT-TYPE
	SYNTAX		INTEGER(0..100)
	UNITS "Pencent(%)"
	MAX-ACCESS	read-write
	STATUS		current
	DESCRIPTION
		"The threshold for uplink send utilization to trigger major alarm." 
	DEFVAL		{85}
	::= { topCcmtsSniUtilThresholdObject 6 }
topCcmtsSniRxUtilMinorAlarmThreshold  OBJECT-TYPE
	SYNTAX	INTEGER(0..100)
	UNITS "Pencent(%)"
	MAX-ACCESS	read-write
	STATUS		current
	DESCRIPTION
		"The threshold for uplink receive utilization to trigger minor alarm." 
	DEFVAL		{0}
	::= { topCcmtsSniUtilThresholdObject 7 }
topCcmtsSniRxUtilMinorRecoveryThreshold  OBJECT-TYPE
	SYNTAX	INTEGER(0..100)
	UNITS "Pencent(%)"
	MAX-ACCESS	read-write
	STATUS		current
	DESCRIPTION
		"The threshold for uplink receive utilization to trigger minor recovery alarm." 
	DEFVAL		{0}
	::= { topCcmtsSniUtilThresholdObject 8 }
topCcmtsSniRxUtilMajorAlarmThreshold  OBJECT-TYPE
	SYNTAX		INTEGER(0..100)
	UNITS "Pencent(%)"
	MAX-ACCESS	read-write
	STATUS		current
	DESCRIPTION
		"The threshold for uplink receive utilization to trigger major alarm." 
	DEFVAL		{70}
	::= { topCcmtsSniUtilThresholdObject 9 }
topCcmtsSniRxUtilMajorRecoveryThreshold  OBJECT-TYPE
	SYNTAX		INTEGER(0..100)
	UNITS "Pencent(%)"
	MAX-ACCESS	read-write
	STATUS		current
	DESCRIPTION
		"The threshold for uplink receive utilization to trigger major recovery alarm." 
	DEFVAL		{65}
	::= { topCcmtsSniUtilThresholdObject 10 }
topCcmtsSniRxUtilCriticalAlarmThreshold  OBJECT-TYPE
	SYNTAX		INTEGER(0..100)
	UNITS "Pencent(%)"
	MAX-ACCESS	read-write
	STATUS		current
	DESCRIPTION
		"The threshold for uplink receive utilization to trigger critical alarm." 
	DEFVAL		{90}
	::= { topCcmtsSniUtilThresholdObject 11 }
topCcmtsSniRxUtilCriticalRecoveryThreshold  OBJECT-TYPE
	SYNTAX		INTEGER(0..100)
	UNITS "Pencent(%)"
	MAX-ACCESS	read-write
	STATUS		current
	DESCRIPTION
		"The threshold for uplink receive utilization to trigger major alarm." 
	DEFVAL		{85}
	::= { topCcmtsSniUtilThresholdObject 12 }

topCcmtsSniUplinkForwardVlan OBJECT-TYPE
	SYNTAX  INTEGER(0..4096)
	MAX-ACCESS      read-write
	STATUS          current
	DESCRIPTION
		"enable(1-4096): enable traffic the specific vlan id forward to eth untag.
		disable(0):disable vlan forward."
	DEFVAL              {0}
	::={ topCcmtsSniObject 8 }

--------------------------------------------------------------------
--topCcmtsDevObject
--added at 2012-9-3
--------------------------------------------------------------------
topCcmtsDevObject	OBJECT IDENTIFIER ::={ topCcmtsSystemObject 6 }  

topCcmtsDevSaveConfig OBJECT-TYPE
	SYNTAX		TruthValue
	MAX-ACCESS	read-write
	STATUS		current
	DESCRIPTION
		"This object is used to save config information.When set
		to true(1),save config information. And false(2), 
		as clear config information. When read, this object
		always return false(3)."
	::={ topCcmtsDevObject 1 }    
	
topCcmtsDevSaveConfigStatus OBJECT-TYPE
	SYNTAX		INTEGER{
					saving(1),
					savedSuccess(2), 
					savedFailed(3)
					
				}
	MAX-ACCESS	read-only
	STATUS		current
	DESCRIPTION
		"This object is used to show save result."
	::={ topCcmtsDevObject 2 }


--------------------------------------------------------------------
--topCcmtsLoginObject
--added at 2016-1-29
--------------------------------------------------------------------
topCcmtsLoginObject	OBJECT IDENTIFIER ::={ topCcmtsSystemObject 26 }  

topCcmtsLoginTryNum OBJECT-TYPE
	SYNTAX		INTEGER (1..20)
	MAX-ACCESS	read-write
	STATUS		current
	DESCRIPTION
		"When the CLI login,of the same user fails for try-num times in a row, 
		this account must be locked for lock-time."
	::={ topCcmtsLoginObject 1 }    
	
topCcmtsLoginFailLockTime OBJECT-TYPE
	SYNTAX		INTEGER (5..60)
	MAX-ACCESS	read-write
	STATUS		current
	DESCRIPTION
		"When the CLI login,of the same user fails for try-num times in a row, 
		this account must be locked for lock-time."
	::={ topCcmtsLoginObject 2 }

topCcmtsLoginFailLockExtTime OBJECT-TYPE
	SYNTAX		INTEGER (5..60)
	MAX-ACCESS	read-write
	STATUS		current
	DESCRIPTION
		"When the CLI login,of the same user fails for try-num times in a row,
		with each try-num consecutive fails,always extend-time time is added to the lock timer."
	::={ topCcmtsLoginObject 3 }	
--------------------------------------------------------------------
--topCcmtsQuickReplaceTable
--date 2013-03-08
--by Tang Bo
--------------------------------------------------------------------
topCcmtsQuickReplaceTable OBJECT-TYPE
	SYNTAX		SEQUENCE OF TopCcmtsQuickReplaceEntry
	MAX-ACCESS	not-accessible
	STATUS		current
	DESCRIPTION
		"Use a new Ccmts to replace current Ccmts.
		Copy current Ccmts's configuration to the new Ccmts"
	::={ topCcmtsSystemObject 7 }

topCcmtsQuickReplaceEntry OBJECT-TYPE
	SYNTAX		TopCcmtsQuickReplaceEntry
	MAX-ACCESS	not-accessible
	STATUS		current
	DESCRIPTION	
		"Use a new Ccmts to replace current Ccmts.
		Copy current Ccmts's configuration to the new Ccmts"
	INDEX  { ifIndex }
	::={ topCcmtsQuickReplaceTable 1 }
	
TopCcmtsQuickReplaceEntry ::=SEQUENCE{
	topNewCcmtsMacAddr	 MacAddress
}

topNewCcmtsMacAddr OBJECT-TYPE
	SYNTAX		MacAddress
	MAX-ACCESS	read-write
	STATUS		current
	DESCRIPTION
		"The Mac Address of the new Ccmts which is used to replace current Ccmts"
	::={ topCcmtsQuickReplaceEntry 1 }
	
--------------------------------------------------------------------
--topCcmtsUpChannelExtTable
--date 2013-04-15
--by WangPeiYao
--------------------------------------------------------------------
topCcmtsUpChannelExtTable OBJECT-TYPE
	SYNTAX		SEQUENCE OF TopCcmtsUpChannelExtEntry
	MAX-ACCESS	not-accessible
	STATUS		current
	DESCRIPTION
		"The ExtTable of docsIfUpstreamChannelTable"
	::={ topCcmtsSystemObject 8 }

topCcmtsUpChannelExtEntry OBJECT-TYPE
	SYNTAX		TopCcmtsUpChannelExtEntry
	MAX-ACCESS	not-accessible
	STATUS		current
	DESCRIPTION	
		"Refer to docsIfUpstreamChannelTable"
	INDEX  { ifIndex }
	::={ topCcmtsUpChannelExtTable 1 }
	
TopCcmtsUpChannelExtEntry ::=SEQUENCE{
	topCcmtsUpStreamChannelExtType	 INTEGER
}

topCcmtsUpStreamChannelExtType OBJECT-TYPE  
    SYNTAX      INTEGER {
		v2(2) ,
		v3(3) 
		}
	MAX-ACCESS	read-create
	STATUS		current
	DESCRIPTION
		"The upstream channel type ,including V2(2),V3(3)."
	::={ topCcmtsUpChannelExtEntry 1 }
	

    
------------------------------------------------
-- topCcmtsRateLimitObject
------------------------------------------------
topCcmtsRateLimitObject	OBJECT IDENTIFIER ::={ topCcmtsSystemObject 9 }

topCcmtsRateLimitCpuPortEgressArp OBJECT-TYPE
    SYNTAX INTEGER
    MAX-ACCESS read-write
    STATUS current
    DESCRIPTION
		"cpu port arp rate-limit(pps) with configurable value varies depending on device type."
    ::= { topCcmtsRateLimitObject 1 }
                               
topCcmtsRateLimitCpuPortEgressUni OBJECT-TYPE
    SYNTAX INTEGER
    MAX-ACCESS read-write
    STATUS current
    DESCRIPTION
		"cpu port Unicast rate-limit(pps) with configurable value varies depending on device type."
    ::= { topCcmtsRateLimitObject 2 }  
    
topCcmtsRateLimitCpuPortEgressUdp OBJECT-TYPE
    SYNTAX INTEGER
    MAX-ACCESS read-write
    STATUS current
    DESCRIPTION
		"cpu port Udp(exclude port=161) rate-limit(pps) with configurable value varies depending on device type."
    ::= { topCcmtsRateLimitObject 3 }
                               
topCcmtsRateLimitCpuPortEgressDhcp OBJECT-TYPE
    SYNTAX INTEGER
    MAX-ACCESS read-write
    STATUS current
    DESCRIPTION
		"cpu port dhcp rate-limit(pps) with configurable value varies depending on device type."
    ::= { topCcmtsRateLimitObject 4 }

topCcmtsRateLimitUplinkEgressIcmp OBJECT-TYPE
    SYNTAX INTEGER
    MAX-ACCESS read-write
    STATUS current
    DESCRIPTION
		"uplink egress icmp rate-limit(pps) with configurable value varies depending on device type."
    ::= { topCcmtsRateLimitObject 5 }

topCcmtsRateLimitUplinkEgressIgmp OBJECT-TYPE
    SYNTAX INTEGER
    MAX-ACCESS read-write
    STATUS current
    DESCRIPTION
		"uplink egress igmp rate-limit(pps) with configurable value varies depending on device type."
    ::= { topCcmtsRateLimitObject 6 }        

topCcmtsRateLimitUplinkIngressBroadcast OBJECT-TYPE
    SYNTAX INTEGER
    MAX-ACCESS read-write
    STATUS current
    DESCRIPTION
		"uplink ingress broadcast rate-limit(pps) with configurable value varies depending on device type."
    ::= { topCcmtsRateLimitObject 7 }

topCcmtsRateLimitUplinkIngressMulticast OBJECT-TYPE
    SYNTAX INTEGER
    MAX-ACCESS read-write
    STATUS current
    DESCRIPTION
		"uplink ingress multicast rate-limit(pps) with configurable value varies depending on device type."
    ::= { topCcmtsRateLimitObject 8 } 

topCcmtsRateLimitCableIngressBroadcast OBJECT-TYPE
    SYNTAX INTEGER
    MAX-ACCESS read-write
    STATUS current
    DESCRIPTION
		"cable ingress broadcast rate-limit(pps) with configurable value varies depending on device type."
    ::= { topCcmtsRateLimitObject 9 }

topCcmtsRateLimitCableIngressMulticast OBJECT-TYPE
    SYNTAX INTEGER
    MAX-ACCESS read-write
    STATUS current
    DESCRIPTION
		"cable ingress multicast rate-limit(pps) with configurable value varies depending on device type."
    ::= { topCcmtsRateLimitObject 10 }
    
topCcmtsRateLimitCableIngressArp OBJECT-TYPE
	SYNTAX INTEGER 
	MAX-ACCESS read-write
    STATUS current
    DESCRIPTION
        "cm based cable ingress arp rate-limit(pps) with configurable value varies depending on device type."   
    ::= { topCcmtsRateLimitObject 11 }
 
topCcmtsRateLimitCableIngressDhcp OBJECT-TYPE
	SYNTAX INTEGER 
	MAX-ACCESS read-write
    STATUS current
    DESCRIPTION
        "cm based cable ingress dhcp rate-limit(pps) with configurable value varies depending on device type."   
    ::= { topCcmtsRateLimitObject 12 }

------------------------------------------------
--topCcmtsDevRateLimitTable
------------------------------------------------	
topCcmtsDevRateLimitTable OBJECT-TYPE
	SYNTAX		SEQUENCE OF TopCcmtsDevRateLimitEntry	
	MAX-ACCESS	not-accessible
	STATUS		current
	DESCRIPTION
		""
	::={ topCcmtsRateLimitObject 13 }

topCcmtsDevRateLimitEntry OBJECT-TYPE
	SYNTAX		TopCcmtsDevRateLimitEntry
	MAX-ACCESS	not-accessible
	STATUS		current
	DESCRIPTION
		""
	INDEX { ifIndex }
	::= { topCcmtsDevRateLimitTable 1 }
TopCcmtsDevRateLimitEntry ::=SEQUENCE{   
         topCcmtsDevRateLimitCpuPortIngressArp			INTEGER,
         topCcmtsDevRateLimitCpuPortIngressUni			INTEGER,
         topCcmtsDevRateLimitCpuPortIngressUdp			INTEGER,
         topCcmtsDevRateLimitCpuPortIngressDhcp			INTEGER,
         topCcmtsDevRateLimitUplinkIngressIcmp			INTEGER,
         topCcmtsDevRateLimitUplinkIngressIgmp			INTEGER,
         topCcmtsDevRateLimitUplinkIngressBroadcast		INTEGER, 
         topCcmtsDevRateLimitUplinkIngressMulticast		INTEGER,
         topCcmtsDevRateLimitCableIngressBroadcast		INTEGER,
         topCcmtsDevRateLimitCableIngressMulticast		INTEGER,
         topCcmtsDevRateLimitCableIngressArp			INTEGER,  
         topCcmtsDevRateLimitCableIngressDhcp    		INTEGER,
		 topCcmtsDevRateLimitCpuPortIngressDhcpv6		INTEGER,
		 topCcmtsDevRateLimitUplinkIngressIcmpv6		INTEGER,
		 topCcmtsDevRateLimitUplinkIngressMld			INTEGER,
		 topCcmtsDevRateLimitCableIngressIgmpMld		INTEGER,
		 topCcmtsDevRateLimitCableIngressIcmpv6			INTEGER,  
         topCcmtsDevRateLimitCableIngressDhcpv6    		INTEGER
	}
    
topCcmtsDevRateLimitCpuPortIngressArp OBJECT-TYPE
    SYNTAX INTEGER
    MAX-ACCESS read-write
    STATUS current
    DESCRIPTION
		"cpu port arp rate-limit(pps) with configurable value varies depending on device type."
    ::= { topCcmtsDevRateLimitEntry 1 }
                               
topCcmtsDevRateLimitCpuPortIngressUni OBJECT-TYPE
    SYNTAX INTEGER
    MAX-ACCESS read-write
    STATUS current
    DESCRIPTION
		"cpu port Unicast rate-limit(pps) with configurable value varies depending on device type."
    ::= { topCcmtsDevRateLimitEntry 2 }  
    
topCcmtsDevRateLimitCpuPortIngressUdp OBJECT-TYPE
    SYNTAX INTEGER
    MAX-ACCESS read-write
    STATUS current
    DESCRIPTION
		"cpu port Udp(exclude port=161) rate-limit(pps) with configurable value varies depending on device type."
    ::= { topCcmtsDevRateLimitEntry 3 }
                               
topCcmtsDevRateLimitCpuPortIngressDhcp OBJECT-TYPE
    SYNTAX INTEGER
    MAX-ACCESS read-write
    STATUS current
    DESCRIPTION
		"cpu port dhcp rate-limit(pps) with configurable value varies depending on device type."
    ::= { topCcmtsDevRateLimitEntry 4 }

topCcmtsDevRateLimitUplinkIngressIcmp OBJECT-TYPE
    SYNTAX INTEGER
    MAX-ACCESS read-write
    STATUS current
    DESCRIPTION
		"uplink ingress icmp rate-limit(pps) with configurable value varies depending on device type."
    ::= { topCcmtsDevRateLimitEntry 5 }

topCcmtsDevRateLimitUplinkIngressIgmp OBJECT-TYPE
    SYNTAX INTEGER
    MAX-ACCESS read-write
    STATUS current
    DESCRIPTION
		"uplink ingress igmp rate-limit(pps) with configurable value varies depending on device type."
    ::= { topCcmtsDevRateLimitEntry 6 }        

topCcmtsDevRateLimitUplinkIngressBroadcast OBJECT-TYPE
    SYNTAX INTEGER
    MAX-ACCESS read-write
    STATUS current
    DESCRIPTION
		"uplink ingress broadcast rate-limit(pps) with configurable value varies depending on device type."
    ::= { topCcmtsDevRateLimitEntry 7 }

topCcmtsDevRateLimitUplinkIngressMulticast OBJECT-TYPE
    SYNTAX INTEGER
    MAX-ACCESS read-write
    STATUS current
    DESCRIPTION
		"uplink ingress multicast rate-limit(pps) with configurable value varies depending on device type."
    ::= { topCcmtsDevRateLimitEntry 8 } 

topCcmtsDevRateLimitCableIngressBroadcast OBJECT-TYPE
    SYNTAX INTEGER
    MAX-ACCESS read-write
    STATUS current
    DESCRIPTION
		"cable ingress broadcast rate-limit(pps) with configurable value varies depending on device type."
    ::= { topCcmtsDevRateLimitEntry 9 }

topCcmtsDevRateLimitCableIngressMulticast OBJECT-TYPE
    SYNTAX INTEGER
    MAX-ACCESS read-write
    STATUS current
    DESCRIPTION
		"cable ingress multicast rate-limit(pps) with configurable value varies depending on device type."
    ::= { topCcmtsDevRateLimitEntry 10 }
    
topCcmtsDevRateLimitCableIngressArp OBJECT-TYPE
	SYNTAX INTEGER 
	MAX-ACCESS read-write
    STATUS current
    DESCRIPTION
        "cm based cable ingress arp rate-limit(pps) with configurable value varies depending on device type."   
    ::= { topCcmtsDevRateLimitEntry 11 }
 
topCcmtsDevRateLimitCableIngressDhcp OBJECT-TYPE
	SYNTAX INTEGER 
	MAX-ACCESS read-write
    STATUS current
    DESCRIPTION
        "cm based cable ingress dhcp rate-limit(pps) with configurable value varies depending on device type."   
    ::= { topCcmtsDevRateLimitEntry 12 }

topCcmtsDevRateLimitCpuPortIngressDhcpv6 OBJECT-TYPE
    SYNTAX INTEGER
    MAX-ACCESS read-write
    STATUS current
    DESCRIPTION
		"cpu port dhcpv6 rate-limit(pps) with configurable value varies depending on device type."
    ::= { topCcmtsDevRateLimitEntry 13 }
	
topCcmtsDevRateLimitUplinkIngressIcmpv6 OBJECT-TYPE
    SYNTAX INTEGER
    MAX-ACCESS read-write
    STATUS current
    DESCRIPTION
		"uplink ingress icmpv6 rate-limit(pps) with configurable value varies depending on device type."
    ::= { topCcmtsDevRateLimitEntry 14 }

topCcmtsDevRateLimitUplinkIngressMld OBJECT-TYPE
    SYNTAX INTEGER
    MAX-ACCESS read-write
    STATUS current
    DESCRIPTION
		"uplink ingress mld rate-limit(pps) with configurable value varies depending on device type."
    ::= { topCcmtsDevRateLimitEntry 15 }
	
topCcmtsDevRateLimitCableIngressIgmpMld OBJECT-TYPE
    SYNTAX INTEGER
    MAX-ACCESS read-write
    STATUS current
    DESCRIPTION
		"cable ingress igmp and mld rate-limit(pps) with configurable value varies depending on device type."
    ::= { topCcmtsDevRateLimitEntry 16 }
	
topCcmtsDevRateLimitCableIngressIcmpv6 OBJECT-TYPE
	SYNTAX INTEGER 
	MAX-ACCESS read-write
    STATUS current
    DESCRIPTION
        "cm based cable ingress ICMPv6 rate-limit(pps) with configurable value varies depending on device type."   
    ::= { topCcmtsDevRateLimitEntry 17 }
 
topCcmtsDevRateLimitCableIngressDhcpv6 OBJECT-TYPE
	SYNTAX INTEGER 
	MAX-ACCESS read-write
    STATUS current
    DESCRIPTION
        "cm based cable ingress DHCPv6 rate-limit(pps) with configurable value varies depending on device type."   
    ::= { topCcmtsDevRateLimitEntry 18 }
	
------------------------------------------------
--topCcmtsDevRateLimitObject
------------------------------------------------	
topCcmtsDevRateLimitObject	OBJECT IDENTIFIER ::={ topCcmtsRateLimitObject 14 }

topCcmtsRateLimitCpuPortIngressArp OBJECT-TYPE
    SYNTAX INTEGER
    MAX-ACCESS read-write
    STATUS current
    DESCRIPTION
		"cpu port arp rate-limit(pps) with configurable value varies depending on device type."
    ::= { topCcmtsDevRateLimitObject 1 }
                               
topCcmtsRateLimitCpuPortIngressUni OBJECT-TYPE
    SYNTAX INTEGER
    MAX-ACCESS read-write
    STATUS current
    DESCRIPTION
		"cpu port Unicast rate-limit(pps) with configurable value varies depending on device type."
    ::= { topCcmtsDevRateLimitObject 2 }  
    
topCcmtsRateLimitCableIngressIgmpMld OBJECT-TYPE
    SYNTAX INTEGER
    MAX-ACCESS read-write
    STATUS current
    DESCRIPTION
		"cable ingress igmp and mld rate-limit(pps) with configurable value varies depending on device type."
    ::= { topCcmtsDevRateLimitObject 3 }
                               
topCcmtsRateLimitCpuPortIngressDhcp OBJECT-TYPE
    SYNTAX INTEGER
    MAX-ACCESS read-write
    STATUS current
    DESCRIPTION
		"cpu port dhcp rate-limit(pps) with configurable value varies depending on device type."
    ::= { topCcmtsDevRateLimitObject 4 }

topCcmtsRateLimitUplinkIngressIcmp OBJECT-TYPE
    SYNTAX INTEGER
    MAX-ACCESS read-write
    STATUS current
    DESCRIPTION
		"uplink ingress icmp rate-limit(pps) with configurable value varies depending on device type."
    ::= { topCcmtsDevRateLimitObject 5 }

topCcmtsRateLimitUplinkIngressIgmp OBJECT-TYPE
    SYNTAX INTEGER
    MAX-ACCESS read-write
    STATUS current
    DESCRIPTION
		"uplink ingress igmp rate-limit(pps) with configurable value varies depending on device type."
    ::= { topCcmtsDevRateLimitObject 6 }  
	
topCcmtsRateLimitCpuPortIngressDhcpv6 OBJECT-TYPE
    SYNTAX INTEGER
    MAX-ACCESS read-write
    STATUS current
    DESCRIPTION
		"cpu port dhcpv6 rate-limit(pps) with configurable value varies depending on device type."
    ::= { topCcmtsDevRateLimitObject 7 }

topCcmtsRateLimitUplinkIngressIcmpv6 OBJECT-TYPE
    SYNTAX INTEGER
    MAX-ACCESS read-write
    STATUS current
    DESCRIPTION
		"uplink ingress icmpv6 rate-limit(pps) with configurable value varies depending on device type."
    ::= { topCcmtsDevRateLimitObject 8 }

topCcmtsRateLimitUplinkIngressMld OBJECT-TYPE
    SYNTAX INTEGER
    MAX-ACCESS read-write
    STATUS current
    DESCRIPTION
		"uplink ingress mld rate-limit(pps) with configurable value varies depending on device type."
    ::= { topCcmtsDevRateLimitObject 9 }  
	
topCcmtsRateLimitCableIngressIcmpv6 OBJECT-TYPE
    SYNTAX INTEGER
    MAX-ACCESS read-write
    STATUS current
    DESCRIPTION
        "cm based cable ingress ICMPv6 rate-limit(pps) with configurable value varies depending on device type."   
    ::= { topCcmtsDevRateLimitObject 10 }
 
topCcmtsRateLimitCableIngressDhcpv6 OBJECT-TYPE
    SYNTAX INTEGER
    MAX-ACCESS read-write
    STATUS current
    DESCRIPTION
        "cm based cable ingress DHCPv6 rate-limit(pps) with configurable value varies depending on device type."   
    ::= { topCcmtsDevRateLimitObject 11 }
	
------------------------------------------------
--topCcmtsEquipmentTemperature
------------------------------------------------   
topCcmtsEquipmentTemperatureTable OBJECT-TYPE
	SYNTAX		SEQUENCE OF TopCcmtsEquipmentTemperatureEntry	
	MAX-ACCESS	not-accessible
	STATUS		current
	DESCRIPTION
		""
	::={ topCcmtsSystemObject 10 }

topCcmtsEquipmentTemperatureEntry OBJECT-TYPE
	SYNTAX		TopCcmtsEquipmentTemperatureEntry
	MAX-ACCESS	not-accessible
	STATUS		current
	DESCRIPTION
		""
	INDEX { ifIndex }
	::= { topCcmtsEquipmentTemperatureTable 1 }
TopCcmtsEquipmentTemperatureEntry ::=SEQUENCE{   
         topCcmtsDDRTemperature    Integer32,
         topCcmtsRFTemperature	Integer32,
         topCcmtsUSTemperature	Integer32,
         topCcmtsBRCM3218Temperature	Integer32,
         topCcmtsSupply1TjTemperature	Integer32,
         topCcmtsSupply2TjTemperature	Integer32,
         topCcmtsSupply3TjTemperature	Integer32
	}
    	
topCcmtsDDRTemperature OBJECT-TYPE
    SYNTAX Integer32
    UNITS "degC"
    MAX-ACCESS read-only
    STATUS current
    DESCRIPTION
		"3218 externally DDR temperature"
    ::= { topCcmtsEquipmentTemperatureEntry 1 }

topCcmtsRFTemperature OBJECT-TYPE
    SYNTAX Integer32     
    UNITS "degC"
    MAX-ACCESS read-only
    STATUS current
    DESCRIPTION
		"The RF downstream zoom chip temperature"
    ::= { topCcmtsEquipmentTemperatureEntry 2 }

topCcmtsUSTemperature OBJECT-TYPE
    SYNTAX Integer32
    UNITS "degC"
    MAX-ACCESS read-only
    STATUS current
    DESCRIPTION
		"The RF downstream zoom chip temperature"
    ::= { topCcmtsEquipmentTemperatureEntry 3 }

topCcmtsBRCM3218Temperature OBJECT-TYPE
    SYNTAX Integer32
    UNITS "degC"
    MAX-ACCESS read-only
    STATUS current
    DESCRIPTION
		"BCM3218 chip temperature"
    ::= { topCcmtsEquipmentTemperatureEntry 4 }

topCcmtsSupply1TjTemperature OBJECT-TYPE
    SYNTAX Integer32
    UNITS "degC"
    MAX-ACCESS read-only
    STATUS current
    DESCRIPTION
		"The first power chip (Power Supply1) of temperature"
    ::= { topCcmtsEquipmentTemperatureEntry 5 }

topCcmtsSupply2TjTemperature OBJECT-TYPE
    SYNTAX Integer32
    UNITS "degC"
    MAX-ACCESS read-only
    STATUS current
    DESCRIPTION
		"The second power chip (Power Supply2) temperature"
    ::= { topCcmtsEquipmentTemperatureEntry 6 }

topCcmtsSupply3TjTemperature OBJECT-TYPE
    SYNTAX Integer32
    UNITS "degC"
    MAX-ACCESS read-only
    STATUS current
    DESCRIPTION
		"The third power chip (Power Supply3) temperature"
    ::= { topCcmtsEquipmentTemperatureEntry 7 }
                                                                  
                                                                  
 ------------------------------------------------
--topCcmtsTemperatureSensor
------------------------------------------------   
topCcmtsTemperatureSensorTable OBJECT-TYPE
	SYNTAX		SEQUENCE OF TopCcmtsTemperatureSensorEntry	
	MAX-ACCESS	not-accessible
	STATUS		current
	DESCRIPTION
		""
	::={ topCcmtsSystemObject 19 }

topCcmtsTemperatureSensorEntry OBJECT-TYPE
	SYNTAX		TopCcmtsTemperatureSensorEntry
	MAX-ACCESS	not-accessible
	STATUS		current
	DESCRIPTION
		""
	INDEX { ifIndex }
	::= { topCcmtsTemperatureSensorTable 1 }
TopCcmtsTemperatureSensorEntry ::=SEQUENCE{      
         topCcmtsUsModuleTemperature	Integer32, 
         topCcmtsDsModuleTemperature	Integer32,    
 		 topCcmtsBRCM3218OutsideTemperature	Integer32,    
         topCcmtsBRCM3218InsideTemperature	Integer32,
         topCcmtsMacTemperature	Integer32
	}    
    	
topCcmtsUsModuleTemperature OBJECT-TYPE
    SYNTAX Integer32
    UNITS "degC"
    MAX-ACCESS read-only
    STATUS current
    DESCRIPTION
		"The upstream zoom chip temperature"
    ::= { topCcmtsTemperatureSensorEntry 1 }

topCcmtsDsModuleTemperature OBJECT-TYPE
    SYNTAX Integer32     
    UNITS "degC"
    MAX-ACCESS read-only
    STATUS current
    DESCRIPTION
		"The downstream zoom chip temperature"
    ::= { topCcmtsTemperatureSensorEntry 2 }

topCcmtsBRCM3218OutsideTemperature OBJECT-TYPE
    SYNTAX Integer32
    UNITS "degC"
    MAX-ACCESS read-only
    STATUS deprecated
    DESCRIPTION
		"BCM3218 chip outside temperature"
    ::= { topCcmtsTemperatureSensorEntry 3 }

topCcmtsBRCM3218InsideTemperature OBJECT-TYPE
    SYNTAX Integer32
    UNITS "degC"
    MAX-ACCESS read-only
    STATUS deprecated
    DESCRIPTION
		"BCM3218 chip inside temperature"
    ::= { topCcmtsTemperatureSensorEntry 4 }

topCcmtsMacTemperature OBJECT-TYPE
    SYNTAX Integer32
    UNITS "degC"
    MAX-ACCESS read-only
    STATUS current
    DESCRIPTION
		"Docsis MAC temperature"
    ::= { topCcmtsTemperatureSensorEntry 5 }
 
----------------------------------------------------
-- topCcmtsOpticalTransceiverInfoTable
----------------------------------------------------

topCcmtsOpticalTransceiverInfoTable OBJECT-TYPE
	SYNTAX		SEQUENCE OF TopCcmtsOpticalTransceiverInfoEntry
	MAX-ACCESS	not-accessible
	STATUS		current
	DESCRIPTION
		"This table describes optical transceiver information of specific ccmts port."
	::={ topCcmtsSystemObject 11 }

topCcmtsOpticalTransceiverInfoEntry OBJECT-TYPE
	SYNTAX		TopCcmtsOpticalTransceiverInfoEntry
	MAX-ACCESS	not-accessible
	STATUS		current
	DESCRIPTION
		"This object describes row's definition."
	INDEX { opticalTransceiverIndex }
	::={ topCcmtsOpticalTransceiverInfoTable 1 }

TopCcmtsOpticalTransceiverInfoEntry ::=SEQUENCE {
	opticalTransceiverIndex	        INTEGER, 
	opticalTransceiverSff8472Id     INTEGER,
	opticalTransceiverBitRate       INTEGER,
	opticalTransceiverWaveLen       INTEGER,  
	opticalTransceiverVendorName    DisplayString,
	opticalTransceiverVendorPn      DisplayString,
	opticalTransceiverVendorSn      DisplayString,
    opticalTransceiverDateCode      DisplayString,
	opticalTransceiverRxPower	    INTEGER,
	opticalTransceiverTxPower	    INTEGER,
	opticalTransceiverBiasCurrent   INTEGER,
	opticalTransceiverVoltage       INTEGER,
	opticalTransceiverTemperature   INTEGER
}

opticalTransceiverIndex OBJECT-TYPE
	SYNTAX		INTEGER
	MAX-ACCESS	read-only
	STATUS		current
	DESCRIPTION
		"The index of optical transceiver."
	::={ topCcmtsOpticalTransceiverInfoEntry 1 }
	
opticalTransceiverSff8472Id  OBJECT-TYPE
	SYNTAX INTEGER {
	   unknown(0),
       gbic(1),
       solder(2),
       sfp(3)
    } 
    MAX-ACCESS	read-only
	STATUS		current
	DESCRIPTION
		"unknown(0):Unknown or unspecified
		 gbic(1):GBIC
		 solder(2):Module/connector soldered to motherboard
		 sfp(3):SFP"
	::={ topCcmtsOpticalTransceiverInfoEntry 2 }
	
opticalTransceiverBitRate	OBJECT-TYPE
	SYNTAX		INTEGER 
	UNITS "Mbps"
	MAX-ACCESS	read-only
	STATUS		current
	DESCRIPTION
		"The bit rate of optical Transceiver." 
	::={ topCcmtsOpticalTransceiverInfoEntry 3 } 
	
opticalTransceiverWaveLen	OBJECT-TYPE
	SYNTAX		INTEGER 
	UNITS "nm"
	MAX-ACCESS	read-only
	STATUS		current
	DESCRIPTION
		"The wave length of optical Transceiver." 
	::={ topCcmtsOpticalTransceiverInfoEntry 4 }
	
opticalTransceiverVendorName OBJECT-TYPE
	SYNTAX		DisplayString (SIZE (0..20))
	MAX-ACCESS	read-only
	STATUS		current
	DESCRIPTION
		"The name of Vendor."
	::={ topCcmtsOpticalTransceiverInfoEntry 5 }		

opticalTransceiverVendorPn OBJECT-TYPE
	SYNTAX		DisplayString (SIZE (0..20))
	MAX-ACCESS	read-only
	STATUS		current
	DESCRIPTION
		"The PN of vendor."
	::={ topCcmtsOpticalTransceiverInfoEntry 6 }
	
opticalTransceiverVendorSn OBJECT-TYPE
	SYNTAX		DisplayString (SIZE (0..20))
	MAX-ACCESS	read-only
	STATUS		current
	DESCRIPTION
		"The SN of vendor."
	::={ topCcmtsOpticalTransceiverInfoEntry 7 }
	
opticalTransceiverDateCode OBJECT-TYPE
	SYNTAX		DisplayString (SIZE (0..10))
	MAX-ACCESS	read-only
	STATUS		current
	DESCRIPTION
		"The production date."
	::={ topCcmtsOpticalTransceiverInfoEntry 8 } 
	
opticalTransceiverRxPower OBJECT-TYPE
	SYNTAX		INTEGER 
	UNITS "HundredthdBm"
	MAX-ACCESS	read-only
	STATUS		current
	DESCRIPTION
		"The rx power of optical transceiver."
	::={ topCcmtsOpticalTransceiverInfoEntry 9 } 
	
opticalTransceiverTxPower OBJECT-TYPE
	SYNTAX		INTEGER 
	UNITS "HundredthdBm"
	MAX-ACCESS	read-only
	STATUS		current
	DESCRIPTION
		"The tx power of optical transceiver."
	::={ topCcmtsOpticalTransceiverInfoEntry 10 }

opticalTransceiverBiasCurrent OBJECT-TYPE
	SYNTAX		INTEGER
	UNITS "HundredthmA"
	MAX-ACCESS	read-only
	STATUS		current
	DESCRIPTION
		"The bias current of optical transceiver."
	::={ topCcmtsOpticalTransceiverInfoEntry 11 }
	
opticalTransceiverVoltage OBJECT-TYPE
	SYNTAX		INTEGER
	UNITS "HundredthmV"
	MAX-ACCESS	read-only
	STATUS		current
	DESCRIPTION
		"The working voltage of optical transceiver."
	::={ topCcmtsOpticalTransceiverInfoEntry 12 }
	
opticalTransceiverTemperature OBJECT-TYPE
	SYNTAX		INTEGER 
	UNITS "HundredthDegC"
	MAX-ACCESS	read-only
	STATUS		current
	DESCRIPTION
		"The working temperature of optical transceiver."
	::={ topCcmtsOpticalTransceiverInfoEntry 13 }
----------------------------------------------------
-- topCcmtsPowerVoltageTable
----------------------------------------------------

topCcmtsPowerVoltageTable OBJECT-TYPE
	SYNTAX		SEQUENCE OF TopCcmtsPowerVoltageEntry
	MAX-ACCESS	not-accessible
	STATUS		current
	DESCRIPTION
		"This table describes ccmts power voltage."
	::={ topCcmtsSystemObject 12 }

topCcmtsPowerVoltageEntry OBJECT-TYPE
	SYNTAX		TopCcmtsPowerVoltageEntry
	MAX-ACCESS	not-accessible
	STATUS		current
	DESCRIPTION
		"This object describes row's definition."
	INDEX { topCcmtsPowerVoltageIndex }
	::={ topCcmtsPowerVoltageTable 1 }

TopCcmtsPowerVoltageEntry ::=SEQUENCE {
	topCcmtsPowerVoltageIndex		Unsigned32,
	topCcmtsBcm3715Power33 		INTEGER,
	topCcmtsBcm3715Power12		INTEGER,
	topCcmtsPllPowerVoltage		INTEGER,
	topCcmtsRfPowerVoltage		INTEGER,
	topCcmtsBcm3219Voltage33	INTEGER,
	topCcmtsBcm3219Voltage12 	INTEGER,	
	topCcmtsBcm3219Voltage25 	INTEGER,	
	topCcmtsDACPowerVoltage	 	INTEGER,	
	topCcmtsBcm3218Voltage09 	INTEGER,	
	topCcmtsBcm3218Voltage30 	INTEGER,	
	topCcmtsBcm3218Voltage25 	INTEGER,	
	topCcmtsBcm3218Voltage15 	INTEGER,
	topCcmtsPowerVoltageInput	 	INTEGER
}

topCcmtsPowerVoltageIndex OBJECT-TYPE
	SYNTAX		Unsigned32
	MAX-ACCESS	read-only
	STATUS		current
	DESCRIPTION
		"The index of ccmts Power Voltage."
	::={ topCcmtsPowerVoltageEntry 1 }

topCcmtsBcm3715Power33 OBJECT-TYPE
	SYNTAX		INTEGER
	MAX-ACCESS	read-only
	STATUS		current
	DESCRIPTION
		"The 3715 3.3v power measured value."
	::={ topCcmtsPowerVoltageEntry 2 }

topCcmtsBcm3715Power12 OBJECT-TYPE
	SYNTAX		INTEGER
	MAX-ACCESS	read-only
	STATUS		current
	DESCRIPTION
		"The 3715 1.2v  power  measured value"
	::={ topCcmtsPowerVoltageEntry 3 }

topCcmtsPllPowerVoltage OBJECT-TYPE
	SYNTAX		INTEGER
	MAX-ACCESS	read-only
	STATUS		current
	DESCRIPTION
		"The pll power measured value."
	::={ topCcmtsPowerVoltageEntry 4 }
	
topCcmtsRfPowerVoltage OBJECT-TYPE
	SYNTAX		INTEGER
	MAX-ACCESS	read-only
	STATUS		current
	DESCRIPTION
		"The radio power measured value."
	::={ topCcmtsPowerVoltageEntry 5 }
	
topCcmtsBcm3219Voltage33 OBJECT-TYPE
	SYNTAX		INTEGER
	MAX-ACCESS	read-only
	STATUS		current
	DESCRIPTION
		"The 3219 chip 3.3v power measured value."
	::={ topCcmtsPowerVoltageEntry 6 }

topCcmtsBcm3219Voltage12 OBJECT-TYPE
	SYNTAX		INTEGER
	MAX-ACCESS	read-only
	STATUS		current
	DESCRIPTION
		"The 3219 chip 1.2v power measured value."
	::={ topCcmtsPowerVoltageEntry 7 }

topCcmtsBcm3219Voltage25 OBJECT-TYPE
	SYNTAX		INTEGER
	MAX-ACCESS	read-only
	STATUS		current
	DESCRIPTION
		"The 3219 chip 2.5v power measured value."
	::={ topCcmtsPowerVoltageEntry 8 }
	
topCcmtsDACPowerVoltage OBJECT-TYPE
	SYNTAX		INTEGER
	MAX-ACCESS	read-only
	STATUS		current
	DESCRIPTION
		"The AD9739 chip dac power measured value."
	::={ topCcmtsPowerVoltageEntry 9 }

topCcmtsBcm3218Voltage09 OBJECT-TYPE
	SYNTAX		INTEGER
	MAX-ACCESS	read-only
	STATUS		current
	DESCRIPTION
		"The 3218 chip 0.9V power measured value."
	::={ topCcmtsPowerVoltageEntry 10 }

topCcmtsBcm3218Voltage30 OBJECT-TYPE
	SYNTAX		INTEGER
	MAX-ACCESS	read-only
	STATUS		current
	DESCRIPTION
		"The 3218 chip 3.0V power measured value."
	::={ topCcmtsPowerVoltageEntry 11 }

topCcmtsBcm3218Voltage25 OBJECT-TYPE
	SYNTAX		INTEGER
	MAX-ACCESS	read-only
	STATUS		current
	DESCRIPTION
		"The 3218 chip 2.5V power measured value."
	::={ topCcmtsPowerVoltageEntry 12 }

topCcmtsBcm3218Voltage15 OBJECT-TYPE
	SYNTAX		INTEGER
	MAX-ACCESS	read-only
	STATUS		current
	DESCRIPTION
		"The 3218 chip 1.5V power measured value."
	::={ topCcmtsPowerVoltageEntry 13 }

topCcmtsPowerVoltageInput OBJECT-TYPE
	SYNTAX		INTEGER
	MAX-ACCESS	read-only
	STATUS		current
	DESCRIPTION
		"The power chip input power measured value."
	::={ topCcmtsPowerVoltageEntry 14 }
	
----------------------------------------------------
-- topCcmtsPowerCurrentTable
----------------------------------------------------

topCcmtsPowerCurrentTable OBJECT-TYPE
	SYNTAX		SEQUENCE OF TopCcmtsPowerCurrentEntry
	MAX-ACCESS	not-accessible
	STATUS		current
	DESCRIPTION
		"This table describes ccmts power voltage."
	::={ topCcmtsSystemObject 13 }

topCcmtsPowerCurrentEntry OBJECT-TYPE
	SYNTAX		TopCcmtsPowerCurrentEntry
	MAX-ACCESS	not-accessible
	STATUS		current
	DESCRIPTION
		"This object describes row's definition."
	INDEX { topCcmtsPowerCurrentIndex }
	::={ topCcmtsPowerCurrentTable 1 }

TopCcmtsPowerCurrentEntry ::=SEQUENCE {
	topCcmtsPowerCurrentIndex		Unsigned32,
	topCcmtsBcm3715Current33 	INTEGER,
	topCcmtsBcm3715Current12	INTEGER,
	topCcmtsPllPowerCurrent		INTEGER,
	topCcmtsRfPowerCurrent		INTEGER,
	topCcmtsBcm3219Current33	INTEGER,
	topCcmtsBcm3219Current12 	INTEGER,	
	topCcmtsBcm3219Current25 	INTEGER,	
	topCcmtsDACPowerCurrent	 	INTEGER,	
	topCcmtsBcm3218Current09 	INTEGER,	
	topCcmtsBcm3218Current30 	INTEGER,	
	topCcmtsBcm3218Current25 	INTEGER,	
	topCcmtsBcm3218Current15 	INTEGER
}

topCcmtsPowerCurrentIndex OBJECT-TYPE
	SYNTAX		Unsigned32
	MAX-ACCESS	read-only
	STATUS		current
	DESCRIPTION
		"The index of ccmts Power current table index."
	::={ topCcmtsPowerCurrentEntry 1 }

topCcmtsBcm3715Current33 OBJECT-TYPE
	SYNTAX		INTEGER
	MAX-ACCESS	read-only
	STATUS		current
	DESCRIPTION
		"The 3715 3.3v power current measured value."
	::={ topCcmtsPowerCurrentEntry 2 }

topCcmtsBcm3715Current12 OBJECT-TYPE
	SYNTAX		INTEGER
	MAX-ACCESS	read-only
	STATUS		current
	DESCRIPTION
		"The 3715 1.2v  power  current measured value"
	::={ topCcmtsPowerCurrentEntry 3 }

topCcmtsPllPowerCurrent OBJECT-TYPE
	SYNTAX		INTEGER
	MAX-ACCESS	read-only
	STATUS		current
	DESCRIPTION
		"The pll power current measured value."
	::={ topCcmtsPowerCurrentEntry 4 }
	
topCcmtsRfPowerCurrent OBJECT-TYPE
	SYNTAX		INTEGER
	MAX-ACCESS	read-only
	STATUS		current
	DESCRIPTION
		"The radio power current measured value."
	::={ topCcmtsPowerCurrentEntry 5 }
	
topCcmtsBcm3219Current33 OBJECT-TYPE
	SYNTAX		INTEGER
	MAX-ACCESS	read-only
	STATUS		current
	DESCRIPTION
		"The 3219 chip 3.3v power current measured value."
	::={ topCcmtsPowerCurrentEntry 6 }

topCcmtsBcm3219Current12 OBJECT-TYPE
	SYNTAX		INTEGER
	MAX-ACCESS	read-only
	STATUS		current
	DESCRIPTION
		"The 3219 chip 1.2v power current measured value."
	::={ topCcmtsPowerCurrentEntry 7 }

topCcmtsBcm3219Current25 OBJECT-TYPE
	SYNTAX		INTEGER
	MAX-ACCESS	read-only
	STATUS		current
	DESCRIPTION
		"The 3219 chip 2.5v power current measured value."
	::={ topCcmtsPowerCurrentEntry 8 }
	
topCcmtsDACPowerCurrent OBJECT-TYPE
	SYNTAX		INTEGER
	MAX-ACCESS	read-only
	STATUS		current
	DESCRIPTION
		"The AD9739 chip dac power current measured value."
	::={ topCcmtsPowerCurrentEntry 9 }

topCcmtsBcm3218Current09 OBJECT-TYPE
	SYNTAX		INTEGER
	MAX-ACCESS	read-only
	STATUS		current
	DESCRIPTION
		"The 3218 chip 0.9V power current measured value."
	::={ topCcmtsPowerCurrentEntry 10 }

topCcmtsBcm3218Current30 OBJECT-TYPE
	SYNTAX		INTEGER
	MAX-ACCESS	read-only
	STATUS		current
	DESCRIPTION
		"The 3218 chip 3.0V power current measured value."
	::={ topCcmtsPowerCurrentEntry 11 }

topCcmtsBcm3218Current25 OBJECT-TYPE
	SYNTAX		INTEGER
	MAX-ACCESS	read-only
	STATUS		current
	DESCRIPTION
		"The 3218 chip 2.5V power current measured value."
	::={ topCcmtsPowerCurrentEntry 12 }

topCcmtsBcm3218Current15 OBJECT-TYPE
	SYNTAX		INTEGER
	MAX-ACCESS	read-only
	STATUS		current
	DESCRIPTION
		"The 3218 chip 1.5V power current measured value."
	::={ topCcmtsPowerCurrentEntry 13 }    
	
    
------------------------------------------------
-- topCcmtsLinkStatusObject
------------------------------------------------
topCcmtsLinkStatusObject	OBJECT IDENTIFIER ::={ topCcmtsSystemObject 14 }

topCcmtsDownLinkStatus OBJECT-TYPE
    SYNTAX INTEGER {down(0),up(1)}
    MAX-ACCESS read-only
    STATUS current
    DESCRIPTION
		"The downlink status."
    ::= { topCcmtsLinkStatusObject 1 } 
    
topCcmtsUpLinkTable OBJECT-TYPE
	SYNTAX		SEQUENCE OF TopCcmtsUpLinkEntry
	MAX-ACCESS	not-accessible
	STATUS		current
	DESCRIPTION
		"This uplink table."
	::={ topCcmtsLinkStatusObject 2 }  
	
topCcmtsUpLinkEntry OBJECT-TYPE
	SYNTAX		TopCcmtsUpLinkEntry
	MAX-ACCESS	not-accessible
	STATUS		current
	DESCRIPTION
		"This object describes uplink information."      
	INDEX  { topCcmtsUplinkIndex }
	::={ topCcmtsUpLinkTable 1 }  
	
TopCcmtsUpLinkEntry ::=SEQUENCE {
	topCcmtsUplinkIndex		    Unsigned32,     
	topCcmtsUplinkMedia     	INTEGER,
	topCcmtsUplinkStatus     	INTEGER,
	topCcmtsUplinkSpeed			INTEGER,
	topCcmtsUplinkDuplexMode    INTEGER,
	topCcmtsUplinkDscr			OCTET STRING
}  

topCcmtsUplinkIndex OBJECT-TYPE
    SYNTAX Unsigned32    
    MAX-ACCESS read-only
    STATUS current
    DESCRIPTION  
    	"The uplink index"
    ::={topCcmtsUpLinkEntry 1}    
    
topCcmtsUplinkMedia OBJECT-TYPE
    SYNTAX INTEGER {copper(1),fiber(2),epon(3),gpon(4)}
    MAX-ACCESS read-only
    STATUS current
    DESCRIPTION  
    	"The uplink media"
    ::={topCcmtsUpLinkEntry 2}     
    
topCcmtsUplinkStatus OBJECT-TYPE
    SYNTAX INTEGER {up(1),down(2)}
    MAX-ACCESS read-only
    STATUS current
    DESCRIPTION  
    	"The uplink status"
    ::={topCcmtsUpLinkEntry 3}    
    
topCcmtsUplinkSpeed OBJECT-TYPE
    SYNTAX INTEGER {mbps1000(1),mbps100(2),reserved(3)}
    MAX-ACCESS read-only
    STATUS current
    DESCRIPTION  
    	"The uplink speed"
    ::={topCcmtsUpLinkEntry 4}    
    
topCcmtsUplinkDuplexMode OBJECT-TYPE
    SYNTAX INTEGER {full(1),half(2)}
    MAX-ACCESS read-only
    STATUS current
    DESCRIPTION  
    	"The uplink duplex mode"
    ::={topCcmtsUpLinkEntry 5}    
    
topCcmtsUplinkDscr OBJECT-TYPE
	SYNTAX OCTET STRING (SIZE (0..255))
    MAX-ACCESS read-only
    STATUS current
    DESCRIPTION  
    	"The uplink description"
    ::={topCcmtsUpLinkEntry 6}  
                   
------------------------------------------------
--topCcmtsUpChnlSigQTraceTable
------------------------------------------------

 topUpChnlSigQTraceTable OBJECT-TYPE
	SYNTAX		SEQUENCE OF TopUpChnlSigQTraceEntry
	MAX-ACCESS	not-accessible
	STATUS		current
	DESCRIPTION
		""
	::={ topCcmtsSystemObject 15 }

topUpChnlSigQTraceEntry OBJECT-TYPE
	SYNTAX		TopUpChnlSigQTraceEntry
	MAX-ACCESS	not-accessible
	STATUS		current
	DESCRIPTION
		""
	INDEX { topUpChnlSigQCmcIndex }
	::={ topUpChnlSigQTraceTable 1 }

TopUpChnlSigQTraceEntry ::=SEQUENCE {
	topUpChnlSigQCmcIndex    						 InterfaceIndex,
	topUpChnlSigQHistoryRecEnable                    INTEGER,
	topUpChnlSigQHistoyRecClear						 INTEGER,
	topUpChnlSigQSignalNoiseThreshold                TenthdB,
	topUpChnlSigQSignalNoiseRecoveryThreshold        TenthdB,
	topUpChnlSigQCorrectedsThreshold                 Unsigned32,
	topUpChnlSigQCorrectedsRecoveryThreshold         Unsigned32,
	topUpChnlSigQUncorrectablesThreshold             Unsigned32,
	topUpChnlSigQUncorrectablesRecoveryThreshold     Unsigned32
}

topUpChnlSigQCmcIndex OBJECT-TYPE
	SYNTAX		InterfaceIndex
	MAX-ACCESS	read-only
	STATUS		current
	DESCRIPTION
		"The InterfaceIndex of CCMTS."
	::={ topUpChnlSigQTraceEntry 1 }

topUpChnlSigQHistoryRecEnable OBJECT-TYPE
	SYNTAX		INTEGER{
		enable(1) ,
		disable(2) 
		}
	MAX-ACCESS	read-write
	STATUS		current
	DESCRIPTION
		"Enable/Disable the Func,which allow to Record Signal Quality History."
	::={ topUpChnlSigQTraceEntry 2 }
       
topUpChnlSigQHistoyRecClear OBJECT-TYPE
	SYNTAX		INTEGER{
		enable(1) ,
		disable(2) 
		}
	MAX-ACCESS	read-write
	STATUS		current
	DESCRIPTION
		"Clear Cmc's UpChannel Signal Quality History Records."
	::={ topUpChnlSigQTraceEntry 3 }

topUpChnlSigQSignalNoiseThreshold OBJECT-TYPE
	SYNTAX		TenthdB
	MAX-ACCESS	read-write
	STATUS		current
	DESCRIPTION
		"The Threshold to inform that SignalNoise is badly low "
	::={ topUpChnlSigQTraceEntry 4 }

topUpChnlSigQSignalNoiseRecoveryThreshold OBJECT-TYPE
	SYNTAX		TenthdB
	MAX-ACCESS	read-write
	STATUS		current
	DESCRIPTION
		"The Threshold to inform that SignalNoise Recoverid"
	::={ topUpChnlSigQTraceEntry 5 }

topUpChnlSigQCorrectedsThreshold OBJECT-TYPE
	SYNTAX		Unsigned32
	MAX-ACCESS	read-write
	STATUS		current
	DESCRIPTION
		"The Threshold to inform that Correcteds is badly high"
	::={ topUpChnlSigQTraceEntry 6 }

topUpChnlSigQCorrectedsRecoveryThreshold OBJECT-TYPE
	SYNTAX		Unsigned32
	MAX-ACCESS	read-write
	STATUS		current
	DESCRIPTION
		"The Threshold to inform that Correcteds Recoverid" 
	::={ topUpChnlSigQTraceEntry 7 }

topUpChnlSigQUncorrectablesThreshold OBJECT-TYPE
	SYNTAX		Unsigned32
	MAX-ACCESS	read-write
	STATUS		current
	DESCRIPTION
		"The Threshold to inform that Uncorrectables is badly high"
	::={ topUpChnlSigQTraceEntry 8 }

topUpChnlSigQUncorrectablesRecoveryThreshold OBJECT-TYPE
	SYNTAX		Unsigned32
	MAX-ACCESS	read-write
	STATUS		current
	DESCRIPTION
		"The Threshold to inform that Uncorrectables Recoverid"
	::={ topUpChnlSigQTraceEntry 9 } 
    
------------------------------------------------
-- topCcmtsObject
------------------------------------------------
topCcmtsSysTimeObject	OBJECT IDENTIFIER ::={ topCcmtsSystemObject 16 }

topCcmtsSysTime OBJECT-TYPE
    SYNTAX 		Unsigned32 
    MAX-ACCESS read-write
    STATUS current
    DESCRIPTION
		"The current system time value,which is the seconds past since 1970-01-01."
	DEFVAL          { 0 }
    ::= { topCcmtsSysTimeObject 1 }  
    
topCcmtsSysTimeZone OBJECT-TYPE
    SYNTAX 		INTEGER (-13..14)
    MAX-ACCESS read-write
    STATUS current
    DESCRIPTION
		"The timezone value."
	DEFVAL          { 8 }
    ::= { topCcmtsSysTimeObject 2 }
                               
topCcmtsNtpserverAddress OBJECT-TYPE
    SYNTAX 		DisplayString (SIZE (3..51))
    MAX-ACCESS read-write
    STATUS current
    DESCRIPTION
		"The NTP server address could be a domain name or an IP.
		 When NTP server is configured to be domain name, it only consists of letters ['a-z', 'A-Z', '0-9', '.', '-'], and without '-' or '.' at the begining or end."
--	DEFVAL          { 0 }
    ::= { topCcmtsSysTimeObject 3 }

topCcmtsSysTimeSynInterval OBJECT-TYPE
    SYNTAX 		Unsigned32 (0..2595599)
    MAX-ACCESS read-write
    STATUS deprecated
    DESCRIPTION
		"How long the system time be synchronized,which's unit is seconds."
	DEFVAL          { 0 }
    ::= { topCcmtsSysTimeObject 4 }
    
topCcmtsSysTimeZone_min OBJECT-TYPE
    SYNTAX 		INTEGER (-780..840)
    MAX-ACCESS read-write
    STATUS current
    DESCRIPTION
		"The timezone offset value in minute."
    ::= { topCcmtsSysTimeObject 5 }

----------------------------------------------------
-- topCcmtsAccessDenyIpTable
----------------------------------------------------

topCcmtsAccessDenyIpTable OBJECT-TYPE
	SYNTAX		SEQUENCE OF TopCcmtsAccessDenyIpEntry
	MAX-ACCESS	not-accessible
	STATUS		current
	DESCRIPTION
		"This table describes ccmts' blacklist."
	::={ topCcmtsSystemObject 17 }

topCcmtsAccessDenyIpEntry OBJECT-TYPE
	SYNTAX		TopCcmtsAccessDenyIpEntry
	MAX-ACCESS	not-accessible
	STATUS		current
	DESCRIPTION
		"This object describes row's definition."
	INDEX { topCcmtsAccessDenyIpIndex }
	::={ topCcmtsAccessDenyIpTable 1 }

TopCcmtsAccessDenyIpEntry ::=SEQUENCE {
	topCcmtsAccessDenyIpIndex			Unsigned32,
	topCcmtsAccessDenyIpAddr 			Unsigned32,
	topCcmtsAccessDenyIpMask			Unsigned32,
	topCcmtsAccessDenyIpStatus		Unsigned32
}

topCcmtsAccessDenyIpIndex OBJECT-TYPE
	SYNTAX		Unsigned32
	MAX-ACCESS	read-only
	STATUS		current
	DESCRIPTION
		"The index of ccmts blacklist table index."
	::={ topCcmtsAccessDenyIpEntry 1 }

topCcmtsAccessDenyIpAddr OBJECT-TYPE
	SYNTAX		Unsigned32
	MAX-ACCESS	read-write
	STATUS		current
	DESCRIPTION
		"The current blacklist IP value."
	::={ topCcmtsAccessDenyIpEntry 2 }

topCcmtsAccessDenyIpMask OBJECT-TYPE
	SYNTAX		Unsigned32
	MAX-ACCESS	read-write
	STATUS		current
	DESCRIPTION
		"The current blacklist IP mask value."
	::={ topCcmtsAccessDenyIpEntry 3 }

topCcmtsAccessDenyIpStatus OBJECT-TYPE
	SYNTAX		Unsigned32
	MAX-ACCESS	read-write
	STATUS		current
	DESCRIPTION
		"The sign of adding or deleting a record of blacklist."
	::={ topCcmtsAccessDenyIpEntry 4 }
	
------------------------------------------------
--topCcmtsRouteTable
------------------------------------------------
topCcmtsRouteTable OBJECT-TYPE
	SYNTAX		SEQUENCE OF TopCcmtsRouteEntry
	MAX-ACCESS	not-accessible
	STATUS		current
	DESCRIPTION
		""
	::={ topCcmtsSystemObject 18 }

topCcmtsRouteEntry OBJECT-TYPE
	SYNTAX		TopCcmtsRouteEntry
	MAX-ACCESS	not-accessible
	STATUS		current
	DESCRIPTION
		""
	INDEX { topCcmtsRouteIndex }
	::={ topCcmtsRouteTable 1 }

TopCcmtsRouteEntry ::=SEQUENCE {
	topCcmtsRouteIndex    		INTEGER,
	topCcmtsRouteDstIp          IpAddress,
	topCcmtsRouteIpMask			IpAddress,
	topCcmtsRouteNexthop        IpAddress,
	topCcmtsRoutePort           OCTET STRING,
	topCcmtsRouteStatus			RowStatus
	}

topCcmtsRouteIndex OBJECT-TYPE
	SYNTAX		INTEGER
	MAX-ACCESS	not-accessible
	STATUS		current
	DESCRIPTION
		"The index of route table, value range is 0-77.
		The first 12(0-11) entries are read-write for static route which user can configure manually;
		The next 64(12-75) entries are readonly for direct route of VLAN interface;
		The last 2(76-77) entries are readonly for direct route of outband interface."
	::={ topCcmtsRouteEntry 1 }

topCcmtsRouteDstIp OBJECT-TYPE
	SYNTAX		IpAddress
	MAX-ACCESS	read-write
	STATUS		current
	DESCRIPTION
		"The destination ip address."
	::={ topCcmtsRouteEntry 2 }
       
topCcmtsRouteIpMask OBJECT-TYPE
	SYNTAX		IpAddress	
	MAX-ACCESS	read-write
	STATUS		current
	DESCRIPTION
		"The destination network mask."
	::={ topCcmtsRouteEntry 3 }

topCcmtsRouteNexthop OBJECT-TYPE
	SYNTAX		IpAddress
	MAX-ACCESS	read-write
	STATUS		current
	DESCRIPTION
		"The next hop ip address"
	::={ topCcmtsRouteEntry 4 }   
	
topCcmtsRoutePort OBJECT-TYPE
	SYNTAX		OCTET STRING(SIZE(0..30)) 
	MAX-ACCESS	read-only
	STATUS		current
	DESCRIPTION
		"The interface name"
	::={ topCcmtsRouteEntry 5 }

topCcmtsRouteStatus OBJECT-TYPE
	SYNTAX		RowStatus
	MAX-ACCESS	read-write
	STATUS		current
	DESCRIPTION
		"The status of the route"
	::={ topCcmtsRouteEntry 6 }   
	
------------------------------------------------
--topCcmtsSysSpecObject       
--topCcmtsSysSpecAclObject
--added by liubin at July.12 2013
------------------------------------------------
topCcmtsSysSpecObject		OBJECT IDENTIFIER ::={ topCcmtsSystemObject 20 }
topCcmtsSysSpecAclObject	OBJECT IDENTIFIER ::={ topCcmtsSysSpecObject 1 }

topCcmtsSysSpecAclUplinkEgressCnt OBJECT-TYPE
	SYNTAX INTEGER (0..65535)
	MAX-ACCESS	read-only
	STATUS	current
	DESCRIPTION
		"The number of uplink egress acl"
	::= { topCcmtsSysSpecAclObject 1 }

topCcmtsSysSpecAclUplinkIngressCnt OBJECT-TYPE
	SYNTAX INTEGER (0..65535)
	MAX-ACCESS	read-only
	STATUS	current
	DESCRIPTION
		"The number of uplink ingress acl"
	::= { topCcmtsSysSpecAclObject 2 }

topCcmtsSysSpecAclCableEgressCnt OBJECT-TYPE
	SYNTAX INTEGER (0..65535)
	MAX-ACCESS	read-only
	STATUS	current
	DESCRIPTION
		"The number of cable egress acl"
	::= { topCcmtsSysSpecAclObject 3 }

topCcmtsSysSpecAclCableIngressCnt OBJECT-TYPE
	SYNTAX INTEGER (0..65535)
	MAX-ACCESS	read-only
	STATUS	current
	DESCRIPTION
		"The number of cable ingress acl"
	::= { topCcmtsSysSpecAclObject 4 }

topCcmtsSysSpecAclUplinkEgressCopy2cpu OBJECT-TYPE
	SYNTAX INTEGER {
					true(1),
					false(2)
					}                
	MAX-ACCESS	read-only
	STATUS	current
	DESCRIPTION
		"true(1) support capture packets to cpu, false(2) don't support"
	::= { topCcmtsSysSpecAclObject 5 }

topCcmtsSysSpecAclUplinkIngressCopy2cpu OBJECT-TYPE
	SYNTAX INTEGER {
					true(1),
					false(2)
					}
	MAX-ACCESS	read-only
	STATUS	current
	DESCRIPTION
		"true(1) support capture packets to cpu, false(2) don't support"
	::= { topCcmtsSysSpecAclObject 6 }

topCcmtsSysSpecAclCableEgressCopy2cpu OBJECT-TYPE
	SYNTAX INTEGER {
					true(1),
					false(2)
					}
	MAX-ACCESS	read-only
	STATUS	current
	DESCRIPTION
		"true(1) support capture packets to cpu, false(2) don't support"
	::= { topCcmtsSysSpecAclObject 7 }

topCcmtsSysSpecAclCableIngressCopy2cpu OBJECT-TYPE
	SYNTAX INTEGER {
					true(1),
					false(2)
					}
	MAX-ACCESS	read-only
	STATUS	current
	DESCRIPTION
		"true(1) support capture packets to cpu, false(2) don't support"
	::= { topCcmtsSysSpecAclObject 8 }

------------------------------------------------     
--topCcmtsSysSpecSubnetVlanObject
--added by liubin at July.12 2013
------------------------------------------------    
topCcmtsSysSpecSubnetVlanObject 	OBJECT IDENTIFIER ::={ topCcmtsSysSpecObject 2 }  

topCcmtsSysSpecSubnetVlanCnt OBJECT-TYPE
	SYNTAX INTEGER (0..65535)
	MAX-ACCESS	read-only
	STATUS	current
	DESCRIPTION
		"The number of subnet vlan "
	::= { topCcmtsSysSpecSubnetVlanObject 1 }

------------------------------------------------     
--topCcmtsSysSpecFpgaObject
--added by liubin at July.12 2013
------------------------------------------------
topCcmtsSysSpecFpgaObject	OBJECT IDENTIFIER ::={ topCcmtsSysSpecObject 3 }

topCcmtsSysSpecFpgaIpqamChnlCnt OBJECT-TYPE
	SYNTAX INTEGER (0..65535)
	MAX-ACCESS	read-only
	STATUS	current
	DESCRIPTION
		"The number of ipqam channel,(0) mean we don't support ipqam"
	::= { topCcmtsSysSpecFpgaObject 1 } 

topCcmtsSysSpecFpgaVipCnt OBJECT-TYPE
	SYNTAX INTEGER (0..65535)
	MAX-ACCESS	read-only
	STATUS	current
	DESCRIPTION
		"The number of vip CPE IP "
	::= { topCcmtsSysSpecFpgaObject 2 }

topCcmtsSysSpecFpgaCosCmCnt OBJECT-TYPE
	SYNTAX INTEGER (0..65535)
	MAX-ACCESS	read-only
	STATUS	current
	DESCRIPTION
		"The number of total CM"
	::= { topCcmtsSysSpecFpgaObject 3 }

topCcmtsSysSpecFpgaCosPerCMCnt OBJECT-TYPE
	SYNTAX INTEGER (0..65535)
	MAX-ACCESS	read-only
	STATUS	current
	DESCRIPTION
		"The number of service flow per cm"
	::= { topCcmtsSysSpecFpgaObject 4 }

topCcmtsSysSpecFpgaMacTableSize OBJECT-TYPE
	SYNTAX INTEGER (0..65535)
	MAX-ACCESS	read-only
	STATUS	current
	DESCRIPTION
		"The size of mac table,number of mac address we learn"
	::= { topCcmtsSysSpecFpgaObject 5 }

topCcmtsSysSpecFpgaSrcVerifyCnt OBJECT-TYPE
	SYNTAX INTEGER (0..65535)
	MAX-ACCESS	read-only
	STATUS	current
	DESCRIPTION
		"The size of source verify table"
	::= { topCcmtsSysSpecFpgaObject 6 }
	
------------------------------------------------
--topCcmtsTemperatureThreshold
------------------------------------------------   
topCcmtsTemperatureThresholdTable OBJECT-TYPE
	SYNTAX		SEQUENCE OF TopCcmtsTemperatureThresholdEntry	
	MAX-ACCESS	not-accessible
	STATUS		current
	DESCRIPTION
		""
	::={ topCcmtsSystemObject 21 }

topCcmtsTemperatureThresholdEntry OBJECT-TYPE
	SYNTAX		TopCcmtsTemperatureThresholdEntry
	MAX-ACCESS	not-accessible
	STATUS		current
	DESCRIPTION
		""
	INDEX { ifIndex }
	::= { topCcmtsTemperatureThresholdTable 1 }
	
TopCcmtsTemperatureThresholdEntry ::=SEQUENCE{      
         topCcmts3218InsRedAlarmThreshold		Integer32, 
         topCcmts3218InsYellowAlarmThreshold	Integer32,    
 		 topCcmtsOtherRedAlarmThreshold			Integer32,    
         topCcmtsOtherYellowAlarmThreshold		Integer32
	}    
    	
topCcmts3218InsRedAlarmThreshold OBJECT-TYPE
    SYNTAX Integer32
    UNITS "degC"
    MAX-ACCESS read-write
    STATUS current
    DESCRIPTION
		"3218 Inside Red Alarm temperature threshold"
    ::= { topCcmtsTemperatureThresholdEntry 1 }    
    
topCcmts3218InsYellowAlarmThreshold OBJECT-TYPE
    SYNTAX Integer32
    UNITS "degC"
    MAX-ACCESS read-write
    STATUS current
    DESCRIPTION
		"3218 Inside Yellow Alarm temperature threshold"
    ::= { topCcmtsTemperatureThresholdEntry 2 }    
    
topCcmtsOtherRedAlarmThreshold OBJECT-TYPE
    SYNTAX Integer32 (-128..127)
    UNITS "degC"
    MAX-ACCESS read-write
    STATUS current
    DESCRIPTION
		"Other Red Alarm temperature threshold, value should be greater than the value of other Yellow Alarm temperature threshold."
    ::= { topCcmtsTemperatureThresholdEntry 3 }  
    
topCcmtsOtherYellowAlarmThreshold OBJECT-TYPE
    SYNTAX Integer32 (-128..127)
    UNITS "degC"
    MAX-ACCESS read-write
    STATUS current
    DESCRIPTION
		"Other Yellow Alarm temperature threshold, value should be smaller than the value of other Red Alarm temperature threshold."
    ::= { topCcmtsTemperatureThresholdEntry 4 }

	
 ------------------------------------------------
--topCcmtsClockTable add by wangpy
------------------------------------------------   
topCcmtsClockTable OBJECT-TYPE
	SYNTAX		SEQUENCE OF TopCcmtsClockEntry	
	MAX-ACCESS	not-accessible
	STATUS		current
	DESCRIPTION
		""
	::={ topCcmtsSystemObject 22 }

topCcmtsClockEntry OBJECT-TYPE
	SYNTAX		TopCcmtsClockEntry
	MAX-ACCESS	not-accessible
	STATUS		current
	DESCRIPTION
		""
	INDEX { topCcmtsMac }
	::= { topCcmtsClockTable 1 }
	
TopCcmtsClockEntry ::=SEQUENCE{      
         topCcmtsMac		MacAddress, 
         topCcmtsClockTime	Counter64    
	}    
    	
topCcmtsMac OBJECT-TYPE
    SYNTAX MacAddress
    MAX-ACCESS read-only
    STATUS current
    DESCRIPTION
		"MAC of C-CMTS"
    ::= { topCcmtsClockEntry 1 }    
  
  
topCcmtsClockTime OBJECT-TYPE
    SYNTAX Counter64
    MAX-ACCESS read-write
    STATUS current
    DESCRIPTION
		"Time On the C-Cmts"
    ::= { topCcmtsClockEntry 2 }    
    
----------------------------------------------------
-- topCcmtsIpFirewallObject
----------------------------------------------------    
topCcmtsIpFirewallObject OBJECT IDENTIFIER ::= { topCcmtsSystemObject 24 }

topCcmtsIpFirewallTable OBJECT-TYPE
	SYNTAX		SEQUENCE OF TopCcmtsIpFirewallEntry
	MAX-ACCESS	not-accessible
	STATUS		deprecated
	DESCRIPTION
		"This table describes ccmts' ip firewall."
	::={ topCcmtsIpFirewallObject 1 }

topCcmtsIpFirewallEntry OBJECT-TYPE
	SYNTAX		TopCcmtsIpFirewallEntry
	MAX-ACCESS	not-accessible
	STATUS		deprecated
	DESCRIPTION
		"This object describes row's definition."
	INDEX { topCcmtsFirewallItemIndex }
	::={ topCcmtsIpFirewallTable 1 } 	
             
TopCcmtsIpFirewallEntry ::=SEQUENCE {
	topCcmtsFirewallItemIndex			Unsigned32,
	topCcmtsFirewallItemIpAddr 			IpAddress,
	topCcmtsFirewallItemIpMask			IpAddress,       
	topCcmtsFirewallItemAction 			INTEGER,
	topCcmtsFirewallItemProtocol		INTEGER,
	topCcmtsFirewallItemOpcode			RowStatus,
	topCcmtsFirewallItemAddrType		Unsigned32,
	topCcmtsFirewallItemIpAddrV6		InetAddressIPv6,
	topCcmtsFirewallItemIpPrefix		Unsigned32
}

topCcmtsFirewallItemIndex OBJECT-TYPE
	SYNTAX		Unsigned32
	MAX-ACCESS	not-accessible
	STATUS		deprecated
	DESCRIPTION
		"The index of ccmts firewall table index."
	::={ topCcmtsIpFirewallEntry 1 }

topCcmtsFirewallItemIpAddr OBJECT-TYPE
	SYNTAX		IpAddress
	MAX-ACCESS	read-write
	STATUS		deprecated
	DESCRIPTION
		"The current firewall IP value."
	::={ topCcmtsIpFirewallEntry 2 }

topCcmtsFirewallItemIpMask OBJECT-TYPE
	SYNTAX		IpAddress
	MAX-ACCESS	read-write
	STATUS		deprecated
	DESCRIPTION
		"The current firewall IP mask value."
	::={ topCcmtsIpFirewallEntry 3 }

topCcmtsFirewallItemAction OBJECT-TYPE
	SYNTAX		INTEGER {deny(0),permit(1)}
	MAX-ACCESS	read-write
	STATUS		deprecated
	DESCRIPTION
		"Permit or deny the IP access the device."
	::={ topCcmtsIpFirewallEntry 4 }      
	
topCcmtsFirewallItemProtocol OBJECT-TYPE
	SYNTAX		INTEGER {telnet(1),ssh(2),snmp(3),web(4)}
	MAX-ACCESS	read-write
	STATUS		deprecated
	DESCRIPTION
		"The protocol which this firewall item will be used for."
	::={ topCcmtsIpFirewallEntry 5 }

topCcmtsFirewallItemOpcode OBJECT-TYPE
	SYNTAX		RowStatus {active(1),createAndGo(4),destroy(6)}
	MAX-ACCESS	write-only
	STATUS		deprecated
	DESCRIPTION
		"The sign of adding or deleting a record of firewall."
	::={ topCcmtsIpFirewallEntry 6 }   
	 
topCcmtsFirewallItemAddrType OBJECT-TYPE
	SYNTAX		Unsigned32 {undown(0),ipv4(1),ipv6(2)}
	MAX-ACCESS	read-write
	STATUS		deprecated
	DESCRIPTION
		"The type of ip address used."
	::={ topCcmtsIpFirewallEntry 7 }  	

topCcmtsFirewallItemIpAddrV6 OBJECT-TYPE
	SYNTAX		InetAddressIPv6(SIZE(0..16)) 
	MAX-ACCESS	read-write
	STATUS		deprecated
	DESCRIPTION
		"The value of ipv6 address."
	::={ topCcmtsIpFirewallEntry 8 }

topCcmtsFirewallItemIpPrefix OBJECT-TYPE
	SYNTAX		Unsigned32 (1..128)
	MAX-ACCESS	read-write
	STATUS		deprecated
	DESCRIPTION
		"The value of ipv6 address prefix."
	::={ topCcmtsIpFirewallEntry 9 }  
	
topCcmtsFirewallSwitchTable OBJECT-TYPE
	SYNTAX		SEQUENCE OF TopCcmtsFirewallSwitchEntry
	MAX-ACCESS	not-accessible
	STATUS		deprecated
	DESCRIPTION
		"This table describes ccmts' ip firewall swich."
	::={ topCcmtsIpFirewallObject 2 }

topCcmtsFirewallSwitchEntry OBJECT-TYPE
	SYNTAX		TopCcmtsFirewallSwitchEntry
	MAX-ACCESS	not-accessible
	STATUS		deprecated
	DESCRIPTION
		"This object describes row's definition."
	INDEX { topCcmtsFirewallProtocol }
	::={ topCcmtsFirewallSwitchTable 1 } 	
             
TopCcmtsFirewallSwitchEntry ::=SEQUENCE {
	topCcmtsFirewallProtocol		    INTEGER,
	topCcmtsFirewallStatus   			INTEGER
}

topCcmtsFirewallProtocol OBJECT-TYPE
	SYNTAX		INTEGER {telnet(1),ssh(2),snmp(3),web(4)}
	MAX-ACCESS	read-only
	STATUS		deprecated
	DESCRIPTION
		"The protocol which the firewall can control."
	::={ topCcmtsFirewallSwitchEntry 1 }
 
topCcmtsFirewallStatus OBJECT-TYPE
	SYNTAX		INTEGER {enable(1),disable(0)}
	MAX-ACCESS	read-write
	STATUS		deprecated
	DESCRIPTION
		"The protocol switch status."
	::={ topCcmtsFirewallSwitchEntry 2 }

--------------------------------------------------------------------
--
--added at 2017-12-18
--------------------------------------------------------------------
topCcmtsDevIpFirewallTable OBJECT-TYPE
	SYNTAX		SEQUENCE OF TopCcmtsDevIpFirewallEntry
	MAX-ACCESS	not-accessible
	STATUS		current
	DESCRIPTION
		"This table describes ccmts' ip firewall."
	::={ topCcmtsIpFirewallObject 3 }

topCcmtsDevIpFirewallEntry OBJECT-TYPE
	SYNTAX		TopCcmtsDevIpFirewallEntry
	MAX-ACCESS	not-accessible
	STATUS		current
	DESCRIPTION
		"This object describes row's definition."
	INDEX { ifIndex, topCcmtsDevFirewallItemIndex }
	::={ topCcmtsDevIpFirewallTable 1 } 	
             
TopCcmtsDevIpFirewallEntry ::=SEQUENCE {
	topCcmtsDevFirewallItemIndex			Unsigned32,
	topCcmtsDevFirewallItemIpAddr 			IpAddress,
	topCcmtsDevFirewallItemIpMask			IpAddress,       
	topCcmtsDevFirewallItemAction 			INTEGER,
	topCcmtsDevFirewallItemProtocol		INTEGER,
	topCcmtsDevFirewallItemOpcode			RowStatus,
	topCcmtsDevFirewallItemAddrType		Unsigned32,
	topCcmtsDevFirewallItemIpAddrV6		InetAddressIPv6,
	topCcmtsDevFirewallItemIpPrefix		Unsigned32
}

topCcmtsDevFirewallItemIndex OBJECT-TYPE
	SYNTAX		Unsigned32
	MAX-ACCESS	not-accessible
	STATUS		current
	DESCRIPTION
		"The index of ccmts firewall table index."
	::={ topCcmtsDevIpFirewallEntry 1 }

topCcmtsDevFirewallItemIpAddr OBJECT-TYPE
	SYNTAX		IpAddress
	MAX-ACCESS	read-write
	STATUS		current
	DESCRIPTION
		"The current firewall IP value."
	::={ topCcmtsDevIpFirewallEntry 2 }

topCcmtsDevFirewallItemIpMask OBJECT-TYPE
	SYNTAX		IpAddress
	MAX-ACCESS	read-write
	STATUS		current
	DESCRIPTION
		"The current firewall IP mask value."
	::={ topCcmtsDevIpFirewallEntry 3 }

topCcmtsDevFirewallItemAction OBJECT-TYPE
	SYNTAX		INTEGER {deny(0),permit(1)}
	MAX-ACCESS	read-write
	STATUS		current
	DESCRIPTION
		"Permit or deny the IP access the device."
	::={ topCcmtsDevIpFirewallEntry 4 }      
	
topCcmtsDevFirewallItemProtocol OBJECT-TYPE
	SYNTAX		INTEGER {telnet(1),ssh(2),snmp(3),web(4)}
	MAX-ACCESS	read-write
	STATUS		current
	DESCRIPTION
		"The protocol which this firewall item will be used for."
	::={ topCcmtsDevIpFirewallEntry 5 }

topCcmtsDevFirewallItemOpcode OBJECT-TYPE
	SYNTAX		RowStatus {active(1),createAndGo(4),destroy(6)}
	MAX-ACCESS	write-only
	STATUS		current
	DESCRIPTION
		"The sign of adding or deleting a record of firewall."
	::={ topCcmtsDevIpFirewallEntry 6 }   
	 
topCcmtsDevFirewallItemAddrType OBJECT-TYPE
	SYNTAX		Unsigned32 {undown(0),ipv4(1),ipv6(2)}
	MAX-ACCESS	read-write
	STATUS		current
	DESCRIPTION
		"The type of ip address used."
	::={ topCcmtsDevIpFirewallEntry 7 }  	

topCcmtsDevFirewallItemIpAddrV6 OBJECT-TYPE
	SYNTAX		InetAddressIPv6(SIZE(0..16)) 
	MAX-ACCESS	read-write
	STATUS		current
	DESCRIPTION
		"The value of ipv6 address."
	::={ topCcmtsDevIpFirewallEntry 8 }

topCcmtsDevFirewallItemIpPrefix OBJECT-TYPE
	SYNTAX		Unsigned32 (1..128)
	MAX-ACCESS	read-write
	STATUS		current
	DESCRIPTION
		"The value of ipv6 address prefix."
	::={ topCcmtsDevIpFirewallEntry 9 }  
	
topCcmtsDevFirewallSwitchTable OBJECT-TYPE
	SYNTAX		SEQUENCE OF TopCcmtsDevFirewallSwitchEntry
	MAX-ACCESS	not-accessible
	STATUS		current
	DESCRIPTION
		"This table describes ccmts' ip firewall swich."
	::={ topCcmtsIpFirewallObject 4 }

topCcmtsDevFirewallSwitchEntry OBJECT-TYPE
	SYNTAX		TopCcmtsDevFirewallSwitchEntry
	MAX-ACCESS	not-accessible
	STATUS		current
	DESCRIPTION
		"This object describes row's definition."
	INDEX { ifIndex, topCcmtsDevFirewallProtocol }
	::={ topCcmtsDevFirewallSwitchTable 1 } 	
             
TopCcmtsDevFirewallSwitchEntry ::=SEQUENCE {
	topCcmtsDevFirewallProtocol		    INTEGER,
	topCcmtsDevFirewallStatus   		INTEGER
}

topCcmtsDevFirewallProtocol OBJECT-TYPE
	SYNTAX		INTEGER {telnet(1),ssh(2),snmp(3),web(4)}
	MAX-ACCESS	read-only
	STATUS		current
	DESCRIPTION
		"The protocol which the firewall can control."
	::={ topCcmtsDevFirewallSwitchEntry 1 }
 
topCcmtsDevFirewallStatus OBJECT-TYPE
	SYNTAX		INTEGER {enable(1),disable(0)}
	MAX-ACCESS	read-write
	STATUS		current
	DESCRIPTION
		"The protocol switch status."
	::={ topCcmtsDevFirewallSwitchEntry 2 }
--------------------------------------------------------------------
--
--added at 2017-12-18 
--------------------------------------------------------------------
	

 	
 topCcmtsMemoryMonitorTable OBJECT-TYPE
	SYNTAX		SEQUENCE OF TopCcmtsMemoryMonitorEntry	
	MAX-ACCESS	not-accessible
	STATUS		current
	DESCRIPTION
		""
	::={ topCcmtsSystemObject 25 }
	
topCcmtsMemoryMonitorEntry OBJECT-TYPE
	SYNTAX		TopCcmtsMemoryMonitorEntry
	MAX-ACCESS	not-accessible
	STATUS		current
	DESCRIPTION
		""
	INDEX { topCcmtsMac }
	::= { topCcmtsMemoryMonitorTable 1 }
	
TopCcmtsMemoryMonitorEntry ::=SEQUENCE{      
         topCcmtsMemoryMonitorThresholdWarning		INTEGER, 
         topCcmtsMemoryMonitorThresholdRecover	    INTEGER,  
         topCcmtsMemoryMonitorAdminStatus           INTEGER    
	}    
    	
topCcmtsMemoryMonitorThresholdWarning OBJECT-TYPE
    SYNTAX    INTEGER(2..96)
    MAX-ACCESS read-write
    STATUS current
    DESCRIPTION
		"the warning threshold, the range is [2-96], and default is 85. 
		Can't be smaller than topCcmtsMemoryMonitorThresholdRecover."
    ::= { topCcmtsMemoryMonitorEntry 1 }    
  
  
topCcmtsMemoryMonitorThresholdRecover OBJECT-TYPE
    SYNTAX INTEGER(1..95)
    MAX-ACCESS read-write
    STATUS current
    DESCRIPTION
		"the recovery threshold, the range is [1-95], and default is 75. 
		Can't be bigger than topCcmtsMemoryMonitorThresholdWarning."
    ::= { topCcmtsMemoryMonitorEntry 2 }     
 
topCcmtsMemoryMonitorAdminStatus OBJECT-TYPE
    SYNTAX INTEGER {
    				enable(1),
    				disable(2)
    			}
    MAX-ACCESS read-write
    STATUS current
    DESCRIPTION
		"Memory Monitor Threshold Warning Switch"
    ::= { topCcmtsMemoryMonitorEntry 3 }   
	
	
----------------------------------------------------
-- topCcmtsZeroTouchObject
----------------------------------------------------    
topCcmtsZeroTouchObject OBJECT IDENTIFIER ::= { topCcmtsSystemObject 27 }

topCcmtsZeroTouchLedIndicateTime OBJECT-TYPE
	SYNTAX		Unsigned32(5..1440)
	MAX-ACCESS	read-write
	STATUS		current
	DESCRIPTION
		"the led instruct that zero touch configuration is completed with update."
	::={ topCcmtsZeroTouchObject 1 }

	
------------------------------------------------
--topCcmtsCapabilityTable add by lht
------------------------------------------------   
topCcmtsCapabilityTable OBJECT-TYPE
	SYNTAX		SEQUENCE OF TopCcmtsCapabilityEntry	
	MAX-ACCESS	not-accessible
	STATUS		current
	DESCRIPTION
		"Cmts capability table"
	::={ topCcmtsSystemObject 28 }

topCcmtsCapabilityEntry OBJECT-TYPE
	SYNTAX 		TopCcmtsCapabilityEntry
	MAX-ACCESS	not-accessible
	STATUS		current
	DESCRIPTION
		"Cmts capability entry"
	INDEX { ifIndex }
	::= { topCcmtsCapabilityTable 1 }
	
TopCcmtsCapabilityEntry ::=SEQUENCE{      
         topCcmtsEqamSupport	TruthValue
}    
    	
topCcmtsEqamSupport OBJECT-TYPE
    SYNTAX TruthValue
    MAX-ACCESS read-only
    STATUS current
    DESCRIPTION
		"Capability of EQAM function support"
    ::= { topCcmtsCapabilityEntry 1 } 
 ----------------------------------------------------
-- [CCMTS-11298] Define Item "AttributeMask" here.
----------------------------------------------------  
AttributeMask ::= TEXTUAL-CONVENTION
     STATUS      current
     DESCRIPTION
        "This data type consists of a sequence of 32-bit positions used
        to select the bonding group or the channel to which a service
        flow is assigned. DOCSIS defines three types of Attribute Masks
        for which this type applies: The Provisionied Attribute Mask
        that is configured to a Bonding Group or a single-channel,
        whereas the Required Attribute and the Forbidden Attribute
        Mask are part of the Service Flow QOS Parameter Set to be
        matched with the Provisioned Attribute Mask of CMTS-configured
        Bonding Groups or single-channels. DOCSIS reserves the
        assignment of the meaning of the first 8 bit positions
        (left to right) as follows:
            Bit 0: 'bonding'
            Bit 1: 'lowLatency'
            Bit 2: 'highAvailability'
            Bit positions 3-15 are reserved.

        Bit positions 16-31 are freely assigned by operators to
        represent their own constraints on the channel(s) selection
        for a particular service flow."
     REFERENCE
         "DOCSIS 3.0 MAC and Upper Layer Protocols Interface
         Specification CM-SP-MULPIv3.0-I08-080522, Service Flow
         Assignment section."
     SYNTAX      BITS {
                       bonding(0),
                       lowLatency(1),
                       highAvailability(2)
                      }
----------------------------------------------------
-- [CCMTS-11298] topCcmtsDocsis30VoiceAttributeObject
----------------------------------------------------   
topCcmtsDocsis30VoiceAttributeObject OBJECT IDENTIFIER ::= { topCcmtsSystemObject 30 }
topCcmtsDsDocsis30VoiceRequiredAttribute OBJECT-TYPE
	SYNTAX		AttributeMask
	MAX-ACCESS	read-write
	STATUS		current
	DESCRIPTION
		"The docsis30-voice default req-attr-mask value of downstream channel."
	DEFVAL { '00000000'H }
	::={ topCcmtsDocsis30VoiceAttributeObject 1 }
topCcmtsDsDocsis30VoiceForbiddenAttribute OBJECT-TYPE
	SYNTAX		AttributeMask
	MAX-ACCESS	read-write
	STATUS		current
	DESCRIPTION
		"The docsis30-voice default forb-attr-mask value of downstream channel."
	DEFVAL { '00000000'H }
	::={ topCcmtsDocsis30VoiceAttributeObject 2 }
topCcmtsUsDocsis30VoiceRequiredAttribute OBJECT-TYPE
	SYNTAX		AttributeMask
	MAX-ACCESS	read-write
	STATUS		current
	DESCRIPTION
		"The docsis30-voice default req-attr-mask value of upstream channel."
	DEFVAL { '00000000'H }
	::={ topCcmtsDocsis30VoiceAttributeObject 3 }
topCcmtsUsDocsis30VoiceForbiddenAttribute OBJECT-TYPE
	SYNTAX		AttributeMask
	MAX-ACCESS	read-write
	STATUS		current
	DESCRIPTION
		"The docsis30-voice default forb-attr-mask value of upstream channel."
	DEFVAL { '00000000'H }
	::={ topCcmtsDocsis30VoiceAttributeObject 4 }  
----------------------------------------------------
-- topCcmtsGponDevInfoTable
----------------------------------------------------  
topCcmtsGponDevInfoTable OBJECT IDENTIFIER ::= { topCcmtsSystemObject 32 }
topCcmtsGponDevInfoVendorId OBJECT-TYPE
	SYNTAX		OCTET STRING(SIZE(0..64)) 
	MAX-ACCESS	read-only
	STATUS		current
	DESCRIPTION
		"Display the gpon vendor ID."
	::={ topCcmtsGponDevInfoTable 1 }
	
topCcmtsGponDevInfoSn OBJECT-TYPE
	SYNTAX		OCTET STRING(SIZE(0..64))
	MAX-ACCESS	read-only
	STATUS		current
	DESCRIPTION
		"Display the gpon serial number."
	::={ topCcmtsGponDevInfoTable 2 }
	
topCcmtsGponDevInfoEquipID OBJECT-TYPE
	SYNTAX		OCTET STRING(SIZE(0..64))
	MAX-ACCESS	read-only
	STATUS		current
	DESCRIPTION
		"Display the gpon equipment ID."
	::={ topCcmtsGponDevInfoTable 3 }
	
topCcmtsGponDevInfoOmccVersion OBJECT-TYPE
	SYNTAX		OCTET STRING(SIZE(0..64))
	MAX-ACCESS	read-only
	STATUS		current
	DESCRIPTION
		"Display the gpon OMCC version."
	::={ topCcmtsGponDevInfoTable 4 }

--------------------------------------------------------------------
--topCcmtsWebGuiAccessObject
--added at 2016-8-4
--------------------------------------------------------------------
topCcmtsWebGuiAccessObject	OBJECT IDENTIFIER ::={ topCcmtsSystemObject 33 }  

topCcmtsWebGuiHttpAccess OBJECT-TYPE
    SYNTAX INTEGER {
    				enable(1),
    				disable(2)
    			}
    MAX-ACCESS read-write
    STATUS current
    DESCRIPTION
		"The object is used to control CMTS's http access behavior. 
The enumerations are:
 1: enable (1)
 2: disable (2)"

	::={ topCcmtsWebGuiAccessObject 1 }    
	
 
------------------------------------------------
--topCcmtsDownstreamTxPowerLimitTable add by huochao
------------------------------------------------   
topCcmtsDownstreamTxPowerLimitTable OBJECT-TYPE
	SYNTAX		SEQUENCE OF TopCcmtsDownstreamTxPowerLimitEntry	
	MAX-ACCESS	not-accessible
	STATUS		current
	DESCRIPTION
		"CMTS downstream channel transmit power configuration limit table."
	::={ topCcmtsSystemObject 29 }

topCcmtsDownstreamTxPowerLimitEntry OBJECT-TYPE
	SYNTAX 		TopCcmtsDownstreamTxPowerLimitEntry
	MAX-ACCESS	not-accessible
	STATUS		current
	DESCRIPTION
		"CMTS downstream channel transmit power configuration limit entry."
	INDEX { ifIndex,
	        topCcmtsDsChnlPowerLimitUpChnlNum
          }
	::= { topCcmtsDownstreamTxPowerLimitTable 1 }
	
TopCcmtsDownstreamTxPowerLimitEntry ::=SEQUENCE{      
         topCcmtsDsChnlPowerLimitUpChnlNum	INTEGER,
		 topCcmtsDsChnlPowerLimitMaxPower   TenthdBmV,
         topCcmtsDsChnlPowerLimitMinPower   TenthdBmV		 
}    
    	
topCcmtsDsChnlPowerLimitUpChnlNum OBJECT-TYPE
    SYNTAX INTEGER
    MAX-ACCESS not-accessible
    STATUS current
    DESCRIPTION
		"The maximum numbers of CMTS downstream active channels."
    ::= { topCcmtsDownstreamTxPowerLimitEntry 1 } 	

topCcmtsDsChnlPowerLimitMaxPower OBJECT-TYPE
    SYNTAX      TenthdBmV
    MAX-ACCESS read-only
    STATUS current
    DESCRIPTION
		"The maximum power level of CMTS downstream channels can be configured."
    ::= { topCcmtsDownstreamTxPowerLimitEntry 2 } 	
	
topCcmtsDsChnlPowerLimitMinPower OBJECT-TYPE
    SYNTAX      TenthdBmV
    MAX-ACCESS read-only
    STATUS current
    DESCRIPTION
		"The maximum power level of CMTS downstream channels can be configured."
    ::= { topCcmtsDownstreamTxPowerLimitEntry 3 } 	
	
------------------------------------------------
--topCcmtsCmStatsObject
------------------------------------------------
topCcmtsCmStatsObject	OBJECT IDENTIFIER ::={ topCcmtsMibObject 2 } 

topCcmtsCmNumTable OBJECT-TYPE
	SYNTAX		SEQUENCE OF TopCcmtsCmNumEntry
	MAX-ACCESS	not-accessible
	STATUS		current
	DESCRIPTION
		"CM number statistics table based CMTS ifindex"
	::={ topCcmtsCmStatsObject 1 }

topCcmtsCmNumEntry OBJECT-TYPE
	SYNTAX		TopCcmtsCmNumEntry
	MAX-ACCESS	not-accessible
	STATUS		current
	DESCRIPTION	
		"CM number statistics entry based CMTS ifindex"
	INDEX  { ifIndex }
	::={ topCcmtsCmNumTable 1 } 
	
TopCcmtsCmNumEntry ::=SEQUENCE{
	topCcmtsCmNumTotal	Integer32,
	topCcmtsCmNumOnline	Integer32,
	topCcmtsCmNumActive  Integer32,
	topCcmtsCmNumUnregistered   Integer32,
	topCcmtsCmNumOffline Integer32,
	topCcmtsCmNumRegistered Integer32,
	topCcmtsCmNumOnlineD Integer32,
	topCcmtsCmNumWideBand Integer32,
	topCcmtsCmNumWideBandD Integer32,
	topCcmtsCmNumExpire Integer32,
	topCcmtsCmNumReject Integer32
}     

topCcmtsCmNumTotal OBJECT-TYPE
	SYNTAX		Integer32
	MAX-ACCESS	read-only
	STATUS		current
	DESCRIPTION
		"Total CM number,include all CM status"
	::={ topCcmtsCmNumEntry 1 }

topCcmtsCmNumOnline OBJECT-TYPE
	SYNTAX		Integer32
	MAX-ACCESS	read-only
	STATUS		current
	DESCRIPTION
		"Total online CM number,include only online status"
	::={ topCcmtsCmNumEntry 2 }

topCcmtsCmNumActive OBJECT-TYPE
	SYNTAX		Integer32
	MAX-ACCESS	read-only
	STATUS		current
	DESCRIPTION
		"Total active CM number,exclude offline CMs"
	::={ topCcmtsCmNumEntry 3 }

topCcmtsCmNumUnregistered OBJECT-TYPE
	SYNTAX		Integer32
	MAX-ACCESS	read-only
	STATUS		current
	DESCRIPTION
		"Total unregistered CM number"
	::={ topCcmtsCmNumEntry 4 }

topCcmtsCmNumOffline OBJECT-TYPE
	SYNTAX		Integer32
	MAX-ACCESS	read-only
	STATUS		current
	DESCRIPTION
		"Total offline CM number"
	::={ topCcmtsCmNumEntry 5 }

topCcmtsCmNumRegistered OBJECT-TYPE
	SYNTAX		Integer32
	MAX-ACCESS	read-only
	STATUS		current
	DESCRIPTION
		"Total registered CM number, include only online and online-d status"     
	::={ topCcmtsCmNumEntry 6 }   
	
topCcmtsCmNumOnlineD OBJECT-TYPE
	SYNTAX		Integer32
	MAX-ACCESS	read-only
	STATUS		current
	DESCRIPTION
		"Total online-d CM number"   
	::={ topCcmtsCmNumEntry 7 }  
	
topCcmtsCmNumWideBand OBJECT-TYPE
	SYNTAX		Integer32
	MAX-ACCESS	read-only
	STATUS		current
	DESCRIPTION
		"Total WideBand CM number"   
	::={ topCcmtsCmNumEntry 8 }
	
topCcmtsCmNumWideBandD OBJECT-TYPE
	SYNTAX		Integer32
	MAX-ACCESS	read-only
	STATUS		current
	DESCRIPTION
		"Total WideBand(d) CM number"   
	::={ topCcmtsCmNumEntry 9 }

topCcmtsCmNumExpire OBJECT-TYPE
	SYNTAX		Integer32
	MAX-ACCESS	read-only
	STATUS		current
	DESCRIPTION
		"Total Expire CM number"   
	::={ topCcmtsCmNumEntry 10 }
	
topCcmtsCmNumReject OBJECT-TYPE
	SYNTAX		Integer32
	MAX-ACCESS	read-only
	STATUS		current
	DESCRIPTION
		"Total Reject CM number"   
	::={ topCcmtsCmNumEntry 11 }

topCcmtsServiceFlowNumTable OBJECT-TYPE
	SYNTAX		SEQUENCE OF TopCcmtsServiceFlowNumEntry
	MAX-ACCESS	not-accessible
	STATUS		current
	DESCRIPTION	
		""	
	::={ topCcmtsCmStatsObject 2 }

topCcmtsServiceFlowNumEntry OBJECT-TYPE
	SYNTAX		TopCcmtsServiceFlowNumEntry
	MAX-ACCESS	not-accessible
	STATUS		current
	DESCRIPTION
		""    
	INDEX { 
		ifIndex,
		docsQosIfDirection 
		}
	::={ topCcmtsServiceFlowNumTable 1 }

TopCcmtsServiceFlowNumEntry ::=SEQUENCE {
	topCcmtsServiceFlowNum	Integer32
}
	
topCcmtsServiceFlowNum OBJECT-TYPE
	SYNTAX		Integer32
	MAX-ACCESS	read-only
	STATUS		current
	DESCRIPTION
		""
	::={ topCcmtsServiceFlowNumEntry 1}


topCcmtsCmNumber OBJECT IDENTIFIER ::={ topCcmtsCmStatsObject 3 }

topCcmtsTotalCmNum OBJECT-TYPE
	SYNTAX		Integer32
	MAX-ACCESS	read-only
	STATUS		current
	DESCRIPTION
		"The number of total Cable Modems on the device."
	::={ topCcmtsCmNumber 1 }

topCcmtsOnlineCmNum OBJECT-TYPE
	SYNTAX		Integer32
	MAX-ACCESS	read-only
	STATUS		current
	DESCRIPTION
		"The number of total Online Cable Modems on the device."
	::={ topCcmtsCmNumber 2}
   
topCcmtsActiveCmNum OBJECT-TYPE
	SYNTAX		Integer32
	MAX-ACCESS	read-only
	STATUS		current
	DESCRIPTION
		"The number of total Active Cable Modems on the device."
	::={ topCcmtsCmNumber 3}
		  
topCcmtsUnregisteredCmNum OBJECT-TYPE
	SYNTAX		Integer32
	MAX-ACCESS	read-only
	STATUS		current
	DESCRIPTION
		"The number of total Unregistered Cable Modems on the device."
	::={ topCcmtsCmNumber 4}        
	
topCcmtsOfflineCmNum OBJECT-TYPE
	SYNTAX		Integer32
	MAX-ACCESS	read-only
	STATUS		current
	DESCRIPTION
		"The number of total Offline Cable Modems on the device."
	::={ topCcmtsCmNumber 5}        

topCcmtsRegisteredCmNum OBJECT-TYPE
	SYNTAX		Integer32
	MAX-ACCESS	read-only
	STATUS		current
	DESCRIPTION
		"The number of total Registered Cable Modems on the device."
	::={ topCcmtsCmNumber 6}
 
topCcmtsOnlineDCmNum OBJECT-TYPE
	SYNTAX		Integer32
	MAX-ACCESS	read-only
	STATUS		current
	DESCRIPTION
		"The number of total Online(d) Cable Modems on the device."
	::={ topCcmtsCmNumber 8}
	
topCcmtsWideBandCmNum OBJECT-TYPE
	SYNTAX		Integer32
	MAX-ACCESS	read-only
	STATUS		current
	DESCRIPTION
		"The number of total WideBand Cable Modems on the device."
	::={ topCcmtsCmNumber 9}

topCcmtsWideBandDCmNum OBJECT-TYPE
	SYNTAX		Integer32
	MAX-ACCESS	read-only
	STATUS		current
	DESCRIPTION
		"The number of total WideBand(d) Cable Modems on the device."
	::={ topCcmtsCmNumber 10}

topCcmtsExpireCmNum OBJECT-TYPE
	SYNTAX		Integer32
	MAX-ACCESS	read-only
	STATUS		current
	DESCRIPTION
		"The number of total Expired Cable Modems on the device."
	::={ topCcmtsCmNumber 11}

topCcmtsRejectCmNum OBJECT-TYPE
	SYNTAX		Integer32
	MAX-ACCESS	read-only
	STATUS		current
	DESCRIPTION
		"The number of total Rejected Cable Modems on the device."
	::={ topCcmtsCmNumber 12}

topCcmtsChannelCmNumTable OBJECT-TYPE
	SYNTAX		SEQUENCE OF TopCcmtsChannelCmNumEntry
	MAX-ACCESS	not-accessible
	STATUS		current
	DESCRIPTION
		"The number of Cable Modems of different states on a specific channel of the device."
	::={ topCcmtsCmNumber 7 }

topCcmtsChannelCmNumEntry OBJECT-TYPE
	SYNTAX		TopCcmtsChannelCmNumEntry
	MAX-ACCESS	not-accessible
	STATUS		current
	DESCRIPTION
		"The number of Cable Modems of different states on a specific channel of the device."
	INDEX { ifIndex }
	::={ topCcmtsChannelCmNumTable 1 }

TopCcmtsChannelCmNumEntry ::=SEQUENCE{
	topCcmtsChannelCmNumTotal	Integer32,
	topCcmtsChannelCmNumOnline	Integer32,
	topCcmtsChannelCmNumActive  Integer32,
	topCcmtsChannelCmNumUnregistered   Integer32,
	topCcmtsChannelCmNumOffline Integer32,
	topCcmtsChannelCmNumRegistered Integer32,
	topCcmtsChannelCmNumOnlineD Integer32,
	topCcmtsChannelCmNumWideBand Integer32,
	topCcmtsChannelCmNumWideBandD Integer32,
	topCcmtsChannelCmNumExpire Integer32,
	topCcmtsChannelCmNumReject Integer32
}

topCcmtsChannelCmNumTotal OBJECT-TYPE
	SYNTAX		Integer32
	MAX-ACCESS	read-only
	STATUS		current
	DESCRIPTION
		"The number of total Cable Modems on a specific channel of the device."
	::={ topCcmtsChannelCmNumEntry 1 }

topCcmtsChannelCmNumOnline OBJECT-TYPE
	SYNTAX		Integer32
	MAX-ACCESS	read-only
	STATUS		current
	DESCRIPTION
		"The number of total Online Cable Modems on a specific channel of the device."
	::={ topCcmtsChannelCmNumEntry 2 }                
	
topCcmtsChannelCmNumActive OBJECT-TYPE
	SYNTAX		Integer32
	MAX-ACCESS	read-only
	STATUS		current
	DESCRIPTION
		"The number of total Active Cable Modems on a specific channel of the device."
	::={ topCcmtsChannelCmNumEntry 3 }   
	
topCcmtsChannelCmNumUnregistered OBJECT-TYPE
	SYNTAX		Integer32
	MAX-ACCESS	read-only
	STATUS		current
	DESCRIPTION
		"The number of total Unregistered Cable Modems on a specific channel of the device."
	::={ topCcmtsChannelCmNumEntry 4 }
	
topCcmtsChannelCmNumOffline OBJECT-TYPE
	SYNTAX		Integer32
	MAX-ACCESS	read-only
	STATUS		current
	DESCRIPTION
		"The number of total Offline Cable Modems on a specific channel of the device."
	::={ topCcmtsChannelCmNumEntry 5 }
	
topCcmtsChannelCmNumRegistered OBJECT-TYPE
	SYNTAX		Integer32
	MAX-ACCESS	read-only
	STATUS		current
	DESCRIPTION
		"The number of total Registered Cable Modems on a specific channel of the device."
	::={ topCcmtsChannelCmNumEntry 6 }  
	
topCcmtsChannelCmNumOnlineD OBJECT-TYPE
	SYNTAX		Integer32
	MAX-ACCESS	read-only
	STATUS		current
	DESCRIPTION
		"The number of total Online(d) Cable Modems on a specific channel of the device."
	::={ topCcmtsChannelCmNumEntry 7 } 
	
topCcmtsChannelCmNumWideBand OBJECT-TYPE
	SYNTAX		Integer32
	MAX-ACCESS	read-only
	STATUS		current
	DESCRIPTION
		"The number of total WideBand Cable Modems on a specific channel of the device."
	::={ topCcmtsChannelCmNumEntry 8 }
	
topCcmtsChannelCmNumWideBandD OBJECT-TYPE
	SYNTAX		Integer32
	MAX-ACCESS	read-only
	STATUS		current
	DESCRIPTION
		"The number of total WideBand(d) Cable Modems on a specific channel of the device."
	::={ topCcmtsChannelCmNumEntry 9 }

topCcmtsChannelCmNumExpire OBJECT-TYPE
	SYNTAX		Integer32
	MAX-ACCESS	read-only
	STATUS		current
	DESCRIPTION
		"The number of total Expired Cable Modems on a specific channel of the device."
	::={ topCcmtsChannelCmNumEntry 10 }
	
topCcmtsChannelCmNumReject OBJECT-TYPE
	SYNTAX		Integer32
	MAX-ACCESS	read-only
	STATUS		current
	DESCRIPTION
		"The number of total Rejected Cable Modems on a specific channel of the device."
	::={ topCcmtsChannelCmNumEntry 11 }
	
--------------------------------------------------------------------
--Added @ 2012.12.14    
--------------------------------------------------------------------
topCcmtsCmControlTable OBJECT-TYPE
	SYNTAX		SEQUENCE OF TopCcmtsCmControlEntry
	MAX-ACCESS	not-accessible
	STATUS		current
	DESCRIPTION
		"Control all CMs(kick or clear offline now) based on C-CMTS"
	::={ topCcmtsCmStatsObject 4 }

topCcmtsCmControlEntry OBJECT-TYPE
	SYNTAX		TopCcmtsCmControlEntry
	MAX-ACCESS	not-accessible
	STATUS		current
	DESCRIPTION	
		"Control all CMs(kick or clear offline now) based on C-CMTS"
	INDEX  { ifIndex }
	::={ topCcmtsCmControlTable 1 }
TopCcmtsCmControlEntry ::=SEQUENCE{
	topCcmtsCmReset			TruthValue,
	topCcmtsCmOfflineClear		TruthValue,
	topCcmtsCmFlapClear			TruthValue
}

topCcmtsCmReset OBJECT-TYPE
	SYNTAX		TruthValue
	MAX-ACCESS	read-write
	STATUS		current
	DESCRIPTION
		"Set true(1) to kick all CMs belong to the C-CMTS.
		When read ,always return false(2)."
	::={ topCcmtsCmControlEntry 1 }

topCcmtsCmOfflineClear OBJECT-TYPE
	SYNTAX		TruthValue
	MAX-ACCESS	read-write
	STATUS		current
	DESCRIPTION
		"Set true(1) to clear all offline CMs belong to the C-CMTS.
		When read ,always return false(2)."
	::={ topCcmtsCmControlEntry 2 }    
	
topCcmtsCmFlapClear OBJECT-TYPE
	SYNTAX		TruthValue
	MAX-ACCESS	read-write
	STATUS		current
	DESCRIPTION
		"Set true(1) to clear all CM flaplist belong to the C-CMTS.
		When read ,always return false(2)."
	::={ topCcmtsCmControlEntry 3 }

	
--------------------------------------------------------------------
--Added @ 2013.4.16    
--------------------------------------------------------------------
topCcmtsCmStaticIpTable OBJECT-TYPE
	SYNTAX		SEQUENCE OF TopCcmtsCmStaticIpEntry
	MAX-ACCESS	not-accessible
	STATUS		deprecated
	DESCRIPTION
		"Show all static IPs(mgmt cpe ip) based on CM"
	::={ topCcmtsCmStatsObject 6 }

topCcmtsCmStaticIpEntry OBJECT-TYPE
	SYNTAX		TopCcmtsCmStaticIpEntry
	MAX-ACCESS	not-accessible
	STATUS		deprecated
	DESCRIPTION	
		"Show one static IP (mgmt cpe ip) based on CM"
	INDEX  { docsIfCmtsCmStatusIndex, topCcmtsCmStaticIPIndex }
	::={ topCcmtsCmStaticIpTable 1 }
TopCcmtsCmStaticIpEntry ::=SEQUENCE{
	topCcmtsCmStaticIPIndex			Unsigned32,  
	topCcmtsCmStaticIPAddress       IpAddress
}

topCcmtsCmStaticIPIndex OBJECT-TYPE
	SYNTAX		Unsigned32
	MAX-ACCESS	read-only
	STATUS		deprecated
	DESCRIPTION
		"static ip address index"
	::={ topCcmtsCmStaticIpEntry 1 }  
	
topCcmtsCmStaticIPAddress OBJECT-TYPE
	SYNTAX		IpAddress
	MAX-ACCESS	read-only
	STATUS		deprecated
	DESCRIPTION
		"static ip address, also named as mgmt cpe ip"
	::={ topCcmtsCmStaticIpEntry 2 }

topCcmtsCmStaticIpv4Table OBJECT-TYPE
	SYNTAX		SEQUENCE OF TopCcmtsCmStaticIpv4Entry
	MAX-ACCESS	not-accessible
	STATUS		current
	DESCRIPTION
		"Show all static IPs(mgmt cpe ipv4 entry) based on CM"
	::={ topCcmtsCmStatsObject 25 }

topCcmtsCmStaticIpv4Entry OBJECT-TYPE
	SYNTAX		TopCcmtsCmStaticIpv4Entry
	MAX-ACCESS	not-accessible
	STATUS		current
	DESCRIPTION	
		"Show one static IP (mgmt cpe ipv4 entry) based on CM"
	INDEX  { docsIfCmtsCmStatusIndex, topCcmtsCmStaticIPSrcType, topCcmtsCmStaticIPv4Index }
	::={ topCcmtsCmStaticIpv4Table 1 }
TopCcmtsCmStaticIpv4Entry ::=SEQUENCE{
	topCcmtsCmStaticIPSrcType       Unsigned32, 
	topCcmtsCmStaticIPv4Index			Unsigned32,  
	topCcmtsCmStaticIPv4Address       IpAddress
}

topCcmtsCmStaticIPSrcType OBJECT-TYPE
	SYNTAX		Unsigned32   
	MAX-ACCESS	read-only
	STATUS		current
	DESCRIPTION
		"static ipv4 address source type, 0 - cli/snmp, 1 - cfg file."
	::={ topCcmtsCmStaticIpv4Entry 1 }  
	
topCcmtsCmStaticIPv4Index OBJECT-TYPE
	SYNTAX		Unsigned32
	MAX-ACCESS	read-only
	STATUS		current
	DESCRIPTION
		"static ipv4 address index"
	::={ topCcmtsCmStaticIpv4Entry 2 }  
	
topCcmtsCmStaticIPv4Address OBJECT-TYPE
	SYNTAX		IpAddress
	MAX-ACCESS	read-only
	STATUS		current
	DESCRIPTION
		"static ipv4 address, also named as mgmt cpe ip"
	::={ topCcmtsCmStaticIpv4Entry 3 }

topCcmtsCmIPv4VlanTable OBJECT-TYPE
	SYNTAX		SEQUENCE OF TopCcmtsCmIPv4VlanEntry
	MAX-ACCESS	not-accessible
	STATUS		current
	DESCRIPTION
		"Cable Modem IPv4 address and VLAN map to Cable Modem MAC address"
	::={ topCcmtsCmStatsObject 26 }

topCcmtsCmIPv4VlanEntry OBJECT-TYPE
	SYNTAX		TopCcmtsCmIPv4VlanEntry
	MAX-ACCESS	not-accessible
	STATUS		current
	DESCRIPTION	
		"Cable Modem IPv4 address and VLAN map to Cable Modem MAC address"
	INDEX  { topCcmtsCmVlan, topCcmtsCmIPv4Address }
	::={ topCcmtsCmIPv4VlanTable 1 }
TopCcmtsCmIPv4VlanEntry ::=SEQUENCE{
	topCcmtsCmVlan				Unsigned32, 
	topCcmtsCmIPv4Address       IpAddress,  
	topCcmtsCmMacAddress       	OCTET STRING
}
 
	
topCcmtsCmVlan OBJECT-TYPE
	SYNTAX		Unsigned32(0..4094)
	MAX-ACCESS	not-accessible
	STATUS		current
	DESCRIPTION
		"Cable Modem VLAN ID"
	::={ topCcmtsCmIPv4VlanEntry 1 }
	
topCcmtsCmIPv4Address OBJECT-TYPE
	SYNTAX		IpAddress   
	MAX-ACCESS	not-accessible
	STATUS		current
	DESCRIPTION
		"Cable Modem IPv4 address"
	::={ topCcmtsCmIPv4VlanEntry 2 } 
	
topCcmtsCmMacAddress OBJECT-TYPE
	SYNTAX		OCTET STRING
	MAX-ACCESS	read-only
	STATUS		current
	DESCRIPTION
		"Cable Modem MAC address"
	::={ topCcmtsCmIPv4VlanEntry 3 }

------------------------------------------------------------------------------
--  topCcmtsCmBlackListObject
--  added at 2013-9-9
--  author wanghao
------------------------------------------------------------------------------
--topCcmtsCmBlackListTable	OBJECT IDENTIFIER ::={ topCcmtsCmStatsObject 7 } 
	
topCcmtsCmBlackListTable OBJECT-TYPE
	SYNTAX 		SEQUENCE OF TopCcmtsCmBlackListEntry
	MAX-ACCESS 	not-accessible
	STATUS 		current
	DESCRIPTION
		"Cable modem black list table"
	::= { topCcmtsCmStatsObject 7 }
	
topCcmtsCmBlackListEntry OBJECT-TYPE
	SYNTAX 		TopCcmtsCmBlackListEntry
	MAX-ACCESS 	not-accessible
	STATUS 		current
	DESCRIPTION
		"Cable modem black list table entry."
	INDEX { topCcmtsCmBlackListMacIndex}
	::= { topCcmtsCmBlackListTable 1 }
		
TopCcmtsCmBlackListEntry ::=	SEQUENCE { 
		topCcmtsCmBlackListMacIndex			MacAddress,
		topCcmtsCmBlackListRowStatus		RowStatus
	 }

topCcmtsCmBlackListMacIndex OBJECT-TYPE
	SYNTAX 		MacAddress 
	MAX-ACCESS 	not-accessible
	STATUS 		current
	DESCRIPTION
		"Cable modem black list CM mac address index" 
	::= { topCcmtsCmBlackListEntry 1 }   
		
topCcmtsCmBlackListRowStatus OBJECT-TYPE
	SYNTAX 		RowStatus 
	MAX-ACCESS 	read-write
	STATUS 		current
	DESCRIPTION
		"Cable modem black list RowStatus"
	::= { topCcmtsCmBlackListEntry 2 }   

 --------------------------------------------------------------------
--Added by liubin @ 2014.03.25    
--------------------------------------------------------------------
topCcmtsCmThroughputTable OBJECT-TYPE
	SYNTAX		SEQUENCE OF TopCcmtsCmThroughputEntry
	MAX-ACCESS	not-accessible
	STATUS		current
	DESCRIPTION
		"Get total upstream and downstream throughput of all cm"
	::={ topCcmtsCmStatsObject 8 }

topCcmtsCmThroughputEntry OBJECT-TYPE
	SYNTAX		TopCcmtsCmThroughputEntry
	MAX-ACCESS	not-accessible
	STATUS		current
	DESCRIPTION	
		"Get total upstream and downstream throughput of a cm"
	INDEX  { docsIfCmtsCmStatusIndex }
	::={ topCcmtsCmThroughputTable 1 }
TopCcmtsCmThroughputEntry ::=SEQUENCE{
	topCcmtsCmUsThroughput		Unsigned32,  
	topCcmtsCmDsThroughput      Unsigned32
}

topCcmtsCmUsThroughput OBJECT-TYPE
	SYNTAX		Unsigned32        
	UNITS	"kbps"
	MAX-ACCESS	read-only
	STATUS		current
	DESCRIPTION
		"total upstream throughput of a cm"
	::={ topCcmtsCmThroughputEntry 1 }  
	
topCcmtsCmDsThroughput OBJECT-TYPE
	SYNTAX		Unsigned32     
	UNITS	"kbps"
	MAX-ACCESS	read-only
	STATUS		current
	DESCRIPTION
		"total downstream throughput of a cm"
	::={ topCcmtsCmThroughputEntry 2 }
	
----------------------------
--topCcmtsExtendsDhcpObject   
--added by Dosion Huang
--at 2012-02-14    
--modified at 2012-8-20
----------------------------
topCcmtsDhcpObject	OBJECT IDENTIFIER ::={ topCcmtsMibObject 3 } 
topCcmtsDhcpConfigObject	OBJECT IDENTIFIER ::={ topCcmtsDhcpObject 1 }

topCcmtsDhcpRelayCableSourceVerify OBJECT-TYPE
	SYNTAX		INTEGER { 			  
			  on(1),
			  off(2)
		  }
	MAX-ACCESS	read-write
	STATUS		deprecated
	DESCRIPTION
		"DHCP Relay Cable source Verify."
	::={topCcmtsDhcpConfigObject 1}

--------------------------------------------------------------
-- topCcmtsDhcpAlloc 
-- modify SYNTAX at 2012-8-27
--------------------------------------------------------------
topCcmtsDhcpAlloc OBJECT-TYPE
	SYNTAX		INTEGER{
						enable(1),
						disable(2)
				} 
	MAX-ACCESS	read-write
	STATUS		current
	DESCRIPTION
		"ip address dhcp-alloc."
	::={topCcmtsDhcpConfigObject 2}

topCcmtsDhcpMode OBJECT-TYPE
	SYNTAX		BITS{
					cmLow(0),   
					cmHigh(1),  
					hostLow(2),
					hostHigh(3),
					mtaLow(4), 
					mtaHigh(5),
					stbLow(6),
					stbHigh(7)
				} 
	MAX-ACCESS	read-write
	STATUS		current
	DESCRIPTION
		"DHCP mode.alloc 2 bits for each device. 00 mean snooping mode,
	01 mean l2-relay mode, 10 mean l3-relay mode, 11 is invalid"
	::={topCcmtsDhcpConfigObject 3}
	
-----------------------------------------------------------------------
--topCcmtsDhcpAllocOption60
--added at 2012-8-27
-----------------------------------------------------------------------	
topCcmtsDhcpAllocOption60 OBJECT-TYPE
	SYNTAX		OCTET STRING(SIZE(0..16)) 
	MAX-ACCESS	read-write
	STATUS		current
	DESCRIPTION
		"ip address dhcp-alloc's option60."
	::={topCcmtsDhcpConfigObject 4} 

-----------------------------------------------------------------------
--topCcmtsDhcpRelaySwitch
--added at 2013-4-27
-----------------------------------------------------------------------	
topCcmtsDhcpRelaySwitch OBJECT-TYPE
	SYNTAX		INTEGER { 			  
			  on(1),
			  off(2)
		  }
	MAX-ACCESS	read-write
	STATUS		current
	DESCRIPTION
		"DHCP Relay Switch."
	::={topCcmtsDhcpConfigObject 5}

topCcmtsDhcpLeaseQueryThreshold OBJECT-TYPE
	SYNTAX		INTEGER(0..255)
	MAX-ACCESS	read-write
	STATUS		current
	DESCRIPTION
		"GLOBAL DHCP LeaseQuery RATE."
	::={topCcmtsDhcpConfigObject 6}

topCcmtsDhcpBundleTable OBJECT-TYPE
		SYNTAX      SEQUENCE OF TopCcmtsDhcpBundleEntry
        MAX-ACCESS  not-accessible
        STATUS      current
        DESCRIPTION
            "This Object describes bundle interface on CCMTS."
        ::= { topCcmtsDhcpObject 2 }

topCcmtsDhcpBundleEntry OBJECT-TYPE
		SYNTAX      TopCcmtsDhcpBundleEntry
        MAX-ACCESS  not-accessible
        STATUS      current
        DESCRIPTION
            "This table describes the dhcp GiAddress for DHCP Relay
	    discover packets."
		INDEX { topCcmtsDhcpBundleInterface }
        ::= { topCcmtsDhcpBundleTable 1 }

TopCcmtsDhcpBundleEntry ::= SEQUENCE {
	topCcmtsDhcpBundleInterface		OCTET STRING,
	topCcmtsDhcpBundlePolicy		INTEGER,
	topCcmtsDhcpBundleCableSourceVerify				INTEGER,	
	topCcmtsDhcpBundleVirtualPrimaryIpAddr   		IpAddress, 
	topCcmtsDhcpBundleVirtualPrimaryIpMask	        IpAddress,
	topCcmtsDhcpBundleStatus		RowStatus,
	topCcmtsDhcpBundleLeaseQueryServer			IpAddress,
	topCcmtsDhcpBundleLeaseQueryThreshold		INTEGER,
	topCcmtsDhcpBundleLeaseQueryInterval		INTEGER
}

topCcmtsDhcpBundleInterface OBJECT-TYPE
        SYNTAX      OCTET STRING(SIZE(7..10))
        MAX-ACCESS  read-only
        STATUS      current
        DESCRIPTION
            "The Bundle interface's ID"
        ::= { topCcmtsDhcpBundleEntry 1 }

topCcmtsDhcpBundlePolicy OBJECT-TYPE
        SYNTAX      INTEGER{
		    primary(1),
		    policy(2),
		    strict(3)
		}
        MAX-ACCESS  read-create
        STATUS      current
        DESCRIPTION
            "The type of the device under this bundle the Giaddress used for.
	    Primary means all of
	    the devices use the same giaddress.Policy means the device use the 
	    IP address of the sub interface for its diaddress. If set strict(3), 
	    need to set topCcmtsDhcpGiAddrTable to complet Giaddr ."
        ::= { topCcmtsDhcpBundleEntry 2 }  
 
topCcmtsDhcpBundleCableSourceVerify	 OBJECT-TYPE
        SYNTAX      INTEGER{
		    on(1),
		    off(2),
		    dhcp(3)
		}
        MAX-ACCESS  read-create
        STATUS      current
        DESCRIPTION
            "DHCP Relay Cable source Verify.
            on(1): means the device does verify ip and mac for packets,then drop any packets verified failed.
            off(2): means the device does not verify ip and mac for packets.
            dhcp(3): means the device does verify ip and mac for packets, but will re-verify the cpe whose packets be verified failed"
        ::= { topCcmtsDhcpBundleEntry 3 }  

topCcmtsDhcpBundleVirtualPrimaryIpAddr OBJECT-TYPE
        SYNTAX      IpAddress
        MAX-ACCESS  read-create
        STATUS      current
        DESCRIPTION
            "Virtual Primary Ip of the DHCP RELAY."
        ::= { topCcmtsDhcpBundleEntry 4 }

topCcmtsDhcpBundleVirtualPrimaryIpMask OBJECT-TYPE
        SYNTAX      IpAddress
        MAX-ACCESS  read-create
        STATUS      current
        DESCRIPTION
            "Virtual Primary Ip Mask of the DHCP RELAY."
        ::= { topCcmtsDhcpBundleEntry 5 }
       
topCcmtsDhcpBundleStatus  OBJECT-TYPE
	SYNTAX          RowStatus
	MAX-ACCESS      read-create
	STATUS          current
	DESCRIPTION
		"Controls and reflects the status of rows in this
		table.  Rows in this table may be created by either the
		create-and-go or create-and-wait paradigm.  There is no
		restriction on changing values in a row of this table
		while the row is active.

		The following objects MUST have valid values before this
		object can be set to active: topCcmtsDhcpBundlePolicy" 
	::= { topCcmtsDhcpBundleEntry 6 }

topCcmtsDhcpBundleLeaseQueryServer OBJECT-TYPE
        SYNTAX      IpAddress
        MAX-ACCESS  read-create
        STATUS      current
        DESCRIPTION
            "DHCP Server ip for dhcp leasequery. if set 0.0.0.0, topCcmtsDhcpHelperIpAddr will be used"
        ::= { topCcmtsDhcpBundleEntry 7 }

topCcmtsDhcpBundleLeaseQueryThreshold OBJECT-TYPE
        SYNTAX      INTEGER(0..255)
        MAX-ACCESS  read-create
        STATUS      current
        DESCRIPTION
            "threshold for dhcp leasequery. threshold packets will be processed in interval seconds.
            see also: topCcmtsDhcpBundleLeaseQueryInterval"
        ::= { topCcmtsDhcpBundleEntry 8 }

topCcmtsDhcpBundleLeaseQueryInterval OBJECT-TYPE
        SYNTAX      INTEGER(1..10)
        MAX-ACCESS  read-create
        STATUS      current
        DESCRIPTION
            "interval for dhcp leasequery.threshold packets will be processed in interval seconds.
            see also: topCcmtsDhcpBundleLeaseQueryThreshold"
        ::= { topCcmtsDhcpBundleEntry 9 }

topCcmtsDhcpHelperTable OBJECT-TYPE
		SYNTAX      SEQUENCE OF TopCcmtsDhcpHelperEntry
        MAX-ACCESS  not-accessible
        STATUS      current
        DESCRIPTION
            "This Object describes helper address on CCMTS."
        ::= { topCcmtsDhcpObject 3 }

topCcmtsDhcpHelperEntry OBJECT-TYPE
		SYNTAX      TopCcmtsDhcpHelperEntry
        MAX-ACCESS  not-accessible
        STATUS      current
        DESCRIPTION
            "This Object describes helper address on CCMTS."
		INDEX { topCcmtsDhcpBundleInterface, 
				topCcmtsDhcpHelperDeviceType, 
				topCcmtsDhcpHelperIndex}
        ::= { topCcmtsDhcpHelperTable 1 }

TopCcmtsDhcpHelperEntry ::=SEQUENCE {
	topCcmtsDhcpHelperDeviceType	INTEGER,
	topCcmtsDhcpHelperIndex		Integer32,
	topCcmtsDhcpHelperIpAddr	IpAddress,
	topCcmtsDhcpHelperStatus	RowStatus
}

topCcmtsDhcpHelperDeviceType OBJECT-TYPE
        SYNTAX      INTEGER{		    
		    cm(1),
		    host(2),
		    mta(3),
		    stb(4),
		    all(5)
		}
        MAX-ACCESS  read-only
        STATUS      current
        DESCRIPTION
            "The device type that the DHCP Server allocate IP Address to."
        ::= { topCcmtsDhcpHelperEntry 1 }

topCcmtsDhcpHelperIndex OBJECT-TYPE
        SYNTAX      Integer32
        MAX-ACCESS  read-only
        STATUS      current
        DESCRIPTION
            "The index of the DHCP Server."
        ::= { topCcmtsDhcpHelperEntry 2 }

topCcmtsDhcpHelperIpAddr OBJECT-TYPE
        SYNTAX      IpAddress
        MAX-ACCESS  read-create
        STATUS      current
        DESCRIPTION
            "The IP address of the DHCP Server."
        ::= { topCcmtsDhcpHelperEntry 3 }

topCcmtsDhcpHelperStatus  OBJECT-TYPE
	SYNTAX          RowStatus
	 MAX-ACCESS      read-create
	 STATUS          current
	 DESCRIPTION
		"Controls and reflects the status of rows in this
		table.  Rows in this table may be created by either the
		create-and-go or create-and-wait paradigm.  There is no
		restriction on changing values in a row of this table
		while the row is active.

		The following objects MUST have valid values before this
		object can be set to active: topCcmtsDhcpHelperIpAddr." 
	::= { topCcmtsDhcpHelperEntry 4 }

topCcmtsDhcpGiAddrTable OBJECT-TYPE
		SYNTAX      SEQUENCE OF TopCcmtsDhcpGiAddrEntry
        MAX-ACCESS  not-accessible
        STATUS      current
        DESCRIPTION
            "This Object describes giaddress on CCMTS."
        ::= { topCcmtsDhcpObject 4 }

topCcmtsDhcpGiAddrEntry OBJECT-TYPE
		SYNTAX      TopCcmtsDhcpGiAddrEntry
        MAX-ACCESS  not-accessible
        STATUS      current
        DESCRIPTION
            "This Object describes giaddress on CCMTS."
		INDEX { topCcmtsDhcpBundleInterface,
				topCcmtsDhcpGiAddrDeviceType}
        ::= { topCcmtsDhcpGiAddrTable 1 }

TopCcmtsDhcpGiAddrEntry ::=SEQUENCE {
	topCcmtsDhcpGiAddrDeviceType	INTEGER,
	topCcmtsDhcpGiAddress			IpAddress,
	topCcmtsDhcpGiAddrStatus		RowStatus
}

topCcmtsDhcpGiAddrDeviceType OBJECT-TYPE
        SYNTAX      INTEGER{		    
		    cm(1),
		    host(2),
		    mta(3),
		    stb(4)
		}
        MAX-ACCESS  read-only
        STATUS      current
        DESCRIPTION
            "device type."
        ::= { topCcmtsDhcpGiAddrEntry 1 }

topCcmtsDhcpGiAddress OBJECT-TYPE
        SYNTAX      IpAddress
        MAX-ACCESS  read-create
        STATUS      current
        DESCRIPTION
            "GiAddress"
        ::= { topCcmtsDhcpGiAddrEntry 2 }

topCcmtsDhcpGiAddrStatus OBJECT-TYPE
        SYNTAX      RowStatus
        MAX-ACCESS  read-create
        STATUS      current
        DESCRIPTION
		"Controls and reflects the status of rows in this
		table.  Rows in this table may be created by either the
		create-and-go or create-and-wait paradigm.  There is no
		restriction on changing values in a row of this table
		while the row is active.

		The following objects MUST have valid values before this
		object can be set to active: topCcmtsDhcpGiAddress."
        ::= { topCcmtsDhcpGiAddrEntry 3 }

topCcmtsDhcpOption60Table OBJECT-TYPE
		SYNTAX      SEQUENCE OF TopCcmtsDhcpOption60Entry
        MAX-ACCESS  not-accessible
        STATUS      current
        DESCRIPTION
            "This Object describes option60 set on CCMTS."
        ::= { topCcmtsDhcpObject 5 }

topCcmtsDhcpOption60Entry OBJECT-TYPE
		SYNTAX      TopCcmtsDhcpOption60Entry
        MAX-ACCESS  not-accessible
        STATUS      current
        DESCRIPTION
            "This Object describes option60 set on CCMTS."  
        INDEX { topCcmtsDhcpBundleInterface,
        		topCcmtsDhcpOption60DeviceType,
        		topCcmtsDhcpOption60Index}
        ::= { topCcmtsDhcpOption60Table 1 }

TopCcmtsDhcpOption60Entry ::=SEQUENCE{
	topCcmtsDhcpOption60DeviceType	INTEGER,
	topCcmtsDhcpOption60Index		Integer32,
	topCcmtsDhcpOption60Str			OCTET STRING,
	topCcmtsDhcpOption60Status		RowStatus
}

topCcmtsDhcpOption60DeviceType OBJECT-TYPE
        SYNTAX      INTEGER{		    
		    cm(1),
		    host(2),
		    mta(3),
		    stb(4)
		}
        MAX-ACCESS  read-only
        STATUS      current
        DESCRIPTION
            "Device type"
        ::= { topCcmtsDhcpOption60Entry 1 }

topCcmtsDhcpOption60Index OBJECT-TYPE
        SYNTAX      Integer32
        MAX-ACCESS  read-only
        STATUS      current
        DESCRIPTION
            "Option60 Index."
        ::= { topCcmtsDhcpOption60Entry 2 }

topCcmtsDhcpOption60Str OBJECT-TYPE
        SYNTAX      OCTET STRING(SIZE(1..16))
        MAX-ACCESS  read-create
        STATUS      current
        DESCRIPTION
            "Option60 Index."
        ::= { topCcmtsDhcpOption60Entry 3 }

topCcmtsDhcpOption60Status OBJECT-TYPE
        SYNTAX      RowStatus
        MAX-ACCESS  read-create
        STATUS      current
        DESCRIPTION
		"Controls and reflects the status of rows in this
		table.  Rows in this table may be created by either the
		create-and-go or create-and-wait paradigm.  There is no
		restriction on changing values in a row of this table
		while the row is active.

		The following objects MUST have valid values before this
		object can be set to active: topCcmtsDhcpOption60Str."
		::= { topCcmtsDhcpOption60Entry 4 }	

-----------------------------------------------------------------------
--topCcmtsDhcpVirtualSecendaryIpTable
--added at 2013-4-19
-----------------------------------------------------------------------	
topCcmtsDhcpVirtualSecendaryIpTable OBJECT-TYPE
		SYNTAX      SEQUENCE OF TopCcmtsDhcpVirtualSecendaryIpEntry
        MAX-ACCESS  not-accessible
        STATUS      current
        DESCRIPTION
            "This Object describes bundle virtual ip of CCMTS."
        ::= { topCcmtsDhcpObject 6 }

topCcmtsDhcpVirtualSecendaryIpEntry OBJECT-TYPE 
		SYNTAX      TopCcmtsDhcpVirtualSecendaryIpEntry
        MAX-ACCESS  not-accessible
        STATUS      current
        DESCRIPTION
            "This Object describes bundle virtual ip of CCMTS."
        INDEX { topCcmtsDhcpBundleInterface,
        		topCcmtsDhcpVirtualSecendaryIpIndex}
        ::= { topCcmtsDhcpVirtualSecendaryIpTable 1 }

TopCcmtsDhcpVirtualSecendaryIpEntry ::=SEQUENCE{
	topCcmtsDhcpVirtualSecendaryIpIndex		Integer32,
	topCcmtsDhcpVirtualSecendaryIpAddr			IpAddress,
	topCcmtsDhcpVirtualSecendaryIpMask			IpAddress,
	topCcmtsDhcpVirtualSecendaryIpStatus		RowStatus
}

topCcmtsDhcpVirtualSecendaryIpIndex OBJECT-TYPE
        SYNTAX      Integer32
        MAX-ACCESS  read-only
        STATUS      current
        DESCRIPTION
            "Ip Index."
        ::= { topCcmtsDhcpVirtualSecendaryIpEntry 1 }

topCcmtsDhcpVirtualSecendaryIpAddr OBJECT-TYPE
        SYNTAX      IpAddress
        MAX-ACCESS  read-create
        STATUS      current
        DESCRIPTION
            "Virtual sub (secendary) Ip of the DHCP RELAY."
        ::= { topCcmtsDhcpVirtualSecendaryIpEntry 2 }

topCcmtsDhcpVirtualSecendaryIpMask OBJECT-TYPE
        SYNTAX      IpAddress
        MAX-ACCESS  read-create
        STATUS      current
        DESCRIPTION
            "Virtual sub (secendary) Ip Mask of the DHCP RELAY."
        ::= { topCcmtsDhcpVirtualSecendaryIpEntry 3 }

topCcmtsDhcpVirtualSecendaryIpStatus OBJECT-TYPE
        SYNTAX      RowStatus
        MAX-ACCESS  read-create
        STATUS      current
        DESCRIPTION
		"Controls and reflects the status of rows in this
		table.  Rows in this table may be created by either the
		create-and-go or create-and-wait paradigm.  There is no
		restriction on changing values in a row of this table
		while the row is active."
		::= { topCcmtsDhcpVirtualSecendaryIpEntry 4 }	 

-----------------------------------------------------------------------
--topCcmtsDhcpPacketVlanTable
--added at 2013-4-19
-----------------------------------------------------------------------	
topCcmtsDhcpPacketVlanTable OBJECT-TYPE
		SYNTAX      SEQUENCE OF TopCcmtsDhcpPacketVlanEntry
        MAX-ACCESS  not-accessible
        STATUS      current
        DESCRIPTION
            "This Object describes dhcp packet vlan adding of different device."
        ::= { topCcmtsDhcpObject 7 }

topCcmtsDhcpPacketVlanEntry OBJECT-TYPE 
		SYNTAX      TopCcmtsDhcpPacketVlanEntry
        MAX-ACCESS  not-accessible
        STATUS      current
        DESCRIPTION
            "This Object describes dhcp packet vlan adding of different device.
            The config take effect in snooping mode or l2-relay mode."
        INDEX { topCcmtsDhcpBundleInterface,
        		topCcmtsDhcpDeviceType}
        ::= { topCcmtsDhcpPacketVlanTable 1 }
		TopCcmtsDhcpPacketVlanEntry ::=SEQUENCE{
		topCcmtsDhcpDeviceType			INTEGER,
		topCcmtsDhcpTagVlan				INTEGER,
		topCcmtsDhcpTagPriority			INTEGER,
		topCcmtsDhcpPacketVlanStatus	RowStatus
		}

topCcmtsDhcpDeviceType OBJECT-TYPE
        SYNTAX      INTEGER{		    
		    cm(1),
		    host(2),
		    mta(3),
		    stb(4)
		}
        MAX-ACCESS  read-only
        STATUS      current
        DESCRIPTION
            "Device type"
        ::= { topCcmtsDhcpPacketVlanEntry 1 } 

topCcmtsDhcpTagVlan OBJECT-TYPE
        SYNTAX      INTEGER (1..4094)
	    MAX-ACCESS  read-create
	    STATUS      current
        DESCRIPTION
            "tag vlan"
        ::= { topCcmtsDhcpPacketVlanEntry 2 }       

topCcmtsDhcpTagPriority OBJECT-TYPE
        SYNTAX      INTEGER (0..7)
	    MAX-ACCESS  read-create
        STATUS      current
        DESCRIPTION
            "tag priority"
        ::= { topCcmtsDhcpPacketVlanEntry 3 } 

topCcmtsDhcpPacketVlanStatus OBJECT-TYPE
        SYNTAX      RowStatus
        MAX-ACCESS  read-create
        STATUS      current
        DESCRIPTION
		"Controls and reflects the status of rows in this
		table.  Rows in this table may be created by either the
		create-and-go or create-and-wait paradigm.  There is no
		restriction on changing values in a row of this table
		while the row is active."
		::= { topCcmtsDhcpPacketVlanEntry 4 }

-----------------------------------------------------------------------
--topCcmtsDhcpBundleVlanTable
--added at 2013-4-27
-----------------------------------------------------------------------			
topCcmtsDhcpBundleVlanTable OBJECT-TYPE
		SYNTAX      SEQUENCE OF TopCcmtsDhcpBundleVlanEntry
   		MAX-ACCESS  not-accessible
    	STATUS      current
    	DESCRIPTION
            "This Object describes bundle vlan table.
            dhcp packet can be relayed, when a packet vlan matches the bundle vlan."
    		::= { topCcmtsDhcpObject 8 }

topCcmtsDhcpBundleVlanEntry OBJECT-TYPE
		SYNTAX      TopCcmtsDhcpBundleVlanEntry
        MAX-ACCESS  not-accessible
        STATUS      current
    	DESCRIPTION
            "This Object describes bundle vlan ."
		INDEX { topCcmtsDhcpBundleInterface}
        ::= { topCcmtsDhcpBundleVlanTable 1 }
		TopCcmtsDhcpBundleVlanEntry ::=SEQUENCE {
		topCcmtsDhcpBundleVlanMap	OCTET STRING
		}

topCcmtsDhcpBundleVlanMap OBJECT-TYPE
        SYNTAX      OCTET STRING(SIZE(512))
        MAX-ACCESS  read-write
        STATUS      current
        DESCRIPTION
            "The Bundle vlan map. each bit stand for a vlan.
            setting bit N to 1 means adding vlan N to the bundle;
            setting bit N to 0 means deleting vlan N to the bundle,
            vlan range 1-4094, no use of bit 0 and bit 4095.
            the default setting of all bit is 1."
        ::= { topCcmtsDhcpBundleVlanEntry 1 }


-----------------------------------------------------------------------
--topCcmtsDhcpExtensionalDevTable
--added at 2013-4-27
-----------------------------------------------------------------------	
topCcmtsDhcpExtensionalDevTable OBJECT-TYPE
		SYNTAX      SEQUENCE OF TopCcmtsDhcpExtensionalDevEntry
        MAX-ACCESS  not-accessible
        STATUS      current
        DESCRIPTION
            "creat a dev name and add identifiable option60 strings to a kind of extentional dev.
            extentional devs have similar funcations and configurations to ordinary devs."
        ::= { topCcmtsDhcpObject 9 }

topCcmtsDhcpExtensionalDevEntry OBJECT-TYPE
		SYNTAX      TopCcmtsDhcpExtensionalDevEntry
        MAX-ACCESS  not-accessible
        STATUS      current
        DESCRIPTION
        	"creat a dev name and add identifiable option60 strings to a kind of extentional dev.
        	extentional devs have similar funcations and configurations to ordinary devs."  
        INDEX { topCcmtsDhcpBundleInterface,
        		topCcmtsDhcpExtensionalDeviceName,
        		topCcmtsDhcpExtensionalDevOptionIndex}
        ::= { topCcmtsDhcpExtensionalDevTable 1 }

		TopCcmtsDhcpExtensionalDevEntry ::=SEQUENCE{
		topCcmtsDhcpExtensionalDeviceName	OCTET STRING,
		topCcmtsDhcpExtensionalDevOptionIndex		Integer32,
		topCcmtsDhcpExtensionalDevOptionStr			OCTET STRING,
		topCcmtsDhcpExtensionalDevOptionStatus		RowStatus
		}

topCcmtsDhcpExtensionalDeviceName OBJECT-TYPE
        SYNTAX      OCTET STRING(SIZE(0..100))
        MAX-ACCESS  read-only
        STATUS      current
        DESCRIPTION
            "Device Name str."
        ::= { topCcmtsDhcpExtensionalDevEntry 1 }

topCcmtsDhcpExtensionalDevOptionIndex OBJECT-TYPE
        SYNTAX      Integer32
        MAX-ACCESS  read-only
        STATUS      current
        DESCRIPTION
            "Option60 Index."
        ::= { topCcmtsDhcpExtensionalDevEntry 2 }

topCcmtsDhcpExtensionalDevOptionStr OBJECT-TYPE
        SYNTAX      OCTET STRING(SIZE(0..100))
        MAX-ACCESS  read-create
        STATUS      current
        DESCRIPTION
            "Option60 str."
        ::= { topCcmtsDhcpExtensionalDevEntry 3 }

topCcmtsDhcpExtensionalDevOptionStatus OBJECT-TYPE
        SYNTAX      RowStatus
        MAX-ACCESS  read-create
        STATUS      current
        DESCRIPTION
		"Controls and reflects the status of rows in this
		table.  Rows in this table may be created by either the
		create-and-go or create-and-wait paradigm.  There is no
		restriction on changing values in a row of this table
		while the row is active.

		The following objects MUST have valid values before this
		object can be set to active: topCcmtsDhcpExtensionalDevOptionStr."
		::= { topCcmtsDhcpExtensionalDevEntry 4 }	

-----------------------------------------------------------------------
--topCcmtsDhcpExtensionalDevGiAddrTable
--added at 2013-4-27
-----------------------------------------------------------------------
topCcmtsDhcpExtensionalDevGiAddrTable OBJECT-TYPE
		SYNTAX      SEQUENCE OF TopCcmtsDhcpExtensionalDevGiAddrEntry
        MAX-ACCESS  not-accessible
        STATUS      current
        DESCRIPTION
            "This Object describes extensional dev giaddress on CCMTS."
        ::= { topCcmtsDhcpObject 10 }

topCcmtsDhcpExtensionalDevGiAddrEntry OBJECT-TYPE
		SYNTAX      TopCcmtsDhcpExtensionalDevGiAddrEntry
        MAX-ACCESS  not-accessible
        STATUS      current
        DESCRIPTION
            "This Object describes extensional dev giaddress on CCMTS."
		INDEX { topCcmtsDhcpBundleInterface,
				topCcmtsDhcpExtensionalDeviceName}
        ::= { topCcmtsDhcpExtensionalDevGiAddrTable 1 }

TopCcmtsDhcpExtensionalDevGiAddrEntry ::=SEQUENCE {
	topCcmtsDhcpExtensionalDevGiAddress			IpAddress,
	topCcmtsDhcpExtensionalDevGiAddrStatus		RowStatus
}

topCcmtsDhcpExtensionalDevGiAddress OBJECT-TYPE
        SYNTAX      IpAddress
        MAX-ACCESS  read-create
        STATUS      current
        DESCRIPTION
            "GiAddress"
        ::= { topCcmtsDhcpExtensionalDevGiAddrEntry 2 }

topCcmtsDhcpExtensionalDevGiAddrStatus OBJECT-TYPE
        SYNTAX      RowStatus
        MAX-ACCESS  read-create
        STATUS      current
        DESCRIPTION
		"Controls and reflects the status of rows in this
		table.  Rows in this table may be created by either the
		create-and-go or create-and-wait paradigm.  There is no
		restriction on changing values in a row of this table
		while the row is active.

		The following objects MUST have valid values before this
		object can be set to active: topCcmtsDhcpExtensionalDevGiAddress."
        ::= { topCcmtsDhcpExtensionalDevGiAddrEntry 3 }

-----------------------------------------------------------------------
--topCcmtsDhcpExtensionalDevHelperTable
--added at 2013-4-27
-----------------------------------------------------------------------
topCcmtsDhcpExtensionalDevHelperTable OBJECT-TYPE
		SYNTAX      SEQUENCE OF TopCcmtsDhcpExtensionalDevHelperEntry
        MAX-ACCESS  not-accessible
        STATUS      current
        DESCRIPTION
            "This Object describes extensional dev helper address on CCMTS.
            and extensional dev share all type helper address with ordinary dev"
        ::= { topCcmtsDhcpObject 11 }

topCcmtsDhcpExtensionalDevHelperEntry OBJECT-TYPE
		SYNTAX      TopCcmtsDhcpExtensionalDevHelperEntry
        MAX-ACCESS  not-accessible
        STATUS      current
        DESCRIPTION
            "This Object describes extensional dev helper address on CCMTS.
            and extensional dev share all type helper address with ordinary dev"
		INDEX { topCcmtsDhcpBundleInterface, 
				topCcmtsDhcpExtensionalDeviceName, 
				topCcmtsDhcpExtensionalDevHelperIndex}
        ::= { topCcmtsDhcpExtensionalDevHelperTable 1 }

		TopCcmtsDhcpExtensionalDevHelperEntry ::=SEQUENCE {
		topCcmtsDhcpExtensionalDevHelperIndex		Integer32,
		topCcmtsDhcpExtensionalDevHelperIpAddr	IpAddress,
		topCcmtsDhcpExtensionalDevHelperStatus	RowStatus
		}

topCcmtsDhcpExtensionalDevHelperIndex OBJECT-TYPE
        SYNTAX      Integer32
        MAX-ACCESS  read-only
        STATUS      current
        DESCRIPTION
            "The index of the DHCP Server."
        ::= { topCcmtsDhcpExtensionalDevHelperEntry 1 }

topCcmtsDhcpExtensionalDevHelperIpAddr OBJECT-TYPE
        SYNTAX      IpAddress
        MAX-ACCESS  read-create
        STATUS      current
        DESCRIPTION
            "The IP address of the DHCP Server."
        ::= { topCcmtsDhcpExtensionalDevHelperEntry 2 }

topCcmtsDhcpExtensionalDevHelperStatus  OBJECT-TYPE
	SYNTAX          RowStatus
	 MAX-ACCESS      read-create
	 STATUS          current
	 DESCRIPTION
		"Controls and reflects the status of rows in this
		table.  Rows in this table may be created by either the
		create-and-go or create-and-wait paradigm.  There is no
		restriction on changing values in a row of this table
		while the row is active.

		The following objects MUST have valid values before this
		object can be set to active: topCcmtsDhcpExtensionalDevHelperIpAddr." 
	::= { topCcmtsDhcpExtensionalDevHelperEntry 3 } 
	
------------------------------------------
--topCcmtsDhcpExtensionalDevPacketVlanTable
--added at 2013-8-13
------------------------------------------
topCcmtsDhcpExtensionalDevPacketVlanTable OBJECT-TYPE
		SYNTAX      SEQUENCE OF TopCcmtsDhcpExtensionalDevPacketVlanEntry
        MAX-ACCESS  not-accessible
        STATUS      current
        DESCRIPTION
            "This Object describes extensional dev packet vlan on CCMTS."
        ::= { topCcmtsDhcpObject 12 }

topCcmtsDhcpExtensionalDevPacketVlanEntry OBJECT-TYPE
		SYNTAX      TopCcmtsDhcpExtensionalDevPacketVlanEntry
        MAX-ACCESS  not-accessible
        STATUS      current
        DESCRIPTION
            "This row of the table."
		INDEX { topCcmtsDhcpBundleInterface,
				topCcmtsDhcpExtensionalDeviceName}
        ::= { topCcmtsDhcpExtensionalDevPacketVlanTable 1 }

TopCcmtsDhcpExtensionalDevPacketVlanEntry ::=SEQUENCE {
	topCcmtsDhcpExtensionalDevTagVlan			INTEGER,
	topCcmtsDhcpExtensionalDevTagPriority		INTEGER,
	topCcmtsDhcpExtensionalDevPacketVlanStatus	RowStatus
}

topCcmtsDhcpExtensionalDevTagVlan OBJECT-TYPE
        SYNTAX      INTEGER (1..4094)
        MAX-ACCESS  read-create
        STATUS      current
        DESCRIPTION
            "Extensional device tag vlan"
        ::= { topCcmtsDhcpExtensionalDevPacketVlanEntry 1 }

topCcmtsDhcpExtensionalDevTagPriority OBJECT-TYPE
        SYNTAX      INTEGER (0..7)
	    MAX-ACCESS  read-create
        STATUS      current
        DESCRIPTION
            "Extensional device tag priority"
        ::= { topCcmtsDhcpExtensionalDevPacketVlanEntry 2 } 

topCcmtsDhcpExtensionalDevPacketVlanStatus OBJECT-TYPE
        SYNTAX      RowStatus
        MAX-ACCESS  read-create
        STATUS      current
        DESCRIPTION
		"Controls and reflects the status of rows in this
		table.  Rows in this table may be created by either the
		create-and-go or create-and-wait paradigm.  There is no
		restriction on changing values in a row of this table
		while the row is active."
		::= { topCcmtsDhcpExtensionalDevPacketVlanEntry 3 }

------------------------------------------
--topCcmtsExtensionalDevDhcpModeTable 
--added at 2013-8-13
------------------------------------------
topCcmtsExtensionalDevDhcpModeTable OBJECT-TYPE
		SYNTAX      SEQUENCE OF TopCcmtsExtensionalDevDhcpModeEntry
        MAX-ACCESS  not-accessible
        STATUS      current
        DESCRIPTION
            "This Object describes extensional dev dhcp mode on CCMTS."
        ::= { topCcmtsDhcpObject 13 } 
        
topCcmtsExtensionalDevDhcpModeEntry OBJECT-TYPE
		SYNTAX      TopCcmtsExtensionalDevDhcpModeEntry
        MAX-ACCESS  not-accessible
        STATUS      current
        DESCRIPTION
            "This Object describes the entry of the table."
		INDEX { topCcmtsExtensionalDevName }
        ::= { topCcmtsExtensionalDevDhcpModeTable 1 } 
        
TopCcmtsExtensionalDevDhcpModeEntry ::=SEQUENCE {
		topCcmtsExtensionalDevName	OCTET STRING,
		topCcmtsExtensionalDevDhcpMode INTEGER
	    }
	    
topCcmtsExtensionalDevName OBJECT-TYPE
        SYNTAX      OCTET STRING(SIZE(0..100))
        MAX-ACCESS  read-only
        STATUS      current
        DESCRIPTION
            "Device Name str."
        ::= { topCcmtsExtensionalDevDhcpModeEntry 1 } 

topCcmtsExtensionalDevDhcpMode OBJECT-TYPE
		SYNTAX	INTEGER {
			dhcp-snooping (1),
			dhcp-l2-relay (2),
			dhcp-l3-relay (3)
		}
		MAX-ACCESS read-write
    	STATUS current
    	DESCRIPTION
		"dhcp mode: 1 dhcp-snooping; 2 dhcp-l2-relay; 3 dhcp-l3-relay."
		DEFVAL { dhcp-snooping }
    ::= { topCcmtsExtensionalDevDhcpModeEntry 2 } 
 
------------------------------------------------     
--topCcmtsDhcpOptionObject
--add by wupeng for ccmts-9533 2016/01/14
------------------------------------------------
topCcmtsDhcpOptionObject OBJECT IDENTIFIER ::={ topCcmtsDhcpObject 14 }

topCcmtsDhcpCircuitIdPrefixValue  OBJECT-TYPE
    SYNTAX      DisplayString (SIZE (1..128))
    MAX-ACCESS read-write
    STATUS current
    DESCRIPTION
		"Support a configurable DHCPv4 option 82.1 and DHCPv6 option 18 identification value,at maximum 128 characters"
	::= { topCcmtsDhcpOptionObject 1 }

topCcmtsDhcpCircuitIdPrefixCmd   OBJECT-TYPE
    SYNTAX INTEGER {
			Active(1),
			Destory(2)
		   }
	
    MAX-ACCESS read-write
    STATUS current
    DESCRIPTION
		"Indicates the status of the rows in this table and can be used to destroy the specific row"
	DEFVAL          { 1 }
    ::= { topCcmtsDhcpOptionObject 2 }

----------------------------
--topCcmtsExtendsDhcpObject   
--end
--modified at 2013-4-19
----------------------------

		
topCcmtsNmAccessObject	OBJECT IDENTIFIER ::={ topCcmtsMibObject 4 }

topCcmtsNmAccessTable OBJECT-TYPE
    SYNTAX          SEQUENCE OF TopCcmtsNmAccessEntry 
    MAX-ACCESS      not-accessible
    STATUS          current
    DESCRIPTION
        "This table controls access to SNMP objects by network
        management stations.  If the table is empty, access to
        SNMP objects is unrestricted."
    ::= { topCcmtsNmAccessObject 1 }

topCcmtsNmAccessEntry OBJECT-TYPE
    SYNTAX          TopCcmtsNmAccessEntry
    MAX-ACCESS      not-accessible
    STATUS          current
    DESCRIPTION
        "An entry describing access to SNMP objects by a
        particular network management station.  An entry in
        this table is not readable unless the management station
        has read-write permission (either implicit if the table
        is empty, or explicit through an entry in this table).
        Entries are ordered by topCcmtsNmAccessIndex.  The first
        matching entry (e.g., matching IP address and community
        string) is used to derive access."
    INDEX           { topCcmtsNmAccessIndex } 
    ::= { topCcmtsNmAccessTable 1 }

TopCcmtsNmAccessEntry ::= SEQUENCE {
        topCcmtsNmAccessIndex       Integer32,
        topCcmtsNmAccessIp          IpAddress,
        topCcmtsNmAccessIpMask      IpAddress,
	topCcmtsNmAccessReadCommunity   OCTET STRING,
        topCcmtsNmAccessWriteCommunity   OCTET STRING,
        topCcmtsNmAccessControl     INTEGER,
        topCcmtsNmAccessStatus      RowStatus
}

topCcmtsNmAccessIndex OBJECT-TYPE
    SYNTAX          Integer32 (1..2147483647)
    MAX-ACCESS      not-accessible
    STATUS          current
    DESCRIPTION
        "Index used to order the application of access
        entries." 
    ::= { topCcmtsNmAccessEntry 1 }

topCcmtsNmAccessIp OBJECT-TYPE
    SYNTAX          IpAddress
    MAX-ACCESS      read-create
    STATUS          current
    DESCRIPTION
        "The IP address (or subnet) of the network management
        station.  The address 0.0.0.0 is defined to mean
        any Network Management Station (NMS).  If traps are
        enabled for this entry, then the value must be the
        address of a specific device.  Implementations MAY
        recognize 255.255.255.255 as equivalent to 0.0.0.0."
    DEFVAL          { '00000000'H } 
    ::= { topCcmtsNmAccessEntry 2 }

topCcmtsNmAccessIpMask OBJECT-TYPE
    SYNTAX          IpAddress
    MAX-ACCESS      read-create
    STATUS          current
    DESCRIPTION
        "The IP subnet mask of the network management stations.
        If traps are enabled for this entry, then the value must
        be 0.0.0.0.  Implementations MAY recognize
        255.255.255.255 as equivalent to 0.0.0.0."
    DEFVAL          { '00000000'H } 
    ::= { topCcmtsNmAccessEntry 3 }

topCcmtsNmAccessReadCommunity OBJECT-TYPE
    SYNTAX          OCTET STRING (SIZE  (0..32))
    MAX-ACCESS      read-create
    STATUS          current
    DESCRIPTION
        "The community string to be matched for read-access by this
        entry. "
    DEFVAL          { "public" } 
    ::= { topCcmtsNmAccessEntry 4 }

 topCcmtsNmAccessWriteCommunity OBJECT-TYPE
    SYNTAX          OCTET STRING (SIZE  (0..32))
    MAX-ACCESS      read-create
    STATUS          current
    DESCRIPTION
        "The community string to be matched for write-access by this
        entry. "
    DEFVAL          { "private" } 
    ::= { topCcmtsNmAccessEntry 5 }

topCcmtsNmAccessControl OBJECT-TYPE
    SYNTAX          INTEGER  {
                        none(1),
                        read(2),
                        readWrite(3),
                        roWithTraps(4),
                        rwWithTraps(5),
                        trapsOnly(6)
                    }
    MAX-ACCESS      read-create
    STATUS          current
    DESCRIPTION
        "Specifies the type of access allowed to this NMS.
        Setting this object to none(1) causes the table entry
        to be destroyed.  Read(2) allows access by 'get' and
        'get-next' PDUs.  ReadWrite(3) allows access by 'set' as
        well.  RoWithtraps(4), rwWithTraps(5), and trapsOnly(6)
        control distribution of Trap PDUs transmitted by this
        device."
    DEFVAL          { read } 
    ::= { topCcmtsNmAccessEntry 6 }

topCcmtsNmAccessStatus OBJECT-TYPE
    SYNTAX          RowStatus
    MAX-ACCESS      read-create
    STATUS          deprecated
    DESCRIPTION
        "Controls and reflects the status of rows in this
        table.  Rows in this table may be created by either the
        create-and-go or create-and-wait paradigm.  There is no
        restriction on changing values in a row of this table
        while the row is active.

        The following objects MUST have valid values before this
        object can be set to active: topCcmtsNmAccessIp,
        topCcmtsNmAccessStatus, topCcmtsNmAccessIpMask,
        topCcmtsNmAccessReadCommunity,topCcmtsNmAccessWriteCommunity,
	topCcmtsNmAccessControl." 
    ::= { topCcmtsNmAccessEntry 7 }

topCcmtsSoftwareObject	OBJECT IDENTIFIER ::={ topCcmtsMibObject 5 }

topCcmtsSfFileObject	OBJECT IDENTIFIER ::={ topCcmtsSoftwareObject 1 } 

topCcmtsSfFileTransferType OBJECT-TYPE
    SYNTAX          INTEGER  {
			kernel(1),
			rootfs(2),
			cmcapp(3),
			config(4),
			packimage(5),
			cmimage(6),
			cmDefConfg(7),
			cm30DefConfig(8),
			cmConfig(9)
			}
    MAX-ACCESS      read-write    
    STATUS          current
    DESCRIPTION
        "This object describes software type that will be loaded to 
        this ccmts or uploaded file to a ftp server.Only config(4)
        file can be uploaded.
        Kernel(1) means Linux kernel.
        Rootfs(2) means  DOL system.
        Cmcapp(3) means  CCMTS system.
        Config(4) means config file.
		packimage(5) means a pack may be comprised of kernel,rootfs,cmcapp,etc.
		Cmimage(6) means cable modem upgrade image file.
		cmDefConfg(7) means default cable modem config file.
		cm30DefConfig(8) means default cable modem 3.0 config file.
		cmConfig(9) means cable modem config file." 
    ::= { topCcmtsSfFileObject 1 }

topCcmtsSfFileServerIpAddr OBJECT-TYPE
	SYNTAX			IpAddress
	MAX-ACCESS		read-write
	STATUS			current
    DESCRIPTION
        "The ip address of the FTP server" 
    ::= { topCcmtsSfFileObject 2 }

topCcmtsSfFileFtpUserName OBJECT-TYPE
    SYNTAX          DisplayString (SIZE (0..50))
    MAX-ACCESS      read-write
    STATUS          current
    DESCRIPTION
        "The username of the FTP server" 
    ::= { topCcmtsSfFileObject 3 }

topCcmtsSfFileFtpUserPassword OBJECT-TYPE
    SYNTAX          DisplayString (SIZE (0..50))
    MAX-ACCESS      read-write
    STATUS          current
    DESCRIPTION
        "The password of the FTP server" 
    ::= { topCcmtsSfFileObject 4 }

topCcmtsSfFileSrcPath OBJECT-TYPE
    SYNTAX          DisplayString (SIZE (0..128))
    MAX-ACCESS      read-write
    STATUS          current
    DESCRIPTION
        "The file path on the FTP server" 
    ::= { topCcmtsSfFileObject 5 }

topCcmtsSfFileDestPath OBJECT-TYPE
    SYNTAX          DisplayString (SIZE (0..128))
    MAX-ACCESS      read-write
    STATUS          current
    DESCRIPTION
        "The file path on the ccmts " 
    ::= { topCcmtsSfFileObject 6 }

topCcmtsSfFileTransferAction OBJECT-TYPE
    SYNTAX          INTEGER  { 
			noOperation(0),
			load(1),
			upload(2)
			}
    MAX-ACCESS      read-write
    STATUS          current
    DESCRIPTION
        "This object is used to begin a ftp transfer between ccmts 
        and server.If set to load(1),ccmts begins to load file 
        indicated by topCcmtsSfFileTransferType and topCcmtsSfFileSrcPath 
        from ftp server indicated by topCcmtsSfFileServerIpAddr.
        If set to upload(2),ccmts begins to upload file to ftp server.
        And at this time the node topCcmtsSfFileTransferType must to 
        be set to Config(4).When read this object always return noOperation(0)." 
    ::= { topCcmtsSfFileObject 7 } 

topCcmtsSfFileTransferStatus OBJECT-TYPE
    SYNTAX          Integer32(0..100|200..209)
    MAX-ACCESS      read-only
    STATUS          current
    DESCRIPTION
        "This node is used to indicated the file transfer progress.
        0-100 means 0-100%.Other value means one error happens
        200 : a generic failure
        202 : download image failed
        203 : open image file failed
        204 : length of image file is invalid
        205 : check the magic of file failed
        206 : erase flash failed
        207 : write flash failed
        208 : CRC verify failed
        209 : decompress file failed" 
    ::= { topCcmtsSfFileObject 8 }    

topCcmtsSwTftpTransferObject		OBJECT IDENTIFIER ::={ topCcmtsSfFileObject 9 } 

topCcmtsSwTftpTransferFileType OBJECT-TYPE
    SYNTAX          INTEGER  {
			kernel(1),
			rootfs(2),
			cmcapp(3),
			config(4),
			packimage(5)
			}
    MAX-ACCESS      read-write    
    STATUS          current
    DESCRIPTION
        "This object describes software type that will be loaded to 
        this ccmts or uploaded file to a tftp server.Only config(4)
        file can be uploaded.
        Kernel(1) means Linux kernel.
        Rootfs(2) means  DOL system.
        Cmcapp(3) means  CCMTS system.
        Config(4) means config file.
	packimage(5) means a pack may be comprised of kernel,rootfs,cmcapp,etc." 
    ::= { topCcmtsSwTftpTransferObject 1 }

topCcmtsSwTftpTransferAction OBJECT-TYPE
    SYNTAX          INTEGER  { 
			noOperation(0),
			load(1),
			upload(2)
			}
    MAX-ACCESS      read-write
    STATUS          current
    DESCRIPTION
        "This object is used to begin a tftp transfer between ccmts 
        and server.If set to load(1),ccmts begins to load file indicated 
        by topCcmtsSwFileType and docsDevSwFilename from tftp server 
        indicated by docsDevSwServerAddressType and docsDevSwServerAddress.  
        If set to upload(2),ccmts begins to upload file to tftp server.
        And at this time the node topCcmtsSwTftpTransferFileType must to 
        be set to Config(4). Different from the FTP,this object use standard 
        mib to configure the TFTP server. So before you set this node,
        you must set the standard mib docsDevSoftware must firstly. " 
    ::= { topCcmtsSwTftpTransferObject 2 } 

topCcmtsSwTftpTransferProgress OBJECT-TYPE
    SYNTAX          Integer32(0..100|200..209)
    MAX-ACCESS      read-only
    STATUS          current
    DESCRIPTION
        "This node is used to indicated the file transfer progress.
        0-100 means 0-100%.Other value means one error happens.
        200 : a generic failure
        202 : download image failed
        203 : open image file failed
        204 : length of image file is invalid
        205 : check the magic of file failed
        206 : erase flash failed
        207 : write flash failed
        208 : CRC verify failed
        209 : decompress file failed" 
    ::= { topCcmtsSwTftpTransferObject 3 }
 
----------------------------------------------     
--topCcmtsSfFileInfoMgtTable
--added by lihuanyong at oct.6 2016
----------------------------------------------      
topCcmtsSfFileInfoMgtTable OBJECT-TYPE
	SYNTAX		SEQUENCE OF TopCcmtsSfFileInfoMgtEntry	
	MAX-ACCESS	not-accessible
	STATUS		current
	DESCRIPTION
		"record attributes of the files in ccmts file system."
	::={ topCcmtsSfFileObject 10 } 
	
topCcmtsSfFileInfoMgtEntry OBJECT-TYPE
	SYNTAX		TopCcmtsSfFileInfoMgtEntry
	MAX-ACCESS	not-accessible
	STATUS		current
	DESCRIPTION
		"the entry of topCcmtsSfFileInfoMgtTable."
	INDEX { topCcmtsSfFileType,
			topCcmtsSfFileName}
	::= { topCcmtsSfFileInfoMgtTable 1 }
	
TopCcmtsSfFileInfoMgtEntry ::=SEQUENCE{
	topCcmtsSfFileType	INTEGER,
	topCcmtsSfFileName	OCTET STRING,
	topCcmtsSfFileSize	INTEGER,
	topCcmtsSfFileDate 	Counter64,
	topCcmtsSfFileMgtAction INTEGER
	} 
	
topCcmtsSfFileType OBJECT-TYPE
	SYNTAX          INTEGER  {
			kernel(1),
			rootfs(2),
			cmcapp(3),
			config(4),
			packimage(5),
			cmimage(6),
			cmDefConfg(7),
			cm30DefConfig(8),
			cmConfig(9)
			}
	MAX-ACCESS	read-only
	STATUS		current
	DESCRIPTION
		"file type."
	::={ topCcmtsSfFileInfoMgtEntry 1 } 

topCcmtsSfFileName OBJECT-TYPE
	SYNTAX		OCTET STRING (SIZE (0..64))
	MAX-ACCESS	read-only
	STATUS		current
	DESCRIPTION
		"file name."
	::={ topCcmtsSfFileInfoMgtEntry 2 }  
	
topCcmtsSfFileSize OBJECT-TYPE
	SYNTAX		INTEGER
	MAX-ACCESS	read-only
	STATUS		current
	DESCRIPTION
		"file size."
	::={ topCcmtsSfFileInfoMgtEntry 3 }  
	
topCcmtsSfFileDate OBJECT-TYPE
	SYNTAX		Counter64
	MAX-ACCESS	read-only
	STATUS		current
	DESCRIPTION
		"The date of creating the file."
	::={ topCcmtsSfFileInfoMgtEntry 4 } 
	
topCcmtsSfFileMgtAction OBJECT-TYPE
	SYNTAX          INTEGER  {
			noOperation(1),
			erase(2)
			}
	MAX-ACCESS	read-write
	STATUS		current
	DESCRIPTION
		"The operation of erase the file."
	::={ topCcmtsSfFileInfoMgtEntry 5 }
	
topCcmtsSfFileTotalSize OBJECT-TYPE
	SYNTAX		INTEGER
	MAX-ACCESS	read-only
	STATUS		current
	DESCRIPTION
		"Total file size."
	::={ topCcmtsSfFileObject 11 } 

topCcmtsSfUpdateObject	OBJECT IDENTIFIER ::={ topCcmtsSoftwareObject 2 }

topCcmtsSfUpdatePath OBJECT-TYPE
    SYNTAX          DisplayString
    MAX-ACCESS      read-write
    STATUS          current
    DESCRIPTION
        "" 
    ::= { topCcmtsSfUpdateObject 1 }

topCcmtsSfUpdateReBootConf OBJECT-TYPE
    SYNTAX           INTEGER  {
                        nextReBoot(1),
			auto(2),
			timing(3)
                    }
    MAX-ACCESS      read-write
    STATUS          current
    DESCRIPTION
        "" 
    ::= { topCcmtsSfUpdateObject 2 }

topCcmtsSfUpdateReBootTime OBJECT-TYPE
    SYNTAX          TimeTicks
    MAX-ACCESS      read-write
    STATUS          current
    DESCRIPTION
        "" 
    ::= { topCcmtsSfUpdateObject 3 }

topCcmtsSfUpdateStatus OBJECT-TYPE
    SYNTAX           INTEGER  {
                        idle(1),
			inProgress(2),
			success(3),
			failure(4)
                    }
    MAX-ACCESS      read-write
    STATUS          current
    DESCRIPTION
        "" 
    ::= { topCcmtsSfUpdateObject 4 }

-------------------------------------------------------------------
--topCcmtsSyslogObject
-- added at 2012-8-29
-------------------------------------------------------------------
topCcmtsSyslogObject	OBJECT IDENTIFIER ::={ topCcmtsMibObject 6 }

topCcmtsSyslogServerTable OBJECT-TYPE
    SYNTAX          SEQUENCE OF TopCcmtsSyslogServerEntry 
    MAX-ACCESS      not-accessible
    STATUS          current
    DESCRIPTION
        "This Table contains Syslog Server IP addresses."
    ::= { topCcmtsSyslogObject 1 }

topCcmtsSyslogServerEntry OBJECT-TYPE
    SYNTAX          TopCcmtsSyslogServerEntry 
    MAX-ACCESS      not-accessible
    STATUS          current
    DESCRIPTION
        "This entry descripts a syslog server."
    INDEX	{topCcmtsSyslogServerIndex}
    ::= { topCcmtsSyslogServerTable 1 }

TopCcmtsSyslogServerEntry ::= SEQUENCE {
        topCcmtsSyslogServerIndex       Integer32,
		topCcmtsSyslogServerIpAddr      IpAddress,    
		topCcmtsSyslogServerStatus      INTEGER ,   
		topCcmtsSyslogServerIpPort  	Integer32,
		topCcmtsSyslogServerIpv6Addr    InetAddressIPv6,
		topCcmtsSyslogFacility          Integer32  
}

topCcmtsSyslogServerIndex  OBJECT-TYPE
    SYNTAX          Integer32
    MAX-ACCESS      not-accessible
    STATUS          current
    DESCRIPTION
        "Index of the Table." 
    ::= { topCcmtsSyslogServerEntry 1 }

topCcmtsSyslogServerIpAddr OBJECT-TYPE
    SYNTAX          IpAddress
    MAX-ACCESS      read-create
    STATUS          current
    DESCRIPTION
        "The syslog server's IP address." 
    ::= { topCcmtsSyslogServerEntry 2 }    
    
topCcmtsSyslogServerStatus OBJECT-TYPE
    SYNTAX           INTEGER  {   
    					active(1),
						create(4),
						destory(6)
                    }
    MAX-ACCESS      read-create
    STATUS          current
    DESCRIPTION
        "Status of the entry, when read always return active(1).
	when set to create(4),add 1 entry to the table.when set to
	drop(6),delete this entry." 
    ::= { topCcmtsSyslogServerEntry 3 }  
    
topCcmtsSyslogServerIpPort OBJECT-TYPE
    SYNTAX          Integer32
    MAX-ACCESS      read-create
    STATUS          current
    DESCRIPTION
        "The syslog server's IP port." 
    ::= { topCcmtsSyslogServerEntry 4 }   

topCcmtsSyslogServerIpv6Addr OBJECT-TYPE
	SYNTAX 		InetAddressIPv6
	MAX-ACCESS 	read-create
	STATUS 		current
	DESCRIPTION
		"The syslog ip address for v6."
	::= { topCcmtsSyslogServerEntry 5 }  
    
topCcmtsSyslogFacility OBJECT-TYPE
    SYNTAX          Integer32
    MAX-ACCESS      read-write
    STATUS          current
    DESCRIPTION
        "The syslog server's IP facility code.
        A facility code is used to specify the program type that is handling the message.
        Messages  (events) with different facilities may be handled differently. 
        The list of facilities available is defined by RFC3164.  
        Typically for CMTS, one facility code is used. 
        Default facility code is local0." 
    ::= { topCcmtsSyslogServerEntry 6 }  

------------------------------------------------------------------------------
--  topCcmtsTrapServerTable
--  added at 2013-4-17
--  
------------------------------------------------------------------------------
topCcmtsTrapServerTable OBJECT-TYPE
    SYNTAX          SEQUENCE OF TopCcmtsTrapServerEntry 
    MAX-ACCESS      not-accessible
    STATUS          current
    DESCRIPTION
        "This Table contains trap Server IP addresses."
    ::= { topCcmtsSyslogObject 2 }

topCcmtsTrapServerEntry OBJECT-TYPE
    SYNTAX          TopCcmtsTrapServerEntry 
    MAX-ACCESS      not-accessible
    STATUS          current
    DESCRIPTION
        "This entry descripts a trap server."
    INDEX	{topCcmtsTrapServerIndex}
    ::= { topCcmtsTrapServerTable 1 }

TopCcmtsTrapServerEntry ::= SEQUENCE {
        topCcmtsTrapServerIndex       Integer32,
		topCcmtsTrapServerIpAddr      IpAddress,  
        topCcmtsTrapServerStatus      INTEGER,
        topCcmtsTrapServerIpPort      Integer32,  
		topCcmtsTrapCommunityName     OCTET STRING,      
		topCcmtsTrapServerIpv6Addr    InetAddressIPv6
}

topCcmtsTrapServerIndex  OBJECT-TYPE
    SYNTAX          Integer32
    MAX-ACCESS      not-accessible
    STATUS          current
    DESCRIPTION
        "Index of the Table." 
    ::= { topCcmtsTrapServerEntry 1 }

topCcmtsTrapServerIpAddr OBJECT-TYPE
    SYNTAX          IpAddress
    MAX-ACCESS      read-create
    STATUS          current
    DESCRIPTION
        "The trap server's IP address." 
    ::= { topCcmtsTrapServerEntry 2 } 
   
topCcmtsTrapServerStatus OBJECT-TYPE
    SYNTAX           INTEGER  {
   					    active(1),
    					create(4),
						destory(6)
                    }
    MAX-ACCESS      read-create
    STATUS          current
    DESCRIPTION
        "Status of the entry, when read always return active(1).
	when set to create(4),add 1 entry to the table.when set to
	drop(6),delete this entry." 
    ::= { topCcmtsTrapServerEntry 3 }  
    
topCcmtsTrapServerIpPort OBJECT-TYPE
    SYNTAX          Integer32 (1..65535)
    MAX-ACCESS      read-create
    STATUS          current
    DESCRIPTION
        "The port of trap server." 
    ::= { topCcmtsTrapServerEntry 4 }   
    
topCcmtsTrapCommunityName OBJECT-TYPE
    SYNTAX 		OCTET STRING (SIZE (1..31))
    MAX-ACCESS 	read-create
    STATUS 		current
    DESCRIPTION
      	"The trap community name."
    ::= { topCcmtsTrapServerEntry 5 }       

topCcmtsTrapServerIpv6Addr OBJECT-TYPE
	SYNTAX 		InetAddressIPv6
	MAX-ACCESS 	read-create
	STATUS 		current
	DESCRIPTION
		"The trap server's ip for v6."
	::= { topCcmtsTrapServerEntry 6 }  
    
------------------------------------------------------------------------------
--  topCcmtsSyslogEvtLvlTable
--  added at 2013-4-22
--  
------------------------------------------------------------------------------
topCcmtsSyslogEvtLvlTable OBJECT-TYPE
    SYNTAX          SEQUENCE OF TopCcmtSyslogEvtLvlEntry 
    MAX-ACCESS      not-accessible
    STATUS          current
    DESCRIPTION
        "This Table contains event id - level entry."
    ::= { topCcmtsSyslogObject 3 }

topCcmtSyslogEvtLvlEntry OBJECT-TYPE
    SYNTAX          TopCcmtSyslogEvtLvlEntry 
    MAX-ACCESS      not-accessible
    STATUS          current
    DESCRIPTION
        "This entry descripts event id - level."
    INDEX	{topCcmtsSyslogEvtId}
    ::= { topCcmtsSyslogEvtLvlTable 1 }

TopCcmtSyslogEvtLvlEntry ::= SEQUENCE { 
        topCcmtsSyslogEvtId       Unsigned32,
		topCcmtsSyslogEvtLvl      INTEGER}   

topCcmtsSyslogEvtId OBJECT-TYPE
    SYNTAX          Unsigned32 (1..4294967295)
    MAX-ACCESS      read-create
    STATUS          current
    DESCRIPTION
        "The event id." 
    ::= { topCcmtSyslogEvtLvlEntry 1 }    
    
topCcmtsSyslogEvtLvl OBJECT-TYPE
    SYNTAX          INTEGER { 
    					default(0),
    				 	emergency(1),
    				 	alert(2),
    				 	critical(3),
    				 	error(4),
    				 	warning(5),
    				 	notification(6),
    				 	informational(7),
    				 	debug(8)    				
    				 	}
    MAX-ACCESS      read-create
    STATUS          current
    DESCRIPTION
        "The event level." 
    ::= { topCcmtSyslogEvtLvlEntry 2 }    
------------------------------------------------------------------------------
--  topCcmtsSyslogSwitchTable
--  added at 2012-4-23
--  
------------------------------------------------------------------------------
topCcmtsSyslogSwitchTable OBJECT-TYPE
    SYNTAX          SEQUENCE OF TopCcmtSyslogSwitchEntry 
    MAX-ACCESS      not-accessible
    STATUS          current
    DESCRIPTION
        "This Table contains the log switch of every pon."
    ::= { topCcmtsSyslogObject 4 }

topCcmtSyslogSwitchEntry OBJECT-TYPE
    SYNTAX          TopCcmtSyslogSwitchEntry 
    MAX-ACCESS      not-accessible
    STATUS          current
    DESCRIPTION
        "This entry descripts the log switch of a pon."
    INDEX	{topCcmtsSyslogSlotNum}
    ::= { topCcmtsSyslogSwitchTable 1 }

TopCcmtSyslogSwitchEntry ::= SEQUENCE {
        topCcmtsSyslogSlotNum       INTEGER,
		topCcmtsSyslogPonSwitch      INTEGER
}

topCcmtsSyslogSlotNum OBJECT-TYPE
    SYNTAX          INTEGER (1..18)
    MAX-ACCESS      read-create
    STATUS          current
    DESCRIPTION
        "The slot id." 
    ::= { topCcmtSyslogSwitchEntry 1 } 
    
topCcmtsSyslogPonSwitch OBJECT-TYPE
    SYNTAX          INTEGER (0..1)
    MAX-ACCESS      read-create
    STATUS          current
    DESCRIPTION
        "The pon log switch." 
    ::= { topCcmtSyslogSwitchEntry 2 }  

------------------------------------------------------------------------------
--  the other leaf nodes in the syslog object
--  added at 2012-8-27  
------------------------------------------------------------------------------
topCcmtsSyslogMaxnum OBJECT-TYPE
    SYNTAX          INTEGER (10..10000)
    MAX-ACCESS      read-write
    STATUS          current
    DESCRIPTION
        "The max log number allowed to stored." 
    ::= { topCcmtsSyslogObject 5 }
    
topCcmtsSyslogSwitch OBJECT-TYPE
    SYNTAX          INTEGER {
    					off(0),
    					on(1)
    					}
    MAX-ACCESS      read-write
    STATUS          current
    DESCRIPTION
        "The event log switch." 
    ::= { topCcmtsSyslogObject 6 }

topCcmtsSyslogFlash OBJECT-TYPE
    SYNTAX          INTEGER { 
    					emergency(1),
    				 	alert(2),
    				 	critical(3),
    				 	error(4),
    				 	warning(5),
    				 	notification(6),
    				 	informational(7),
    				 	debug(8), 
    				 	none(28)
    					}
    MAX-ACCESS      read-write
    STATUS          current
    DESCRIPTION
        "The event level recorded in flash." 
    ::= { topCcmtsSyslogObject 7 }   
 
topCcmtsSyslogMemory OBJECT-TYPE
    SYNTAX          INTEGER { 
    					emergency(1),
    				 	alert(2),
    				 	critical(3),
    				 	error(4),
    				 	warning(5),
    				 	notification(6),
    				 	informational(7),
    				 	debug(8), 
    				 	none(28)
    					}
    MAX-ACCESS      read-write
    STATUS          current
    DESCRIPTION
        "The event level recorded in memory." 
    ::= { topCcmtsSyslogObject 8 }    
    
topCcmtsSysloglogServer OBJECT-TYPE
    SYNTAX          INTEGER { 
    					emergency(1),
    				 	alert(2),
    				 	critical(3),
    				 	error(4),
    				 	warning(5),
    				 	notification(6),
    				 	informational(7),
    				 	debug(8), 
    				 	none(28)
    					}
    MAX-ACCESS      read-write
    STATUS          current
    DESCRIPTION
        "The event level recorded in log server." 
    ::= { topCcmtsSyslogObject 9 }    
    
 topCcmtsSyslogTrapServer OBJECT-TYPE
    SYNTAX          INTEGER { 
    					emergency(1),
    				 	alert(2),
    				 	critical(3),
    				 	error(4),
    				 	warning(5),
    				 	notification(6),
    				 	informational(7),
    				 	debug(8), 
    				 	none(28)
    					}
    MAX-ACCESS      read-write
    STATUS          current
    DESCRIPTION
        "The event level recorded in trap server." 
    ::= { topCcmtsSyslogObject 10 }    
    
 topCcmtsSyslogTrotMode OBJECT-TYPE
    SYNTAX          INTEGER { 
    					unconstrained(1),
    				 	maintainBelowThreshold(2),
    				 	stopAtThreshold(3),
    				 	inhibited(4)    					
    				 	}
    MAX-ACCESS      read-write
    STATUS          current
    DESCRIPTION
        "The throttle mode." 
    ::= { topCcmtsSyslogObject 11 }
    
topCcmtsSyslogTrotTrhd OBJECT-TYPE
    SYNTAX          Unsigned32(0..4294967295)
    MAX-ACCESS      read-write
    STATUS          current
    DESCRIPTION
        "The throttle threshold." 
    ::= { topCcmtsSyslogObject 12 }

topCcmtsSyslogTrotInvl OBJECT-TYPE
    SYNTAX          INTEGER (1..2147483647)
    MAX-ACCESS      read-write
    STATUS          current
    DESCRIPTION
        "The throttle interval." 
    ::= { topCcmtsSyslogObject 13 }  
    
------------------------------------------------------------------------------
--  topCcmtsAlarmTable
--  added at 2015-6-23
--  
------------------------------------------------------------------------------
topCcmtsAlarmTable OBJECT-TYPE
    SYNTAX          SEQUENCE OF TopCcmtAlarmTableEntry 
    MAX-ACCESS      not-accessible
    STATUS          current
    DESCRIPTION
        "This Table contains alarm table."
    ::= { topCcmtsSyslogObject 14 }

topCcmtAlarmTableEntry OBJECT-TYPE
    SYNTAX          TopCcmtAlarmTableEntry 
    MAX-ACCESS      not-accessible
    STATUS          current
    DESCRIPTION
        "This entry descripts the alarm table."
    INDEX	{topCcmtsAlarmTableSeq}
    ::= { topCcmtsAlarmTable 1 }

TopCcmtAlarmTableEntry ::= SEQUENCE {
        topCcmtsAlarmTableSeq          INTEGER,
		topCcmtsAlarmId                INTEGER,
		topCcmtsAlarmLevel             INTEGER,
		topCcmtsDescription            OCTET STRING,
		topCcmtsAlarmTime              INTEGER
}

topCcmtsAlarmTableSeq OBJECT-TYPE
    SYNTAX          INTEGER
    MAX-ACCESS      read-only
    STATUS          current
    DESCRIPTION
        "The alarm sequence number." 
    ::= { topCcmtAlarmTableEntry 1 } 
    
topCcmtsAlarmId OBJECT-TYPE
    SYNTAX          INTEGER
    MAX-ACCESS      read-only
    STATUS          current
    DESCRIPTION
        "The alarm id." 
    ::= { topCcmtAlarmTableEntry 2 }          
    
topCcmtsAlarmLevel OBJECT-TYPE
    SYNTAX          INTEGER{ 
    					emergency(1),
    				 	alert(2),
    				 	critical(3),
    				 	error(4),
    				 	warning(5),
    				 	notice(6),
    				 	information(7),
    				 	debug(8)					
    				 	}

    MAX-ACCESS      read-only
    STATUS          current
    DESCRIPTION
        "The alarm level." 
    ::= { topCcmtAlarmTableEntry 3 }    
    
topCcmtsDescription OBJECT-TYPE
    SYNTAX          OCTET STRING
    MAX-ACCESS      read-only
    STATUS          current
    DESCRIPTION
        "The alarm description." 
    ::= { topCcmtAlarmTableEntry 4 }   
    
topCcmtsAlarmTime OBJECT-TYPE
    SYNTAX          INTEGER
    MAX-ACCESS      read-only
    STATUS          current
    DESCRIPTION
        "The alarm time stamp." 
    ::= { topCcmtAlarmTableEntry 5 } 

      
------------------------------------------------------------------------------
--  topCcmtsVlanCfgObject
--  added at 2012-8-27
--  
------------------------------------------------------------------------------
    
topCcmtsVlanCfgObject	OBJECT IDENTIFIER ::={ topCcmtsMibObject 7 } 
topCcmtsVlanPrimaryIfObject		OBJECT IDENTIFIER ::={topCcmtsVlanCfgObject 1 }
 
topCcmtsVlanPrimaryInterface OBJECT-TYPE
    SYNTAX 		Integer32
    MAX-ACCESS 	read-write
    STATUS 		current
    DESCRIPTION
      	" Primary interface's VLAN ID."
    ::= { topCcmtsVlanPrimaryIfObject 1 }
    
topCcmtsVlanPrimaryDefaultRoute OBJECT-TYPE
	SYNTAX		IpAddress
	MAX-ACCESS	read-write
	STATUS		current
	DESCRIPTION
		"Default Route."  
	::={ topCcmtsVlanPrimaryIfObject 2 }     
	
topCcmtsVlanPrimaryDefaultIPAddr OBJECT-TYPE
	SYNTAX		IpAddress
	MAX-ACCESS	read-write
	STATUS		current
	DESCRIPTION
		"Default IP address."  
	::={ topCcmtsVlanPrimaryIfObject 3}    
	
topCcmtsVlanPrimaryDefaultIPMask OBJECT-TYPE
	SYNTAX		IpAddress
	MAX-ACCESS	read-write
	STATUS		current
	DESCRIPTION
		"Default IP mask."  
	::={ topCcmtsVlanPrimaryIfObject 4}

topCcmtsVlanConfigTable OBJECT-TYPE
    SYNTAX SEQUENCE OF TopCcmtsVlanConfigEntry
    MAX-ACCESS not-accessible
    STATUS current
    DESCRIPTION
      	"CCMTS VLAN port config table."
    ::= { topCcmtsVlanCfgObject 2 }

topCcmtsVlanConfigEntry OBJECT-TYPE
    SYNTAX TopCcmtsVlanConfigEntry
    MAX-ACCESS not-accessible
    STATUS current
    DESCRIPTION
      	" "
    INDEX { topCcmtsVlanIndex}
    ::= { topCcmtsVlanConfigTable 1 }

TopCcmtsVlanConfigEntry ::= SEQUENCE {
      topCcmtsVlanIndex				INTEGER,
      topCcmtsVlanName      	    OCTET STRING,
      topCcmtsTaggedPort          	OCTET STRING,
      topCcmtsUntaggedPort          OCTET STRING,   
      topCcmtsVlanFloodMode			INTEGER,
      topCcmtsVlanStatus          	RowStatus
     }

topCcmtsVlanIndex  OBJECT-TYPE
    SYNTAX 		INTEGER(0..4094)
    MAX-ACCESS 	not-accessible
    STATUS 		current
    DESCRIPTION
      	"Vlan Index"
    ::= { topCcmtsVlanConfigEntry 1 }

topCcmtsVlanName OBJECT-TYPE
    SYNTAX 		OCTET STRING (SIZE (0..128))
    MAX-ACCESS 	read-create
    STATUS 		current
    DESCRIPTION
      	"OLT VLAN name"
    ::= { topCcmtsVlanConfigEntry 2 }

topCcmtsTaggedPort OBJECT-TYPE
    SYNTAX 		OCTET STRING
    MAX-ACCESS 	read-create
    STATUS 		current
    DESCRIPTION
	      "
	      Vlan contains tagged SNI in ccmts.
	      It is presented by member port list. Each member port is identified
	      by 3-byte format. The actual length of
	      this string depends of the number of member ports in the port list.
	      The relationship is:
	      Length of the string = 3 * (NUM of member ports)
	      For example, if port 1/2 and 2/3 is the member ports,
	      then this object will be presented as:
	      01 02 00 02 03 00
	      "
    ::= { topCcmtsVlanConfigEntry 3 }

topCcmtsUntaggedPort OBJECT-TYPE
    SYNTAX 		OCTET STRING
    MAX-ACCESS 	read-create
    STATUS 		current
    DESCRIPTION
	      "Vlan contains Untagged SNI in ccmts.
	      It is presented by member port list. Each member port is identified
	      by 3-byte format. The actual length of
	      this string depends of the number of member ports in the port list.
	      The relationship is:
	      Length of the string = 3 * (NUM of member ports)
	      For example, if device 1, port 1/2 and 2/3 is the member ports,
	      then this object will be presented as:
	      01 02 00 02 03 00
	      "
    ::= { topCcmtsVlanConfigEntry 4 }
      
topCcmtsVlanFloodMode OBJECT-TYPE
    SYNTAX 		INTEGER{
    				all(1),
    				unknown(2),
    				none(3)			
    			}
    MAX-ACCESS 	read-create
    STATUS 		current
    DESCRIPTION
      	"CCMTS vlan multicast flood mode
 		all(1):all package flood
 		unkonw(2):unknown package flood
 		none(3): no package flood"
    ::= { topCcmtsVlanConfigEntry 5 }

topCcmtsVlanStatus OBJECT-TYPE
    SYNTAX 		RowStatus
    MAX-ACCESS 	read-create
    STATUS 		current
    DESCRIPTION
      	"The rowstatus of this table. It will be active(1) when you get."
    ::= { topCcmtsVlanConfigEntry 6 }

topCcmtsVifPriIpTable OBJECT-TYPE
	SYNTAX 		SEQUENCE OF TopCcmtsVifPriIpEntry
	MAX-ACCESS 	not-accessible
	STATUS 		current
	DESCRIPTION
		"OLT VIF primary ip table."
	::= { topCcmtsVlanCfgObject 3 }

topCcmtsVifPriIpEntry OBJECT-TYPE
	SYNTAX 		TopCcmtsVifPriIpEntry
	MAX-ACCESS 	not-accessible
	STATUS 		current
	DESCRIPTION
		"OLT VIF primary ip entry."
	INDEX { topCcmtsVifPriIpVlanId }
	::= { topCcmtsVifPriIpTable 1 }
			
TopCcmtsVifPriIpEntry ::=SEQUENCE { 
		topCcmtsVifPriIpVlanId		INTEGER,
		topCcmtsVifPriIpAddr		IpAddress,
		topCcmtsVifPriIpMask		IpAddress,
		topCcmtsVifPriIpStatus		RowStatus
	 }
			 
topCcmtsVifPriIpVlanId OBJECT-TYPE
	SYNTAX 		INTEGER (0..4094)
	MAX-ACCESS 	not-accessible
	STATUS 		current
	DESCRIPTION
		"VIF primary ip ,vlan index from 0 to 4094."
	::= { topCcmtsVifPriIpEntry 1 }
		
topCcmtsVifPriIpAddr OBJECT-TYPE
	SYNTAX 		IpAddress
	MAX-ACCESS 	read-create
	STATUS 		current
	DESCRIPTION
		"vif primary ip address."
	::= { topCcmtsVifPriIpEntry 2 }
		
topCcmtsVifPriIpMask OBJECT-TYPE
	SYNTAX 		IpAddress
	MAX-ACCESS 	read-create
	STATUS 		current
	DESCRIPTION
		"vif primary ip mask."
	::= { topCcmtsVifPriIpEntry 3 }
		
topCcmtsVifPriIpStatus OBJECT-TYPE
	SYNTAX 		RowStatus
	MAX-ACCESS 	read-create
	STATUS 		current
	DESCRIPTION
		"The rowstatus of this table. It will be active(1) when you get."
	::= { topCcmtsVifPriIpEntry 4 }
		
topCcmtsVifSubIpTable OBJECT-TYPE
	SYNTAX 		SEQUENCE OF TopCcmtsVifSubIpEntry
	MAX-ACCESS 	not-accessible
	STATUS 		current
	DESCRIPTION
		"OLT VIF sub IP table"
	::= { topCcmtsVlanCfgObject 4 }
	
topCcmtsVifSubIpEntry OBJECT-TYPE
	SYNTAX 		TopCcmtsVifSubIpEntry
	MAX-ACCESS 	not-accessible
	STATUS 		current
	DESCRIPTION
		"OLT VIF sub IP entry."
	INDEX { topCcmtsVifSubIpVlanIdx, topCcmtsVifSubIpSeqIdx }
	::= { topCcmtsVifSubIpTable 1 }
		
TopCcmtsVifSubIpEntry ::=	SEQUENCE { 
		topCcmtsVifSubIpVlanIdx		INTEGER,
		topCcmtsVifSubIpSeqIdx		INTEGER,
		topCcmtsVifSubIpAddr		IpAddress,
		topCcmtsVifSubIpMask		IpAddress,
		topCcmtsVifSubIpStatus		RowStatus
	 }
		 
topCcmtsVifSubIpVlanIdx OBJECT-TYPE
	SYNTAX 		INTEGER (0..4094)
	MAX-ACCESS 	not-accessible
	STATUS 		current
	DESCRIPTION
		"VIF sub ip ,vlan index from 0 to 4094 ."
	::= { topCcmtsVifSubIpEntry 1 }
	
topCcmtsVifSubIpSeqIdx OBJECT-TYPE
	SYNTAX 		INTEGER (0..62)
	MAX-ACCESS 	not-accessible
	STATUS 		current
	DESCRIPTION
		"VIF sub ip,  sequence index from 0 to 62."
	::= { topCcmtsVifSubIpEntry 2 }
	
topCcmtsVifSubIpAddr OBJECT-TYPE
	SYNTAX 		IpAddress
	MAX-ACCESS 	read-create
	STATUS 		current
	DESCRIPTION
		"VIF sub IP address."
	::= { topCcmtsVifSubIpEntry 3 }
	
topCcmtsVifSubIpMask OBJECT-TYPE
	SYNTAX 		IpAddress
	MAX-ACCESS 	read-create
	STATUS 		current
	DESCRIPTION
		"vif sub ip mask."
	::= { topCcmtsVifSubIpEntry 4 }
	
topCcmtsVifSubIpStatus OBJECT-TYPE
	SYNTAX 		RowStatus
	MAX-ACCESS 	read-create
	STATUS 		current
	DESCRIPTION
		"The rowstatus of this table. It will be active(1) when you get."
	::= { topCcmtsVifSubIpEntry 5 } 
	
topCcmtsVlanDhcpAllocTable OBJECT-TYPE
	SYNTAX		SEQUENCE OF TopCcmtsVlanDhcpAllocEntry
	MAX-ACCESS	not-accessible
	STATUS		current
	DESCRIPTION
			""
	::={topCcmtsVlanCfgObject 5}

topCcmtsVlanDhcpAllocEntry OBJECT-TYPE
	SYNTAX		TopCcmtsVlanDhcpAllocEntry
	MAX-ACCESS	not-accessible
	STATUS		current
	DESCRIPTION
			""        
	INDEX	{topCcmtsVlanIndex}
	::={topCcmtsVlanDhcpAllocTable 1} 
	
TopCcmtsVlanDhcpAllocEntry ::=SEQUENCE{
 	topCcmtsVlanDhcpAlloc			INTEGER,
 	topCcmtsVlanDhcpAllocOption60	OCTET STRING,
 	topCcmtsVlanDhcpAllocIpAddr		IpAddress,
 	topCcmtsVlanDhcpAllocIpMask		IpAddress		
}

topCcmtsVlanDhcpAlloc OBJECT-TYPE
	SYNTAX		INTEGER{
						enable(1),
						disable(2)
				} 
	MAX-ACCESS	read-create
	STATUS		current
	DESCRIPTION
		"This object is used to get ipaddress from DHCP
		Server for the vlan identified by topCcmtsVifPriIpVlanId."
	::={topCcmtsVlanDhcpAllocEntry 1}

topCcmtsVlanDhcpAllocOption60 OBJECT-TYPE
	SYNTAX		OCTET STRING(SIZE(0..128)) 
	MAX-ACCESS	read-create
	STATUS		current
	DESCRIPTION
		"This object describes the option60 field'String used
		in DHCP request."
	::={topCcmtsVlanDhcpAllocEntry 2}    
	
topCcmtsVlanDhcpAllocIpAddr OBJECT-TYPE
	SYNTAX 		IpAddress
	MAX-ACCESS 	read-only
	STATUS 		current
	DESCRIPTION
		"VIF DHCP alloc IP address."
	::= { topCcmtsVlanDhcpAllocEntry 3 }
	
topCcmtsVlanDhcpAllocIpMask OBJECT-TYPE
	SYNTAX 		IpAddress
	MAX-ACCESS 	read-only
	STATUS 		current
	DESCRIPTION
		"DHCP alloc IP mask."
	::= { topCcmtsVlanDhcpAllocEntry 4 }   
	
topCcmtsIpv6PrivateTable OBJECT-TYPE
	SYNTAX		SEQUENCE OF TopCcmtsIpv6PrivateEntry
	MAX-ACCESS	not-accessible
	STATUS		current
	DESCRIPTION
			""
	::={topCcmtsVlanCfgObject 6}     
	
topCcmtsIpv6PrivateEntry OBJECT-TYPE
	SYNTAX		TopCcmtsIpv6PrivateEntry
	MAX-ACCESS	not-accessible
	STATUS		current
	DESCRIPTION
			""        
	INDEX	{topCcmtsIpv6VlanId,topCcmtsIpv6Sequence}
	::={topCcmtsIpv6PrivateTable 1} 

TopCcmtsIpv6PrivateEntry ::=SEQUENCE{
 	topCcmtsIpv6VlanId			INTEGER,
 	topCcmtsIpv6Sequence		INTEGER,
 	topCcmtsIpv6Address			OCTET STRING,
 	topCcmtsIpv6PrxLength       INTEGER,
  	topCcmtsIpv6Operate         INTEGER,
 	topCcmtsIpv6RowStatus       RowStatus		
}           

topCcmtsIpv6VlanId OBJECT-TYPE
	SYNTAX		INTEGER(0..4094) 
	MAX-ACCESS	read-only
	STATUS		current
	DESCRIPTION
		"The vlanId which this ipv6 address belongs."
	::={topCcmtsIpv6PrivateEntry 1}          

topCcmtsIpv6Sequence OBJECT-TYPE
	SYNTAX		INTEGER(0..10) 
	MAX-ACCESS	read-only
	STATUS		current
	DESCRIPTION
		"The sequence number of ipv6 address in the vlan."
	::={topCcmtsIpv6PrivateEntry 2}        
	
topCcmtsIpv6Address OBJECT-TYPE
	SYNTAX		OCTET STRING(SIZE(2..39))
	MAX-ACCESS	read-write
	STATUS		current
	DESCRIPTION
		"The ipv6 address."
	::={topCcmtsIpv6PrivateEntry 3}       
	
topCcmtsIpv6PrxLength OBJECT-TYPE
	SYNTAX		INTEGER(0..128)
	MAX-ACCESS	read-write
	STATUS		current
	DESCRIPTION
		"The prefix of ipv6 address."
	::={topCcmtsIpv6PrivateEntry 4}        

topCcmtsIpv6Operate OBJECT-TYPE
	SYNTAX		INTEGER{any(0),global(1),eui(2),linklocal(3),linklocal_auto(4)}
	MAX-ACCESS	read-write
	STATUS		current
	DESCRIPTION
		"The operate type, any means config any ipv6 address,
		the agent will not check the type of the ipv6 address.
		Global means the ipv6 address we configured is global unicast 
		address.Eui means the ipv6 address will be generated automatically by
		the agent through eui-64.Linklocal means the ipv6 address is linklocal address"
	::={topCcmtsIpv6PrivateEntry 5}  

topCcmtsIpv6RowStatus OBJECT-TYPE
	SYNTAX		RowStatus
	MAX-ACCESS	read-write
	STATUS		current
	DESCRIPTION
		"Rowstatus of this table."
	::={topCcmtsIpv6PrivateEntry 6}   

topCcmtsVlanDhcpv6AllocTable OBJECT-TYPE
        SYNTAX          SEQUENCE OF TopCcmtsVlanDhcpv6AllocEntry
        MAX-ACCESS      not-accessible
        STATUS          current
        DESCRIPTION
                        ""
        ::={topCcmtsVlanCfgObject 7}

topCcmtsVlanDhcpv6AllocEntry OBJECT-TYPE
        SYNTAX          TopCcmtsVlanDhcpv6AllocEntry
        MAX-ACCESS      not-accessible
        STATUS          current
        DESCRIPTION
                        ""        
        INDEX   {topCcmtsVlanIndex}
        ::={topCcmtsVlanDhcpv6AllocTable 1} 

TopCcmtsVlanDhcpv6AllocEntry ::=SEQUENCE{
        topCcmtsVlanDhcpv6Alloc                 INTEGER,
        topCcmtsVlanDhcpv6AllocOption16         OCTET STRING,
        topCcmtsVlanDhcpv6AllocIpv6Addr         OCTET STRING,
        topCcmtsVlanDhcpv6AllocPrefix           INTEGER
}

topCcmtsVlanDhcpv6Alloc OBJECT-TYPE
        SYNTAX          INTEGER{
                                                enable(1),
                                                disable(2)
                                } 
        MAX-ACCESS      read-create
        STATUS          current
        DESCRIPTION
                "This object is used to get ipv6 address from DHCPV6
                Server for the vlan identified by topCcmtsVifPriIpVlanId."
        ::={topCcmtsVlanDhcpv6AllocEntry 1}

topCcmtsVlanDhcpv6AllocOption16 OBJECT-TYPE
        SYNTAX          OCTET STRING(SIZE(0..128)) 
        MAX-ACCESS      read-create
        STATUS          current
        DESCRIPTION
                "This object describes the option16 field'String used
                in DHCPV6 request."
        ::={topCcmtsVlanDhcpv6AllocEntry 2}    

topCcmtsVlanDhcpv6AllocIpv6Addr OBJECT-TYPE
        SYNTAX          OCTET STRING
        MAX-ACCESS      read-only
        STATUS          current
        DESCRIPTION
                "VIF DHCPV6 alloc IPV6 address."
        ::= { topCcmtsVlanDhcpv6AllocEntry 3 }

topCcmtsVlanDhcpv6AllocPrefix OBJECT-TYPE
        SYNTAX          INTEGER
        MAX-ACCESS      read-only
        STATUS          current
        DESCRIPTION
                "DHCPV6 alloc IPV6 prefix length."
        ::= { topCcmtsVlanDhcpv6AllocEntry 4 }  

topCcmtsAuthObject OBJECT IDENTIFIER ::= { topCcmtsMibObject 8 }
		
topCcmtsAuthTable OBJECT-TYPE
	SYNTAX SEQUENCE OF TopCcmtsAuthEntry
	MAX-ACCESS not-accessible
	STATUS current
	DESCRIPTION
		"Authorization Object."
	::= { topCcmtsAuthObject 1 }


topCcmtsAuthEntry OBJECT-TYPE
	SYNTAX TopCcmtsAuthEntry
	MAX-ACCESS not-accessible
	STATUS current
	DESCRIPTION
		"An entry used to get file and authorize to ccmts.
		ifIndex is ccmts's mac domain's ifIndex."
	INDEX { ifIndex }
	::= { topCcmtsAuthTable 1 }


TopCcmtsAuthEntry ::=
	SEQUENCE { 
		topCcmtsAuthTransferProtocol
			INTEGER,
		topCcmtsAuthFileURI
			DisplayString,
		topCcmtsAuthCurrentInfo
			DisplayString,
		topCcmtsAuthApply
			INTEGER,
		topCcmtsAuthApplyError
			DisplayString,
		topCcmtsAuthApplyStatus
			INTEGER
	 }

topCcmtsAuthTransferProtocol OBJECT-TYPE
	SYNTAX INTEGER
		{
		tftp(1),
		other(2)
		}
	MAX-ACCESS read-write
	STATUS current
	DESCRIPTION
		"Transfer protocol."
	::= { topCcmtsAuthEntry 1 }


topCcmtsAuthFileURI OBJECT-TYPE
	SYNTAX DisplayString
	MAX-ACCESS read-write
	STATUS current
	DESCRIPTION
		"Authorization file's URI."
	::= { topCcmtsAuthEntry 2 }

topCcmtsAuthCurrentInfo OBJECT-TYPE
	SYNTAX DisplayString
	MAX-ACCESS read-only
	STATUS current
	DESCRIPTION
		"Current authorization Information.It contains information 
		same as topCcmtsAuthUpdateLicenseInfo descriped."
	::= { topCcmtsAuthEntry 3 }


topCcmtsAuthApply OBJECT-TYPE
	SYNTAX INTEGER
		{
		apply(1),
		noAction(2),
		other(3)
		}
	MAX-ACCESS read-write
	STATUS current
	DESCRIPTION
		"Apply authorization information Action. When set to apply(1),
		device will download file and authorize."
	::= { topCcmtsAuthEntry 4 } 

topCcmtsAuthApplyError OBJECT-TYPE
	SYNTAX DisplayString
	MAX-ACCESS read-only
	STATUS current
	DESCRIPTION
		"Authorization Information will be used to this ccmts.
		It contains the serial number of the License File, the
		cut off time, limited down channel number,limited up 
		channel number,etc."
	::= { topCcmtsAuthEntry 5 }



topCcmtsAuthApplyStatus OBJECT-TYPE
	SYNTAX INTEGER
		{
			init(0),
			getAUpdateCmd(1),
			tftpGetStart(2),
			tftpGetOk(3),
			tftpGetError(4),
			startSendToCmc(5),
			sendingToCmc(6),
			sendToCmcOk(7),
			sendToCmcError(8),
			completeWithError(9),
			success(10),
			operateDbFail(11),
			cmcOffline(12),
			getCmcIfindexFail(13)
		}
	MAX-ACCESS read-only
	STATUS current
	DESCRIPTION
		"Last topCcmtsAuthApply was set to apply(1),device authorized status."
	::= { topCcmtsAuthEntry 6 }

topCcmtsAuthStatus OBJECT-TYPE
	SYNTAX INTEGER
		{
			inProgress(1),
			free(2)			
		}
	MAX-ACCESS read-only
	STATUS current
	DESCRIPTION
		"Inprogress(1) indicates  a CCMTS is authorizing.Free(2) indicates
		the system is free that one of CCMTSs can be authorized."
	::= { topCcmtsAuthObject 2 }
topCcmtsCmRemoteQueryCfgObject	OBJECT IDENTIFIER ::={ topCcmtsMibObject 9 } 
     
topCcmtsCmRemoteQueryCommunity OBJECT-TYPE
	SYNTAX		DisplayString
	MAX-ACCESS	read-write
	STATUS		current
	DESCRIPTION
		"This string is the commnunity-string what
		be used for snmp request connect"
	::={ topCcmtsCmRemoteQueryCfgObject 1 }

topCcmtsCmRemoteQueryInterval OBJECT-TYPE
	SYNTAX		INTEGER(5..86400)
	MAX-ACCESS	read-write
	STATUS		current
	DESCRIPTION
		"The interval after one whole polling end
		 and before another polling process start"
	::={ topCcmtsCmRemoteQueryCfgObject 2}
   
topCcmtsCmRemoteQuerySrcIP OBJECT-TYPE
	SYNTAX		IpAddress
	MAX-ACCESS	read-write
	STATUS		current
	DESCRIPTION
		"The IP address used for snmp connecting.
		The IP must be one of the vaild IPs which Device own 
		Returns 0.0.0.0 if no IP is assigned.
		Write 0.0.0.0 to clear the ip assigned"
	::={ topCcmtsCmRemoteQueryCfgObject 3}


  topCcmtsCmRemoteQueryCmTable OBJECT-TYPE
	SYNTAX SEQUENCE OF TopCcmtsCmRemoteQueryCmEntry
	MAX-ACCESS not-accessible
	STATUS current
	DESCRIPTION
		"Authorization Object."
	::= { topCcmtsCmRemoteQueryCfgObject 4 }


  topCcmtsCmRemoteQueryCmEntry OBJECT-TYPE
	SYNTAX TopCcmtsCmRemoteQueryCmEntry
	MAX-ACCESS not-accessible
	STATUS current
	DESCRIPTION
		"An entry used to get file and authorize to ccmts.
		ifIndex is cm's ifIndex."
	INDEX { topCcmtsCmRemoteQueryCmIndex }
	::= { topCcmtsCmRemoteQueryCmTable 1 }


  TopCcmtsCmRemoteQueryCmEntry ::=
	SEQUENCE { 
		topCcmtsCmRemoteQueryCmIndex			InterfaceIndex,
		topCcmtsCmRemoteQueryStatus			TruthValue,
		topCcmtsCmRemoteQueryCmRxPower			TenthdBmV,
		topCcmtsCmRemoteQueryCmTxPower			TenthdBmV,
		topCcmtsCmRemoteQueryCmSignalNoise		TenthdB,
		topCcmtsCmRemoteQueryCmMicroReflections		Integer32,
		topCcmtsCmRemoteQueryCmDocsBaseCapability	DocsisVersionCcmtsLocal
	 }   
	 
	 
   topCcmtsCmRemoteQueryCmIndex OBJECT-TYPE
	SYNTAX		InterfaceIndex
	MAX-ACCESS	read-only
	STATUS		current
	DESCRIPTION
		"Cm Index"
	::={ topCcmtsCmRemoteQueryCmEntry 1 }
  
   topCcmtsCmRemoteQueryStatus OBJECT-TYPE
	SYNTAX		TruthValue
	MAX-ACCESS	read-only
	STATUS		current
	DESCRIPTION
		"Specifies whether or not the Data about Cm On the Device
		is up to date"
	::={ topCcmtsCmRemoteQueryCmEntry 2 }
   
   topCcmtsCmRemoteQueryCmRxPower OBJECT-TYPE
	SYNTAX		TenthdBmV  
	UNITS		"TenthdBmV"
	MAX-ACCESS	read-only
	STATUS		current
	DESCRIPTION
		"The receive power as perceived for downstream data from
		this cable modem.
		If the receive power is unknown, this object returns
		a value of zero."
	::={ topCcmtsCmRemoteQueryCmEntry 3 }
           
   topCcmtsCmRemoteQueryCmTxPower OBJECT-TYPE
	SYNTAX		TenthdBmV  
	UNITS		"TenthdBmV"
	MAX-ACCESS	read-only
	STATUS		current
	DESCRIPTION
		"The transfer power as perceived for upstream data from
		this cable modem.
		If the transfer power is unknown, this object returns zero."
	::={ topCcmtsCmRemoteQueryCmEntry 4 }
    
   topCcmtsCmRemoteQueryCmSignalNoise OBJECT-TYPE
	SYNTAX		TenthdB     
	UNITS		"TenthdB"
	MAX-ACCESS	read-only
	STATUS		current
	DESCRIPTION
		"Signal/Noise ratio as perceived for downstream data from
		this cable modem.
		If the Signal/Noise is unknown, this object returns
		a value of zero."
	::={ topCcmtsCmRemoteQueryCmEntry 5 }

   topCcmtsCmRemoteQueryCmMicroReflections OBJECT-TYPE
	SYNTAX		 Integer32 (0..255)
	UNITS		"-dBc"
	MAX-ACCESS	read-only
	STATUS		current
	DESCRIPTION
		"Total microreflections, including in-channel response
		as perceived on this interface, measured in dBc below
		the signal level.
		This object is not assumed to return an absolutely
		accurate value, but it gives a rough indication
		of microreflections received on this interface.
		It is up to the implementer to provide information
		as accurately as possible."
	::={ topCcmtsCmRemoteQueryCmEntry 6 }
	
   topCcmtsCmRemoteQueryCmDocsBaseCapability OBJECT-TYPE
	SYNTAX		DocsisVersionCcmtsLocal
	MAX-ACCESS	read-only
	STATUS		current
	DESCRIPTION
            "Indication of the DOCSIS capability of the device."
	::={ topCcmtsCmRemoteQueryCmEntry 7 }	
	
  topCcmtsCmRemoteQueryCmUsTable OBJECT-TYPE
	SYNTAX SEQUENCE OF TopCcmtsCmRemoteQueryCmUsEntry
	MAX-ACCESS not-accessible
	STATUS current
	DESCRIPTION
		"Authorization Object."
	::= { topCcmtsCmRemoteQueryCfgObject 5 }


  topCcmtsCmRemoteQueryCmUsEntry OBJECT-TYPE
	SYNTAX TopCcmtsCmRemoteQueryCmUsEntry
	MAX-ACCESS not-accessible
	STATUS current
	DESCRIPTION
		"An entry used to get file and authorize to ccmts.
		topCcmtsCmRemoteQueryCmIndex is cm's ifIndex.
		topCcmtsCmRemoteQueryCmUsIndex is upstream index of cm"
	INDEX { 
		topCcmtsCmRemoteQueryCmIndex,
		topCcmtsCmRemoteQueryCmUsIndex
	}
	::= { topCcmtsCmRemoteQueryCmUsTable 1 }
	
  TopCcmtsCmRemoteQueryCmUsEntry ::=
	SEQUENCE { 
		topCcmtsCmRemoteQueryCmUsIndex			Integer32,	
		topCcmtsCmRemoteQueryCmUsChanId			Integer32,
		topCcmtsCmRemoteQueryCmUsTxPower		TenthdBmV
	 }
  topCcmtsCmRemoteQueryCmUsIndex OBJECT-TYPE
	SYNTAX		Integer32
	MAX-ACCESS	not-accessible
	STATUS		current
	DESCRIPTION
		"upstream index the cm bound to"
	::={ topCcmtsCmRemoteQueryCmUsEntry 1 }
	
  topCcmtsCmRemoteQueryCmUsChanId OBJECT-TYPE
	SYNTAX		Integer32
	MAX-ACCESS	read-only
	STATUS		current
	DESCRIPTION
		"Up Chan Id of CMC which CM bound to"
	::={ topCcmtsCmRemoteQueryCmUsEntry 2 }
  
   topCcmtsCmRemoteQueryCmUsTxPower OBJECT-TYPE
	SYNTAX		TenthdBmV
	UNITS		"TenthdBmV"
	MAX-ACCESS	read-only
	STATUS		current
	DESCRIPTION
	"The transfer power as perceived for upstream data from
	this cable modem.
	If the transfer power is unknown, this object returns zero."
	::={ topCcmtsCmRemoteQueryCmUsEntry 3 }

  topCcmtsCmRemoteQueryCmDsTable OBJECT-TYPE
	SYNTAX SEQUENCE OF TopCcmtsCmRemoteQueryCmDsEntry
	MAX-ACCESS not-accessible
	STATUS current
	DESCRIPTION
		"Authorization Object."
	::= { topCcmtsCmRemoteQueryCfgObject 6 }


  topCcmtsCmRemoteQueryCmDsEntry OBJECT-TYPE
	SYNTAX TopCcmtsCmRemoteQueryCmDsEntry
	MAX-ACCESS not-accessible
	STATUS current
	DESCRIPTION
		"An entry used to get file and authorize to ccmts.
		topCcmtsCmRemoteQueryCmIndex is cm's ifIndex.
		topCcmtsCmRemoteQueryCmDsIndex is downstream index of cm"
	INDEX { 
		topCcmtsCmRemoteQueryCmIndex,
		topCcmtsCmRemoteQueryCmDsIndex
	}
	::= { topCcmtsCmRemoteQueryCmDsTable 1 }
  TopCcmtsCmRemoteQueryCmDsEntry ::=
	SEQUENCE { 
		topCcmtsCmRemoteQueryCmDsIndex			Integer32,
		topCcmtsCmRemoteQueryCmDsChanId			Integer32,
		topCcmtsCmRemoteQueryCmDsRxPower		TenthdBmV,
		topCcmtsCmRemoteQueryCmDsSignalNoise		TenthdB,
		topCcmtsCmRemoteQueryCmDsMicroReflections	Integer32
	 }
	 
  topCcmtsCmRemoteQueryCmDsIndex OBJECT-TYPE
	SYNTAX		Integer32
	MAX-ACCESS	not-accessible
	STATUS		current
	DESCRIPTION
		"downstream index the cm bound to"
	::={ topCcmtsCmRemoteQueryCmDsEntry 1 }
	 
  topCcmtsCmRemoteQueryCmDsChanId OBJECT-TYPE
	SYNTAX		Integer32
	MAX-ACCESS	read-only
	STATUS		current
	DESCRIPTION
		"Down Chan Id of CMC which CM bound to"
	::={ topCcmtsCmRemoteQueryCmDsEntry 2 }
  
   topCcmtsCmRemoteQueryCmDsRxPower OBJECT-TYPE
	SYNTAX		TenthdBmV  
	UNITS		"TenthdBmV"
	MAX-ACCESS	read-only
	STATUS		current
	DESCRIPTION
		"The receive power as perceived for downstream data from
		this cable modem.
		If the receive power is unknown, this object returns
		a value of zero."
	::={ topCcmtsCmRemoteQueryCmDsEntry 3 }
    
   topCcmtsCmRemoteQueryCmDsSignalNoise OBJECT-TYPE
	SYNTAX		TenthdB
	UNITS		"TenthdB"
	MAX-ACCESS	read-only
	STATUS		current
	DESCRIPTION
		"Signal/Noise ratio as perceived for downstream data from
		this cable modem.
		If the Signal/Noise is unknown, this object returns
		a value of zero."
	::={ topCcmtsCmRemoteQueryCmDsEntry 4 }

   topCcmtsCmRemoteQueryCmDsMicroReflections OBJECT-TYPE
	SYNTAX		 Integer32 (0..255)
	UNITS		"-dBc"
	MAX-ACCESS	read-only
	STATUS		current
	DESCRIPTION
		"Total microreflections, including in-channel response
		as perceived on this interface, measured in dBc below
		the signal level.
		This object is not assumed to return an absolutely
		accurate value, but it gives a rough indication
		of microreflections received on this interface.
		It is up to the implementer to provide information
		as accurately as possible."
	::={ topCcmtsCmRemoteQueryCmDsEntry 5 }	  
    
topCcmtsCmRemoteQuerySystemInfoTable OBJECT-TYPE
	SYNTAX		SEQUENCE OF TopCcmtsCmRemoteQuerySystemInfoEntry
	MAX-ACCESS	not-accessible
	STATUS		current
	DESCRIPTION
		"show cable modem system-info."
	::={ topCcmtsCmRemoteQueryCfgObject 7}

topCcmtsCmRemoteQuerySystemInfoEntry OBJECT-TYPE
	SYNTAX		TopCcmtsCmRemoteQuerySystemInfoEntry
	MAX-ACCESS	not-accessible
	STATUS		current
	DESCRIPTION	
		" show cable modem system-info,the softeware hardware will be list."
	INDEX  { docsIfCmtsCmStatusIndex }
	::={ topCcmtsCmRemoteQuerySystemInfoTable 1 }

-- 
TopCcmtsCmRemoteQuerySystemInfoEntry ::=SEQUENCE{
	topCcmtsCmRemoteQueryDescription		DisplayString,
	topCcmtsCmRemoteQueryResets				Integer32,
	topCcmtCmRemoteQueryUPTime			    TimeTicks
}
	
topCcmtsCmRemoteQueryDescription OBJECT-TYPE
	SYNTAX		DisplayString
	MAX-ACCESS	read-only
	STATUS		current
	DESCRIPTION
		"Description by factory"   
	DEFVAL {""}
	::={ topCcmtsCmRemoteQuerySystemInfoEntry 1 } 
	
topCcmtsCmRemoteQueryResets OBJECT-TYPE
	SYNTAX		Integer32
	MAX-ACCESS	read-only
	STATUS		current
	DESCRIPTION
		"restart times"        
	DEFVAL {0}
	::={ topCcmtsCmRemoteQuerySystemInfoEntry 2 }
	
topCcmtCmRemoteQueryUPTime OBJECT-TYPE
	SYNTAX		TimeTicks
	MAX-ACCESS	read-only
	STATUS		current
	DESCRIPTION
		"up time"      
	DEFVAL {0}
	::={ topCcmtsCmRemoteQuerySystemInfoEntry 3 }
	
topCcmtsCmRemoteQueryUSInfoTable OBJECT-TYPE
	SYNTAX		SEQUENCE OF TopCcmtsCmRemoteQueryUSInfoEntry
	MAX-ACCESS	not-accessible
	STATUS		current
	DESCRIPTION
		"show Cable modem remote-query us-info."
	::={ topCcmtsCmRemoteQueryCfgObject 8}

topCcmtsCmRemoteQueryUSInfoEntry OBJECT-TYPE
	SYNTAX		TopCcmtsCmRemoteQueryUSInfoEntry
	MAX-ACCESS	not-accessible
	STATUS		current
	DESCRIPTION	
		"show Cable modem remote-query us-info."
	INDEX  { docsIfCmtsCmStatusIndex,
			   docsIfUpChannelId }
	::={ topCcmtsCmRemoteQueryUSInfoTable 1 }    
	--docsIfDownChannelId
TopCcmtsCmRemoteQueryUSInfoEntry ::=SEQUENCE{
	topCcmtsCmRemoteQueryUSBps			    Counter64
}

topCcmtsCmRemoteQueryUSBps OBJECT-TYPE
	SYNTAX		Counter64  
	UNITS "bps"
	MAX-ACCESS	read-only
	STATUS		current    
	DESCRIPTION
	"The rate of bits were received by CM through upstream channel"     
	DEFVAL {0}
	::={ topCcmtsCmRemoteQueryUSInfoEntry 1 }
	
topCcmtsCmRemoteQueryDSInfoTable OBJECT-TYPE
	SYNTAX		SEQUENCE OF TopCcmtsCmRemoteQueryDSInfoEntry
	MAX-ACCESS	not-accessible
	STATUS		current
	DESCRIPTION
		"show cable modem remote-query ds-info."
	::={ topCcmtsCmRemoteQueryCfgObject 9}

topCcmtsCmRemoteQueryDSInfoEntry OBJECT-TYPE
	SYNTAX		TopCcmtsCmRemoteQueryDSInfoEntry
	MAX-ACCESS	not-accessible
	STATUS		current
	DESCRIPTION	
		"show cable modem remote-query ds-info."
	INDEX  { docsIfCmtsCmStatusIndex,
		      docsIfDownChannelId }
	::={ topCcmtsCmRemoteQueryDSInfoTable 1 }

TopCcmtsCmRemoteQueryDSInfoEntry ::=SEQUENCE{	
	topCcmtsCmRemoteQueryDSBps			     Counter64,
	topCcmtsCmRemoteQueryDSErrorRation		 DisplayString
}
		
topCcmtsCmRemoteQueryDSBps OBJECT-TYPE
	SYNTAX		Counter64   
	UNITS "bps"
	MAX-ACCESS	read-only
	STATUS		current 
	DESCRIPTION
		"The rate of bits were received by CM through downstream channel"     
	DEFVAL {0}
	::={ topCcmtsCmRemoteQueryDSInfoEntry 1 }
	
topCcmtsCmRemoteQueryDSErrorRation OBJECT-TYPE
	SYNTAX		DisplayString  
	----UNITS      "Pencent(%)"
	MAX-ACCESS	read-only
	STATUS		current 
	DESCRIPTION
		"error ration of downstream channel"    
	DEFVAL {"0"}
	::={ topCcmtsCmRemoteQueryDSInfoEntry 2 }
	
topCcmtsCmRemoteQueryInterfaceInfoTable OBJECT-TYPE
	SYNTAX		SEQUENCE OF TopCcmtsCmRemoteQueryInterfaceInfoEntry
	MAX-ACCESS	not-accessible
	STATUS		current
	DESCRIPTION
		"show cable modem remote-query interface-info."
	::={ topCcmtsCmRemoteQueryCfgObject 10}

topCcmtsCmRemoteQueryInterfaceInfoEntry OBJECT-TYPE
	SYNTAX		TopCcmtsCmRemoteQueryInterfaceInfoEntry
	MAX-ACCESS	not-accessible
	STATUS		current
	DESCRIPTION	
		"show cable modem remote-query interface-info."
	INDEX  { docsIfCmtsCmStatusIndex,
				ifIndex
			}
	::={ topCcmtsCmRemoteQueryInterfaceInfoTable 1 }  

TopCcmtsCmRemoteQueryInterfaceInfoEntry ::=SEQUENCE{
	topCcmtsCmRemoteQueryPortType           INTEGER,
	topCcmtsCmRemoteQueryPortDescription	DisplayString,
	topCcmtsCmRemoteQueryPortStatus		    INTEGER
}

topCcmtsCmRemoteQueryPortType OBJECT-TYPE
	SYNTAX  INTEGER {
				other(1),
				regular1822(2),
				hdh1822(3),
				ddn-x25(4),
				rfc877-x25(5),
				ethernet-csmacd(6),
				iso88023-csmacd(7),
				iso88024-tokenBus(8),
				iso88025-tokenRing(9),
				iso88026-man(10),
				starLan(11),
				proteon-10Mbit(12),
				proteon-80Mbit(13),
				hyperchannel(14),
				fddi(15),
				lapb(16),
				sdlc(17),
				ds1(18),
				e1(19),
				basicISDN(20),
				primaryISDN(21),
				propPointToPointSerial(22),
				ppp(23),
				softwareLoopback(24),
				eon(25),
				ethernet-3Mbit(26),
				nsip(27),
				slip(28),
				ultra(29),
				ds3(30),
				sip(31),
				frame-relay(32),
				hundredMbaseTEthernet(62),
				hundredMFXEthernet(69),
				gigabitMEthernet(117),
				mac(127),
				downsteam(128),
				upstream(129),
                usb(160)            --usb
            }
 
	MAX-ACCESS	read-only
	STATUS		current
	DESCRIPTION
		"port type"         
	DEFVAL {0}
	::={ topCcmtsCmRemoteQueryInterfaceInfoEntry 1 }

topCcmtsCmRemoteQueryPortDescription OBJECT-TYPE
	SYNTAX		DisplayString
	MAX-ACCESS	read-only
	STATUS		current
	DESCRIPTION
		" port descibes"         
	DEFVAL {""}
	::={ topCcmtsCmRemoteQueryInterfaceInfoEntry 2 }
	
topCcmtsCmRemoteQueryPortStatus OBJECT-TYPE
	SYNTAX  INTEGER {
                up(1),        -- ready to pass packets
                down(2),
                testing(3),   -- in some test mode
                unknown(4),   -- status can not be determined
                              -- for some reason.
                dormant(5),
                notPresent(6),    -- some component is missing
                lowerLayerDown(7) -- down due to state of
                                  -- lower-layer interface(s)
            }
 
	MAX-ACCESS	read-only
	STATUS		current
	DESCRIPTION
		"Ethernet port status"         
	DEFVAL {2}
	::={ topCcmtsCmRemoteQueryInterfaceInfoEntry 3 }
	
 topCcmtsCmRemoteQueryCpeInfoTable OBJECT-TYPE
	SYNTAX		SEQUENCE OF TopCcmtsCmRemoteQueryCpeInfoEntry
	MAX-ACCESS	not-accessible
	STATUS		current
	DESCRIPTION
		"show cable modem remote-query cpe-info."
	::={ topCcmtsCmRemoteQueryCfgObject 11}

topCcmtsCmRemoteQueryCpeInfoEntry OBJECT-TYPE
	SYNTAX		TopCcmtsCmRemoteQueryCpeInfoEntry
	MAX-ACCESS	not-accessible
	STATUS		current
	DESCRIPTION	
		"show cable modem remote-query cpe-info."
	INDEX  { docsIfCmtsCmStatusIndex,
				topCcmtsCmRemoteQueryCpeMac
	}
	::={ topCcmtsCmRemoteQueryCpeInfoTable 1 }

TopCcmtsCmRemoteQueryCpeInfoEntry ::=SEQUENCE{
	topCcmtsCmRemoteQueryCpeMac				MacAddress,
	topCcmtsCmRemoteQueryCpeMacStatus       INTEGER
}
	
topCcmtsCmRemoteQueryCpeMac OBJECT-TYPE
	SYNTAX		MacAddress
	MAX-ACCESS	read-only
	STATUS		current
	DESCRIPTION
		"CPE MAC"
	DEFVAL { '000000000000'h }
	::={ topCcmtsCmRemoteQueryCpeInfoEntry 1 }
	
topCcmtsCmRemoteQueryCpeMacStatus OBJECT-TYPE
	SYNTAX      INTEGER {
                       other(1),
                       invalid(2),
                       learned(3),
                       self(4),
                       mgmt(5)
                   }
	MAX-ACCESS	read-only
	STATUS		current
	DESCRIPTION
		"CPE MAC status"
	DEFVAL { 4 }
	::={ topCcmtsCmRemoteQueryCpeInfoEntry 2 }

topCcmtsCmRemoteQueryCmcCfgTable OBJECT-TYPE
	SYNTAX		SEQUENCE OF TopCcmtsCmRemoteQueryCmcCfgEntry
	MAX-ACCESS	not-accessible
	STATUS		current
	DESCRIPTION
		"Configure cable modem remote-query under cmts."
	::={ topCcmtsCmRemoteQueryCfgObject 12}

topCcmtsCmRemoteQueryCmcCfgEntry OBJECT-TYPE
	SYNTAX		TopCcmtsCmRemoteQueryCmcCfgEntry
	MAX-ACCESS	not-accessible
	STATUS		current
	DESCRIPTION	
		"The conceptual row of topCcmtsCmRemoteQueryCfgTable."
	INDEX  { ifIndex }
	::={ topCcmtsCmRemoteQueryCmcCfgTable 1 }

TopCcmtsCmRemoteQueryCmcCfgEntry ::=SEQUENCE{
	topCcmtsCmRemoteQueryCmcStatus					INTEGER,
	topCcmtsCmRemoteQueryCmcCommunity				DisplayString,
	topCcmtsCmRemoteQueryCmcInterval				INTEGER,
	topCcmtsCmRemoteQueryCmcSrcIP					IpAddress  
}

topCcmtsCmRemoteQueryCmcStatus OBJECT-TYPE
	SYNTAX		INTEGER{   
					enable(1),
					disable(2)
				}
	MAX-ACCESS	read-write
	STATUS		current
	DESCRIPTION
		"enable(1):the remotequery effect is on at this Ccmts
		 disable(2):the remotequery effect is off at this Ccmts"
	::={ topCcmtsCmRemoteQueryCmcCfgEntry 1 }
	
topCcmtsCmRemoteQueryCmcCommunity OBJECT-TYPE
	SYNTAX		DisplayString
	MAX-ACCESS	read-write
	STATUS		current
	DESCRIPTION
		"This string is the commnunity-string what
		be used for snmp request connect"
	::={ topCcmtsCmRemoteQueryCmcCfgEntry 2 }
	
topCcmtsCmRemoteQueryCmcInterval OBJECT-TYPE
	SYNTAX      INTEGER(5..86400)
	MAX-ACCESS	read-write
	STATUS		current
	DESCRIPTION
		"The interval after one whole polling end
		 and before another polling process start"
	::={ topCcmtsCmRemoteQueryCmcCfgEntry 3 }
	
topCcmtsCmRemoteQueryCmcSrcIP OBJECT-TYPE
	SYNTAX		IpAddress
	MAX-ACCESS	read-write
	STATUS		current
	DESCRIPTION
		"The IP address used for snmp connecting.
		The IP must be one of the vaild IPs which Device own 
		Returns 0.0.0.0 if no IP is assigned.
		Write 0.0.0.0 to clear the ip assigned"
	::={ topCcmtsCmRemoteQueryCmcCfgEntry 4 }

--
--topCcmtsLoadBalanceObject
--
--modified by lihuanyong
--
topCcmtsLoadBalanceObject	OBJECT IDENTIFIER ::={ topCcmtsMibObject 12}

topCcmtsLoadBalCfgTable OBJECT-TYPE
    SYNTAX SEQUENCE OF TopCcmtsLoadBalCfgEntry
    MAX-ACCESS not-accessible
    STATUS current
    DESCRIPTION
		" Load balancing general configuration."
    ::= { topCcmtsLoadBalanceObject 1 } 
	
topCcmtsLoadBalCfgEntry OBJECT-TYPE
    SYNTAX TopCcmtsLoadBalCfgEntry
    MAX-ACCESS not-accessible
    STATUS current
    DESCRIPTION
		" "
	INDEX { topLoadBalConfigCmcIndex }
    ::= { topCcmtsLoadBalCfgTable 1 }

TopCcmtsLoadBalCfgEntry     ::= SEQUENCE {
	 topLoadBalConfigCmcIndex Unsigned32,
	 topLoadBalConfigEnable INTEGER,
	 topLoadBalConfigInterval Unsigned32,
	 topLoadBalConfigMaxMoves Unsigned32,
	 topLoadBalConfigMethod INTEGER,
	 topLoadBalConfigNumPeriod INTEGER,
	 topLoadBalConfigPeriod Unsigned32,
	 topLoadBalConfigTriggerThresh Unsigned32,
	 topLoadBalConfigDiffThresh Unsigned32,
	 topLoadBalConfigRangingOverrideEnable INTEGER,
     topLoadBalConfigDccInitAtdma INTEGER,
	 topLoadBalConfigDccInitScdma INTEGER,
	 topLoadBalConfigDbcInitAtdma INTEGER,
	 topLoadBalConfigDbcInitScdma INTEGER,
	 topLoadBalConfigLoadMinimum  Unsigned32, 
     topLoadBalConfigHighSysThresh  Unsigned32,
     topLoadBalConfigLowSysThresh  Unsigned32
	}
topLoadBalConfigCmcIndex OBJECT-TYPE
    SYNTAX Unsigned32 (1..4294967295)
    MAX-ACCESS read-only
    STATUS current
    DESCRIPTION
		"The index of CCMTS."
    ::= { topCcmtsLoadBalCfgEntry 1 }

topLoadBalConfigEnable OBJECT-TYPE
    SYNTAX INTEGER {
    	enable(1),
    	disable(2)
    }
    MAX-ACCESS read-write
    STATUS current
    DESCRIPTION
		"enable(1):the load-balance operation is on at this CCMTS
		 disable(2):the load-balance operation is off at this CCMTS" 
	DEFVAL          { enable }
    ::= { topCcmtsLoadBalCfgEntry 2 } 
    
topLoadBalConfigInterval OBJECT-TYPE
    SYNTAX Unsigned32 (0..3600)
    MAX-ACCESS read-write
    STATUS current
    DESCRIPTION
		"Minimum number of seconds that must elapse before moving the same modem 
		to a different channel."
	DEFVAL          { 240 }
    ::= { topCcmtsLoadBalCfgEntry 3 } 
    
topLoadBalConfigMaxMoves OBJECT-TYPE
    SYNTAX Unsigned32 (1..1000)
    MAX-ACCESS read-write
    STATUS current
    DESCRIPTION
		"Maximum number of modems allowed to be moved per load balancer period." 
	DEFVAL          { 16 }
    ::= { topCcmtsLoadBalCfgEntry 4 }
    
topLoadBalConfigMethod OBJECT-TYPE
    SYNTAX INTEGER {
    	utilization(1),
    	service-flow(2),
		modem(3),
		UsUtilization-DsServiceFlow(4),
		UsUtilization-DsModem(5),
		UsServiceFlow-DsUtilization(6),
		UsServiceFlow-DsModem(7),
		UsModem-DsUtilization(8),
		UsModem-DsServiceFlow(9)
    }
    MAX-ACCESS read-write
    STATUS current
    DESCRIPTION
		"The method of load-balance.
		 The method 1 is based on run-time statistics;
		 The method 2 is based on the active service-flow number for both upstream and downstream channels;
		 The method 3 is based on the number of the cable modem for both upstream and downstream channels;
		 The method 4 means run-time statistics for upstream channels and the active service-flow number for downstream channels;
		 The method 5 means run-time statistics for upstream channels and the number of the cable modem for downstream channels;
		 The method 6 means the active service-flow number for upstream channels and run-time statistics for downstream channels;
		 The method 7 means the active service-flow number for upstream channels and the number of the cable modem for downstream channels;
		 The method 8 means the number of the cable modem for upstream channels and run-time statistics for downstream channels;
		 The method 9 means the number of the cable modem for upstream channels and the active service-flow number for downstream channels.
		"  
	DEFVAL          { utilization }
    ::= { topCcmtsLoadBalCfgEntry 5 }

topLoadBalConfigNumPeriod OBJECT-TYPE
    SYNTAX INTEGER {
    	one(1),
    	two(2),
    	four(4)
    }
    MAX-ACCESS read-write
    STATUS current
    DESCRIPTION
		"Number of periods for calculating the weighted average load. Each period 
		 gets twice the weight of the previous period. Valid values are 1, 2, or 4. 
		 Applies to Balancing Method utilization(1) only.When Balancing Method is 
		 modem(2),the value of this object is same as Balancing Method utilization(1)" 
	DEFVAL          { four }
    ::= { topCcmtsLoadBalCfgEntry 6 }
    
topLoadBalConfigPeriod OBJECT-TYPE
    SYNTAX Unsigned32 (60..3600)
    MAX-ACCESS read-write
    STATUS current
    DESCRIPTION
		"Time in seconds between load balancing checks." 
	DEFVAL          { 60 }
    ::= { topCcmtsLoadBalCfgEntry 7 }
    
topLoadBalConfigTriggerThresh OBJECT-TYPE
    SYNTAX Unsigned32 (1..100)
    MAX-ACCESS read-write
    STATUS current
    DESCRIPTION
		"A channel is considered overloaded when the load is at least this percent
		 of capacity. Below this, no attempt is made to balance its load. Applies to
		 Balancing Method utilization(1) only. When Balancing Method is modem(2), 
		 the value of this object is same as Balancing Method utilization(1)." 
	DEFVAL          { 75 }
    ::= { topCcmtsLoadBalCfgEntry 8 }
    
topLoadBalConfigDiffThresh OBJECT-TYPE
    SYNTAX Unsigned32 (1..100)
    MAX-ACCESS read-write
    STATUS current
    DESCRIPTION
		"For channels at or above the overload threshold, only consider less loaded 
		 alternate channels where the load difference is at least this percent. Applies 
		 to Balancing Method utilization(1) only. When Balancing Method is modem(2), 
		 the value of this object is same as Balancing Method utilization(1)"
	DEFVAL          { 15 }
    ::= { topCcmtsLoadBalCfgEntry 9 }
    
topLoadBalConfigRangingOverrideEnable OBJECT-TYPE
    SYNTAX INTEGER {
    	enable(1),
    	disable(2)
    }
    MAX-ACCESS read-write
    STATUS current
    DESCRIPTION
		"1=enable, 2=Disable. When enabled, a modem can be directed to 
		 a different channel via RNG-RSP prior to registration" 
	DEFVAL         { enable }
    ::= { topCcmtsLoadBalCfgEntry 10 }
    
topLoadBalConfigDccInitAtdma OBJECT-TYPE
    SYNTAX INTEGER {
       broadcastInitRanging (1),
       unicastInitRanging (2),
       initRanging (3),
       direct (4)
    }
    MAX-ACCESS read-write
    STATUS current
    DESCRIPTION
		" broadcastInitRanging(1): Perform Broadcast initialranging on new 
		  channel before normal operation.
		  unicastInitRanging(2)  : Perform unicast ranging on new channel 
		  before normal operation.
		  initRanging(3)         : Perform either broadcast or unicast ranging 
		  on new channel before normal operation.
		  direct(4) 		: Use the new channel(s) directly without 
		  re-initializing or ranging." 
	DEFVAL          { broadcastInitRanging }
    ::= { topCcmtsLoadBalCfgEntry 11 }
    
topLoadBalConfigDccInitScdma OBJECT-TYPE
    SYNTAX INTEGER {
       broadcastInitRanging (1),
       unicastInitRanging (2),
       initRanging (3)
    }
    MAX-ACCESS read-write
    STATUS current
    DESCRIPTION
		" broadcastInitRanging(1): Perform Broadcast initialranging on new 
		  channel before normal operation.
		  unicastInitRanging(2)  : Perform unicast ranging on new channel 
		  before normal operation.
		  initRanging(3)         : Perform either broadcast or unicast ranging 
		  on new channel before normal operation."
	DEFVAL          { broadcastInitRanging }
    ::= { topCcmtsLoadBalCfgEntry 12 }
    
topLoadBalConfigDbcInitAtdma OBJECT-TYPE
    SYNTAX INTEGER {
       broadcastInitRanging (1),
       unicastInitRanging (2),
       initRanging (3),
       direct (4)
    }
    MAX-ACCESS read-write
    STATUS current
    DESCRIPTION
		" broadcastInitRanging(1): Perform Broadcast initialranging on new 
		  channel before normal operation.
		  unicastInitRanging(2)  : Perform unicast ranging on new channel 
		  before normal operation.
		  initRanging(3)         : Perform either broadcast or unicast ranging 
		  on new channel before normal operation.
		  direct(4) 		: Use the new channel(s) directly without 
		  re-initializing or ranging." 
	DEFVAL          { broadcastInitRanging }
    ::= { topCcmtsLoadBalCfgEntry 13 }
    
topLoadBalConfigDbcInitScdma OBJECT-TYPE
    SYNTAX INTEGER {
       broadcastInitRanging (1),
       unicastInitRanging (2),
       initRanging (3)
    }
    MAX-ACCESS read-write
    STATUS current
    DESCRIPTION
		" broadcastInitRanging(1): Perform Broadcast initialranging on new 
		  channel before normal operation.
		  unicastInitRanging(2)  : Perform unicast ranging on new channel 
		  before normal operation.
		  initRanging(3)         : Perform either broadcast or unicast ranging 
		  on new channel before normal operation."
	DEFVAL          { broadcastInitRanging }
    ::= { topCcmtsLoadBalCfgEntry 14 } 
    
topLoadBalConfigLoadMinimum OBJECT-TYPE
    SYNTAX Unsigned32 (1..100)
    MAX-ACCESS read-write
    STATUS current
    DESCRIPTION
    		"The minimum difference value allowed between channels. 
    		 When the CM number or service flow number exceeds the value, 
     		 the CMTS will begin load balance. It's applied to the real time load balancing." 
    	DEFVAL          { 5 }
    ::= { topCcmtsLoadBalCfgEntry 15 }

topLoadBalConfigHighSysThresh OBJECT-TYPE
    SYNTAX Unsigned32 (0..100)
    MAX-ACCESS read-write
    STATUS current
    DESCRIPTION
    		"The high system threshold value is used to configure the traffic 
    		threshold of the system. When the load balance method is utilization(1) 
    		and the system utilization exceeds the threshold for high-traffic mode, 
    		CMTS will perform load balancing based on realtime traffic." 
    	DEFVAL          { 0 }
    ::= { topCcmtsLoadBalCfgEntry 16 }
    
topLoadBalConfigLowSysThresh OBJECT-TYPE
    SYNTAX Unsigned32 (0..99)
    MAX-ACCESS read-write
    STATUS current
    DESCRIPTION
    		"Threshold for low-traffic mode of the system in percentage." 
    	DEFVAL          { 0 }
    ::= { topCcmtsLoadBalCfgEntry 17 }

    
topCcmtsLoadBalRestrictCmTable OBJECT-TYPE
	SYNTAX SEQUENCE OF TopCcmtsLoadBalRestrictCmEntry 
    MAX-ACCESS not-accessible
    STATUS current
    DESCRIPTION
		"This table descibes the CMs added in restrict load balacne groups."
    ::= { topCcmtsLoadBalanceObject 2 } 
    
topCcmtsLoadBalRestrictCmEntry OBJECT-TYPE
    SYNTAX TopCcmtsLoadBalRestrictCmEntry 
    MAX-ACCESS not-accessible
    STATUS current
    DESCRIPTION
		"The row of the table. "
	INDEX { docsLoadBalGrpId,
	        topLoadBalRestrictCmIndex}
    ::= { topCcmtsLoadBalRestrictCmTable 1 }
    
TopCcmtsLoadBalRestrictCmEntry  ::= SEQUENCE {
	 topLoadBalRestrictCmIndex INTEGER,
	 topLoadBalRestrictCmMacRang OCTET STRING,
	 topLoadBalRestrictCmStatus  RowStatus
	}
	
topLoadBalRestrictCmIndex OBJECT-TYPE
        SYNTAX     	INTEGER (1..200)
        MAX-ACCESS  read-only
        STATUS      current
        DESCRIPTION
            "The index of CM's macRang."
        ::= { topCcmtsLoadBalRestrictCmEntry 2 }

topLoadBalRestrictCmMacRang OBJECT-TYPE
		SYNTAX     	OCTET STRING (SIZE (25..30))
        MAX-ACCESS  read-create
        STATUS      current
        DESCRIPTION
            "The string of macRang,the format is xx:xx:xx:xx:xx:xx yy:yy:yy:yy:yy:yy.
            when create a row in this table,the specific group must exist."
        ::= { topCcmtsLoadBalRestrictCmEntry 3 }  
        
topLoadBalRestrictCmStatus  OBJECT-TYPE
	SYNTAX          RowStatus
	MAX-ACCESS      read-create
	STATUS          current
	DESCRIPTION
		"Indicates the status of the rows in this table and can be used to destroy the specific row." 
	::= { topCcmtsLoadBalRestrictCmEntry 4 }
	
topCcmtsLoadBalExcludeCmTable OBJECT-TYPE
	SYNTAX SEQUENCE OF TopCcmtsLoadBalExcludeCmEntry 
    MAX-ACCESS not-accessible
    STATUS current
    DESCRIPTION
		"This table describes the CMs excluded out of load balance operation. "
    ::= { topCcmtsLoadBalanceObject 3 }
    
topCcmtsLoadBalExcludeCmEntry OBJECT-TYPE
    SYNTAX TopCcmtsLoadBalExcludeCmEntry 
    MAX-ACCESS not-accessible
    STATUS current
    DESCRIPTION
		"The row of the table."
	INDEX { ifIndex,
	        topLoadBalExcludeCmIndex}
    ::= { topCcmtsLoadBalExcludeCmTable 1 }

TopCcmtsLoadBalExcludeCmEntry  ::= SEQUENCE {
	 topLoadBalExcludeCmIndex INTEGER,
	 topLoadBalExcludeCmMacRang OCTET STRING,
	 topLoadBalExcludeCmStatus  RowStatus
	}
	
topLoadBalExcludeCmIndex OBJECT-TYPE
        SYNTAX     	INTEGER (1..200)
        MAX-ACCESS  read-only
        STATUS      current
        DESCRIPTION
            "The index of cm's macRang."
        ::= { topCcmtsLoadBalExcludeCmEntry 1 }

topLoadBalExcludeCmMacRang OBJECT-TYPE
		SYNTAX     	OCTET STRING (SIZE (25..30))
        MAX-ACCESS  read-create
        STATUS      current
        DESCRIPTION
            "The string of macRang,the format is xx:xx:xx:xx:xx:xx yy:yy:yy:yy:yy:yy."
        ::= { topCcmtsLoadBalExcludeCmEntry 2 }  
        
topLoadBalExcludeCmStatus  OBJECT-TYPE
	SYNTAX          RowStatus
	MAX-ACCESS      read-create
	STATUS          current
	DESCRIPTION
		"Indicates the status of the rows in this table and can be used to destroy the specific row." 
	::= { topCcmtsLoadBalExcludeCmEntry 3 }
	
topCcmtsLoadBalPolicyTable OBJECT-TYPE
	SYNTAX SEQUENCE OF TopCcmtsLoadBalPolicyEntry
    MAX-ACCESS not-accessible
    STATUS current
    DESCRIPTION
		"This table describes the policy used by the CCMTS."
    ::= { topCcmtsLoadBalanceObject 4 }
    
topCcmtsLoadBalPolicyEntry OBJECT-TYPE
    SYNTAX TopCcmtsLoadBalPolicyEntry
    MAX-ACCESS not-accessible
    STATUS current
    DESCRIPTION
		"The row of the table."
	INDEX { ifIndex}
    ::= { topCcmtsLoadBalPolicyTable 1 }

TopCcmtsLoadBalPolicyEntry  ::= SEQUENCE {
	 topLoadBalPolicyId INTEGER
	}
	
topLoadBalPolicyId OBJECT-TYPE
        SYNTAX     	INTEGER (0..200)
        MAX-ACCESS  read-create
        STATUS      current
        DESCRIPTION
            "The policy is being used in the CCMTS."
        ::= { topCcmtsLoadBalPolicyEntry 1 }
 
 
 ------------------------------------------------     
--topCcmtsLoadBalGrpRestrictAllCmTable
--added by wupeng 2015.08.19
------------------------------------------------
 topCcmtsLoadBalGrpRestrictAllCmTable OBJECT-TYPE
	SYNTAX SEQUENCE OF TopCcmtsLoadBalGrpRestrictAllCmEntry 
    MAX-ACCESS not-accessible
    STATUS current
    DESCRIPTION
		"This table describes support the rest CMs will only bonding on the specific Group"
    ::= { topCcmtsLoadBalanceObject 5 }   
    
topCcmtsLoadBalGrpRestrictAllCmEntry OBJECT-TYPE
	SYNTAX TopCcmtsLoadBalGrpRestrictAllCmEntry 
	MAX-ACCESS not-accessible
	STATUS current
	DESCRIPTION
		"It is index by a docsLoadBalGrpId which is unique 	within a CMTS."
	INDEX { docsLoadBalGrpId}
	::= { topCcmtsLoadBalGrpRestrictAllCmTable 1 }   
	
TopCcmtsLoadBalGrpRestrictAllCmEntry  ::= SEQUENCE {
		topLoadBalGrpIncludeAllCm  INTEGER
	}   
	 	
topLoadBalGrpIncludeAllCm OBJECT-TYPE
	SYNTAX  INTEGER 
	{  
		Other(0),
		AddAllCm (1),
		DelAllCm (2)
	}
	MAX-ACCESS  read-write
	STATUS      current
	DESCRIPTION
	"Indicates the status of the rows in this table and can be used to set include all cm,
	the specific group must exist. 
	Set AddAllCm include all cm ,DelAllCm delete all cm from the specific group. Default is zero." 
	DEFVAL          { 0 }
	::= { topCcmtsLoadBalGrpRestrictAllCmEntry 1 }
	  
------------------------------------------------     
--topCcmtsLoadBalExcludeCmByGroupTable
--added by wupeng 2015.08.19
------------------------------------------------
 topCcmtsLoadBalExcludeCmByGroupTable OBJECT-TYPE
	SYNTAX SEQUENCE OF TopCcmtsLoadBalExcludeCmByGroupEntry 
    MAX-ACCESS not-accessible
    STATUS current
    DESCRIPTION
		"This table describes exclude CMs from the specific Group"
    ::= { topCcmtsLoadBalanceObject 6 }   
    
topCcmtsLoadBalExcludeCmByGroupEntry OBJECT-TYPE
	SYNTAX TopCcmtsLoadBalExcludeCmByGroupEntry 
	MAX-ACCESS not-accessible
	STATUS current
	DESCRIPTION
		"docsLoadBalGrpId: It is index by a docsLoadBalGrpId which is unique within a CMTS.
		docsLoadBalMacRangIndex: the index of exclude CM's macRang."
	INDEX { docsLoadBalGrpId,
			docsLoadBalMacRangIndex}
	::= { topCcmtsLoadBalExcludeCmByGroupTable 1 }   
	
	TopCcmtsLoadBalExcludeCmByGroupEntry  ::= SEQUENCE {  
		docsLoadBalMacRangIndex       		INTEGER,
		topLoadBalExcludeCmMacRangByGroup   OCTET STRING,
		topLoadBalExcludeCmByGroupStatus    RowStatus
	}   
	 	
docsLoadBalMacRangIndex OBJECT-TYPE
	SYNTAX     	INTEGER (1..200)
	MAX-ACCESS  read-only
	STATUS      current
	DESCRIPTION
	"The index of cm's macRang."
	::= { topCcmtsLoadBalExcludeCmByGroupEntry 1 } 
	
topLoadBalExcludeCmMacRangByGroup OBJECT-TYPE
	SYNTAX     	OCTET STRING (SIZE (25..30))
	MAX-ACCESS  read-write
	STATUS      current
	DESCRIPTION
		"The string of macRang,the format is xx:xx:xx:xx:xx:xx yy:yy:yy:yy:yy:yy."
	::= { topCcmtsLoadBalExcludeCmByGroupEntry 2 }
	
topLoadBalExcludeCmByGroupStatus  OBJECT-TYPE
	SYNTAX     		RowStatus
	MAX-ACCESS      read-write
	STATUS          current
	DESCRIPTION
		"Indicates the status of the rows in this table and can be used to destroy the specific row."
		DEFVAL          { 1 } 
	::= { topCcmtsLoadBalExcludeCmByGroupEntry 3 }  	
------------------------------------------------     
--topCcmtsLoadBalExcludeCmByGroupTable
--end by wupeng 2015.08.19
------------------------------------------------

------------------------------------------------     
--start by zhengdaqing for V300
------------------------------------------------

topCcmtsLoadBalExcludedCmTable OBJECT-TYPE
	SYNTAX SEQUENCE OF TopCcmtsLoadBalExcludedCmEntry 
    MAX-ACCESS not-accessible
    STATUS current
    DESCRIPTION
		"This table describes the CMs added into the global exclusion list of the load balancing. 
         A CM in this exclusion list will not be load balanced. "
    ::= { topCcmtsLoadBalanceObject 7 }
    
topCcmtsLoadBalExcludedCmEntry OBJECT-TYPE
    SYNTAX TopCcmtsLoadBalExcludedCmEntry 
    MAX-ACCESS not-accessible
    STATUS current
    DESCRIPTION
		"An entry of CMs is within the load balancing exclusion list."
	INDEX { ifIndex,
	        topLoadBalExcludedCmIndex}
    ::= { topCcmtsLoadBalExcludedCmTable 1 }

TopCcmtsLoadBalExcludedCmEntry  ::= SEQUENCE {
	 topLoadBalExcludedCmIndex INTEGER,
	 topLoadBalExcludedCmMacAddr MacAddress,
	 topLoadBalExcludedCmMacMask OCTET STRING,
	 topLoadBalExcludedCmStatus  RowStatus
	}
	
topLoadBalExcludedCmIndex OBJECT-TYPE
        SYNTAX     	INTEGER (1..1000)
        MAX-ACCESS  read-only
        STATUS      current
        DESCRIPTION
            "The index that uniquely identifies an entry which represents excluded cable modem(s)."
        ::= { topCcmtsLoadBalExcludedCmEntry 1 }

topLoadBalExcludedCmMacAddr OBJECT-TYPE
    SYNTAX MacAddress
    MAX-ACCESS read-create
    STATUS current
    DESCRIPTION
		"MAC address of the cable modem without the load-balancing."
        ::= { topCcmtsLoadBalExcludedCmEntry 2 }  
        
topLoadBalExcludedCmMacMask OBJECT-TYPE
    SYNTAX OCTET STRING (SIZE (0 | 6))
    MAX-ACCESS read-create
    STATUS current
    DESCRIPTION
		"A bit mask acting as a wild card to associate a set
		 of modem MAC addresses."
    DEFVAL { ''h }
        ::= { topCcmtsLoadBalExcludedCmEntry 3 }  
		
topLoadBalExcludedCmStatus  OBJECT-TYPE
	SYNTAX          RowStatus {active(1),createAndGo(4),destroy(6)}
	MAX-ACCESS      read-create
	STATUS          current
	DESCRIPTION
		"Indicates or change the status of the rows in this table.
         createAndGo or destroy is supported to create or destroy a CMs. After an entry is created, the state changes to active." 
	::= { topCcmtsLoadBalExcludedCmEntry 4 }

 topCcmtsLoadBalGrpExcludedCmTable OBJECT-TYPE
	SYNTAX SEQUENCE OF TopCcmtsLoadBalGrpExcludedCmEntry 
    MAX-ACCESS not-accessible
    STATUS current
    DESCRIPTION
		"Describes the excluded CMs in the load balancing group."
    ::= { topCcmtsLoadBalanceObject 8 }   
    
topCcmtsLoadBalGrpExcludedCmEntry OBJECT-TYPE
	SYNTAX TopCcmtsLoadBalGrpExcludedCmEntry 
	MAX-ACCESS not-accessible
	STATUS current
	DESCRIPTION
		"An entry of CMs is within the restricted load balancing group."
	INDEX { docsLoadBalGrpId,
	        topLoadBalGrpExcludedMacIndex}
	::= { topCcmtsLoadBalGrpExcludedCmTable 1 }   
	
TopCcmtsLoadBalGrpExcludedCmEntry  ::= SEQUENCE {  
		topLoadBalGrpExcludedMacIndex       INTEGER,
		topLoadBalGrpExcludedCmMacAddr      MacAddress,
		topLoadBalGrpExcludedCmMacMask      OCTET STRING,
		topLoadBalGrpExcludedCmStatus       RowStatus
	}   
	 	
topLoadBalGrpExcludedMacIndex OBJECT-TYPE
	SYNTAX     	INTEGER (1..1000)
	MAX-ACCESS  read-only
	STATUS      current
	DESCRIPTION
	"The index that uniquely identifies an entry which represents excluded cable modem(s) in the load balancing group."
	::= { topCcmtsLoadBalGrpExcludedCmEntry 1 } 
	
topLoadBalGrpExcludedCmMacAddr OBJECT-TYPE
    SYNTAX MacAddress
    MAX-ACCESS read-create
    STATUS current
    DESCRIPTION
		"Mac Address of the cable modem without the load-balancing group."
	::= { topCcmtsLoadBalGrpExcludedCmEntry 2 }

topLoadBalGrpExcludedCmMacMask  OBJECT-TYPE
    SYNTAX OCTET STRING (SIZE (0 | 6))
    MAX-ACCESS read-create
    STATUS current
    DESCRIPTION
		"A bit mask acting as a wild card to associate a set of modem MAC addresses."
    DEFVAL { ''h }
	::= { topCcmtsLoadBalGrpExcludedCmEntry 3 }
	
topLoadBalGrpExcludedCmStatus  OBJECT-TYPE
	SYNTAX          RowStatus {active(1),createAndGo(4),destroy(6)}
	MAX-ACCESS      read-create
	STATUS          current
	DESCRIPTION
		"Indicates or change the status of the rows in this table.
         createAndGo or destroy is supported to create or destroy a CMs. After an entry is created, the state changes to active."
		DEFVAL          { 1 } 
	::= { topCcmtsLoadBalGrpExcludedCmEntry 4 }  	
 
 topCcmtsLoadBalGrpRestrictCmStatusTable OBJECT-TYPE
	SYNTAX SEQUENCE OF TopCcmtsLoadBalGrpRestrictCmStatusEntry 
    MAX-ACCESS not-accessible
    STATUS current
    DESCRIPTION
		"Describes all the MACs of the restricted load balancing group configured to 'addAllCm', the MACs is the rest inversed MACs calculated automatically via the excluded MACs in the group."
    ::= { topCcmtsLoadBalanceObject 9 } 
    
topCcmtsLoadBalGrpRestrictCmStatusEntry OBJECT-TYPE
	SYNTAX TopCcmtsLoadBalGrpRestrictCmStatusEntry 
	MAX-ACCESS not-accessible
	STATUS current
	DESCRIPTION
		"An entry of CMs is within the restricted load balancing group."
	INDEX { docsLoadBalGrpId, 
	        topLoadBalGrpRestrictedCmIndex}
	::= { topCcmtsLoadBalGrpRestrictCmStatusTable 1 }   
	
TopCcmtsLoadBalGrpRestrictCmStatusEntry  ::= SEQUENCE {  
		topLoadBalGrpRestrictedCmIndex      INTEGER,
		topLoadBalGrpRestrictedCmStartMac   MacAddress,
		topLoadBalGrpRestrictedCmEndMac     MacAddress
	}   
	 	
topLoadBalGrpRestrictedCmIndex OBJECT-TYPE
	SYNTAX     	INTEGER (1..1001)
	MAX-ACCESS  read-only
	STATUS      current
	DESCRIPTION
	    "The index references an unique instance per Start/End MAC Address combination."
	::= { topCcmtsLoadBalGrpRestrictCmStatusEntry 1 } 
	
topLoadBalGrpRestrictedCmStartMac OBJECT-TYPE
    SYNTAX MacAddress
    MAX-ACCESS read-only
    STATUS current
    DESCRIPTION
		"The starting MAC address of the cable modem within the load-balancing group."
	::= { topCcmtsLoadBalGrpRestrictCmStatusEntry 2 }	

topLoadBalGrpRestrictedCmEndMac OBJECT-TYPE
    SYNTAX MacAddress
    MAX-ACCESS read-only
    STATUS current
    DESCRIPTION
		"The ending MAC address of the cable modem within the load-balancing group."
	::= { topCcmtsLoadBalGrpRestrictCmStatusEntry 3 }	
		
------------------------------------------------     
--end by zhengdaqing for V300
------------------------------------------------

------------------------------------------------
--topCcmtsLoadBalDynamicMoveInfoTable
--add by hzh for v300
--data: dec.4.2017
------------------------------------------------
topCcmtsLoadBalDynamicMoveInfoStatsTable OBJECT-TYPE
	SYNTAX SEQUENCE OF TopCcmtsLoadBalDynamicMoveInfoStatsEntry 
    MAX-ACCESS not-accessible
    STATUS current
    DESCRIPTION
		"This table describes the Statistics of load balancing operation  "
    ::= { topCcmtsLoadBalanceObject 10 }

topCcmtsLoadBalDynamicMoveInfoStatsEntry OBJECT-TYPE
    SYNTAX TopCcmtsLoadBalDynamicMoveInfoStatsEntry 
    MAX-ACCESS not-accessible
    STATUS current
    DESCRIPTION
		"An entry of Statistics of load balancing operation. "
	INDEX { topLoadBalDynamicMoveInfoStatsCmtsIfIndex}
    ::= { topCcmtsLoadBalDynamicMoveInfoStatsTable 1 }
 
TopCcmtsLoadBalDynamicMoveInfoStatsEntry  ::= SEQUENCE {
	 topLoadBalDynamicMoveInfoStatsCmtsIfIndex Unsigned32,
	 topLoadBalDynamicMoveInfoStatsCmtsStatus INTEGER,
	 topLoadBalDynamicMoveInfoStatsTransferComplete INTEGER,
	 topLoadBalDynamicMoveInfoStatsTransferPending INTEGER,
	 topLoadBalDynamicMoveInfoStatsTransferFailures INTEGER
	}

topLoadBalDynamicMoveInfoStatsCmtsIfIndex OBJECT-TYPE
    SYNTAX Unsigned32 (1..4294967295)
    MAX-ACCESS read-only
    STATUS current
    DESCRIPTION
		"The Index of Cmts. "
        ::= { topCcmtsLoadBalDynamicMoveInfoStatsEntry 1 }   
        
topLoadBalDynamicMoveInfoStatsCmtsStatus  OBJECT-TYPE
	SYNTAX          INTEGER {enable(1),
								disable(2)}
	MAX-ACCESS      read-only
	STATUS          current
	DESCRIPTION
		"The Status of Cmts:
		1:load-balance mode on
		2:load-balance mode off  ." 
	    ::= { topCcmtsLoadBalDynamicMoveInfoStatsEntry 2 }
	
topLoadBalDynamicMoveInfoStatsTransferComplete OBJECT-TYPE
	SYNTAX     	INTEGER (0..350)
	MAX-ACCESS  read-only
	STATUS      current
	DESCRIPTION
		"The number of times that the Cable Modems were successfully moved to the target interface" 
    	DEFVAL          { 0 }			
		::= { topCcmtsLoadBalDynamicMoveInfoStatsEntry 3 } 	
    
topLoadBalDynamicMoveInfoStatsTransferPending OBJECT-TYPE
	SYNTAX     	INTEGER (0..350)
	MAX-ACCESS  read-only
	STATUS      current
	DESCRIPTION
	"The number of  Cable Modems that are in the process of  being move to the target interface" 
	DEFVAL          { 0 } 	
	::= { topCcmtsLoadBalDynamicMoveInfoStatsEntry 4 } 	
	    
topLoadBalDynamicMoveInfoStatsTransferFailures OBJECT-TYPE
	SYNTAX     	INTEGER (0..350)
	MAX-ACCESS  read-only
	STATUS      current
	DESCRIPTION
	"The number of times that the Cable Modems were failed moved to the target interface"  
    DEFVAL          { 0 }	
	::= { topCcmtsLoadBalDynamicMoveInfoStatsEntry 5 } 
		
------------------------------------------------
---end by hzh
------------------------------------------------ 

------------------------------------------------
--topCcmtsLoadBalDynamicMoveInfoTable
--add by hzh for v300
--data: dec.4.2017
------------------------------------------------
topCcmtsLoadBalDynamicMoveInfoTable OBJECT-TYPE
	SYNTAX SEQUENCE OF TopCcmtsLoadBalDynamicMoveInfoEntry 
    MAX-ACCESS not-accessible
    STATUS current
    DESCRIPTION
		"This table describes the Records of load balancing operation  "
    ::= { topCcmtsLoadBalanceObject 11 }

topCcmtsLoadBalDynamicMoveInfoEntry OBJECT-TYPE
    SYNTAX TopCcmtsLoadBalDynamicMoveInfoEntry 
    MAX-ACCESS not-accessible
    STATUS current
    DESCRIPTION
		"An entry of Records of load balancing operation. "
	INDEX { topLoadBalDynamicMoveInfoCmtsIfIndex,topLoadBalDynamicMoveInfoTransferTime}
    ::= { topCcmtsLoadBalDynamicMoveInfoTable 1 }

TopCcmtsLoadBalDynamicMoveInfoEntry  ::= SEQUENCE {	 
	 topLoadBalDynamicMoveInfoCmtsIfIndex  Unsigned32,
	 topLoadBalDynamicMoveInfoTransferTime TimeStamp, 
	 topLoadBalDynamicMoveInfoCmMacAddr	   MacAddress,
	 topLoadBalDynamicMoveInfoSrcUpstream  ChannelList,
	 topLoadBalDynamicMoveInfoDstUpstream  ChannelList,
	 topLoadBalDynamicMoveInfoSrcDownstream ChannelList,
	 topLoadBalDynamicMoveInfoDstDownstream ChannelList,
	 topLoadBalDynamicMoveInfoInitTech      ChChgInitTechMap,
	 topLoadBalDynamicMoveInfoCmd           INTEGER,
	 topLoadBalDynamicMoveInfoResult        INTEGER
	} 

topLoadBalDynamicMoveInfoCmtsIfIndex OBJECT-TYPE
	SYNTAX     	Unsigned32 (1..4294967295)
	MAX-ACCESS  read-only
	STATUS      current
	DESCRIPTION
	"The Index of Cmts. "
	::= { topCcmtsLoadBalDynamicMoveInfoEntry 1 }

topLoadBalDynamicMoveInfoTransferTime OBJECT-TYPE
	SYNTAX     	TimeStamp
	MAX-ACCESS  read-only
	STATUS      current
	DESCRIPTION
	"The system-up time that the cmts were moving the Cable Modems to the target interface"
	::= { topCcmtsLoadBalDynamicMoveInfoEntry 2 }

topLoadBalDynamicMoveInfoCmMacAddr  OBJECT-TYPE
	SYNTAX     	MacAddress
	MAX-ACCESS  read-only
	STATUS      current
	DESCRIPTION
	"The MAC Address of Cable Modems"
	::= { topCcmtsLoadBalDynamicMoveInfoEntry 3 }
 
topLoadBalDynamicMoveInfoSrcUpstream  OBJECT-TYPE
	SYNTAX     	ChannelList
	MAX-ACCESS  read-only
	STATUS      current
	DESCRIPTION
	"The old Upstream Channels that the Cable Modems were on" 
    DEFVAL          { ''H }	
	::= { topCcmtsLoadBalDynamicMoveInfoEntry 4 }
    	
topLoadBalDynamicMoveInfoDstUpstream  OBJECT-TYPE
	SYNTAX     	ChannelList
	MAX-ACCESS  read-only
	STATUS      current
	DESCRIPTION
	"the new Upstream Channels that the Cable Modems were moved to" 
    DEFVAL          { ''H }	
	::= { topCcmtsLoadBalDynamicMoveInfoEntry 5 }
    	
topLoadBalDynamicMoveInfoSrcDownstream  OBJECT-TYPE
	SYNTAX     	ChannelList
	MAX-ACCESS  read-only
	STATUS      current
	DESCRIPTION
	"The old Downstream Channels that the Cable Modems were on" 
    DEFVAL          { ''H }		
	::= { topCcmtsLoadBalDynamicMoveInfoEntry 6 }

    
topLoadBalDynamicMoveInfoDstDownstream  OBJECT-TYPE
	SYNTAX     	ChannelList
	MAX-ACCESS  read-only
	STATUS      current
	DESCRIPTION
	"the new Downstream Channels that the Cable Modems were moved to " 
    DEFVAL          { ''H }	
	::= { topCcmtsLoadBalDynamicMoveInfoEntry 7 }
    
topLoadBalDynamicMoveInfoInitTech  OBJECT-TYPE
	SYNTAX     	ChChgInitTechMap
	MAX-ACCESS  read-only
	STATUS      current
	DESCRIPTION
      "This attribute represents the initialization technique
        that the cable modem is instructed to use when
        performing multiple-channel change-over operation." 
	::= { topCcmtsLoadBalDynamicMoveInfoEntry 8 }

topLoadBalDynamicMoveInfoCmd  OBJECT-TYPE
	SYNTAX     	INTEGER {
	            	dcc(1),
	            	dbc(2)
				}
	MAX-ACCESS  read-only
	STATUS      current
	DESCRIPTION
	"The load balancing MAC Management Message exchange type used by the CMTS "
	::= { topCcmtsLoadBalDynamicMoveInfoEntry 9 }

topLoadBalDynamicMoveInfoResult  OBJECT-TYPE
	SYNTAX     	INTEGER{
	    				   success(0),
	    				   pending(1),
	    				   partialService(2),
		                   cmtsAbortTimeout(3),
		                   cmtsAbortOther(4),
	                       cmtsAbortCmOffline(5),
	                       cmtsAbortIfDown(6),
	                       cmtsAbortNoCm(7),
	                       cmtsAbortNoResource(8),
	                       cmtsAbortNoChange(9),
	                       cmRejectSyntaxError(10),
	                       cmRejectBadRcc(11),
	                       cmRejectBadTcc(12),
	                       cmRejectBadClusterAssignment(13) ,
	                       cmRejectBadDSIDEncoding(14) ,
	                       cmRejectOther(15)}
	MAX-ACCESS  read-only
	STATUS      current
	DESCRIPTION
	"This attribute represents the status of the load-balancing operation. 
	The value can't be:
	success:                      the CM has been move to the target interface success
	pending:                      the CM is in the process of  being move to the target interface
	partialService:               the CM unable to use one or more channels as instructed in the DBC-REQ
	cmtsAbortTimeout:             the CMTS Abort the transaction due to the times of retries exceed the limitation
	cmtsAbortOther:               the CMTS Abort the transaction due to Other reason
	cmtsAbortCmOffline:           the CMTS Abort the transaction due to the specified CM was Offline
	cmtsAbortIfDown:              the CMTS Abort the transaction due to the target interface has been shutdown
	cmtsAbortNoCm:                the CMTS Abort the transaction due to the specified CM wasn't exist
	cmtsAbortNoResource:          the CMTS Abort the transaction due to insufficient resource on target
	cmtsAbortNoChange:            the CMTS Abort the transaciton due to the CM already using the interface specified
	cmRejectSyntaxError:          the CM reject the dcc-req/dbc-req due to the syntax Error in req message
	cmRejectBadRCC:               the CM reject the dbc-req due to the req message contained invalied Receive Channel Configuration
	cmRejectBadTCC:               the CM reject the dbc-req due to the req message contianed invalied Transmit Channel Configuration
	cmRejectBadClusterAssignment: the CM reject the dbc-req due to the req message contained invalid Cluster Assignment
	cmRejectBadDSIDEncoding:      the CM reject the dbc-req due to the req message contained invalid DSID Encoding
	cmRejectRejectOther:          the CM reject the dbc-req due to other reason"
	::= { topCcmtsLoadBalDynamicMoveInfoEntry 10 }
	
------------------------------------------------
---end by hzh
------------------------------------------------
topCcmtsHeartbeatTrapObject	OBJECT IDENTIFIER ::={ topCcmtsMibObject 15 } 
     
topCcmtsHeartbeatTrapCounter OBJECT-TYPE
	SYNTAX		INTEGER
	MAX-ACCESS	not-accessible
	STATUS		current
	DESCRIPTION
		"The trap counter"
	::={ topCcmtsHeartbeatTrapObject 1}
   
topCcmtsManagementIp OBJECT-TYPE
	SYNTAX		IpAddress
	MAX-ACCESS	not-accessible
	STATUS		current
	DESCRIPTION
		"The IP address of management interface"
	::={ topCcmtsHeartbeatTrapObject 2}

------------------------------------------------     
--topCcmtsObject
--added by liubin at July.12 2013
------------------------------------------------
topCcmtsObject OBJECT IDENTIFIER ::={ topCcmtsMibObject 18 }

topCcmtsSysCfgTable OBJECT-TYPE
	SYNTAX   	SEQUENCE OF  TopCcmtsSysCfgEntry
	MAX-ACCESS	not-accessible
	STATUS		current
	DESCRIPTION
		"config for each CMTS" 
	::={ topCcmtsObject 1 }

topCcmtsSysCfgEntry OBJECT-TYPE
	SYNTAX		TopCcmtsSysCfgEntry
	MAX-ACCESS	not-accessible
	STATUS		current
	DESCRIPTION	
		"The row of the table"
	INDEX	    { ifIndex }  
	::={ topCcmtsSysCfgTable 1 }   
	
TopCcmtsSysCfgEntry ::=SEQUENCE{
   topCcmtsSysCfgPiggyback INTEGER,
   topCcmtsSysCfgUdcEnable INTEGER,
   topCcmtsSysCfgInactiveTimeout INTEGER,
   topCcmtsSysCfgCmPollingState INTEGER
}

topCcmtsSysCfgPiggyback  OBJECT-TYPE
	SYNTAX		INTEGER {
						true(1),
						false(2)
				}
	MAX-ACCESS	read-write
	STATUS		current
	DESCRIPTION	
		"Piggyback switch for each C-CMTS. Set true(1) to enable piggyback,false(2) to disable"   
	::={ topCcmtsSysCfgEntry 1 }
	    
topCcmtsSysCfgUdcEnable  OBJECT-TYPE
	SYNTAX		INTEGER {
						true(1),
						false(2)
				}
	MAX-ACCESS	read-write
	STATUS		current
	DESCRIPTION	
		"UDC switch for each C-CMTS. Set true(1) to enable udc,false(2) to disable"   
	::={ topCcmtsSysCfgEntry 2 }       
  
topCcmtsSysCfgInactiveTimeout  OBJECT-TYPE
	SYNTAX		INTEGER (30..65535) 

	MAX-ACCESS	read-write
	STATUS		current
	DESCRIPTION	
		"InactiveTimeout for each C-CMTS. Set CM Dynamic service flow inactive timeout,The rang is [0|30~65535]"   
	::={ topCcmtsSysCfgEntry 3 }           
  
topCcmtsSysCfgCmPollingState  OBJECT-TYPE
	SYNTAX		INTEGER {
						true(1),
						false(2)
				}
	MAX-ACCESS	read-write
	STATUS		current
	DESCRIPTION	
		"CM polling switch for each C-CMTS. 
		Set true(1) to enable polling, false(2) to disable and then 
		docsIfCmtsCmStatusTable could got real-time data. 
		You will get real-time data if set true(1) but set topCcmtsCmPollingPeriod to zero."
	DEFVAL    { 1 }
	::={ topCcmtsSysCfgEntry 4 }

topCcmtsGlobal OBJECT IDENTIFIER ::={ topCcmtsObject 2 }  
 
topUpChannelSignalQualityRealTimeSnmpDataStatus OBJECT-TYPE
 	SYNTAX		INTEGER {
						enable(1),
						disable(2)
				}
        MAX-ACCESS  read-write
        STATUS      current   
        DESCRIPTION
            "CMTS upstream channels' signal quality Polling Status.
            enable(1): You will get real-time docsIfSignalQualityTable.
            disable(2):You can get docsIfSignalQualityTable immediately,
                       but its data is old,which is from polling."   
        DEFVAL          { enable }

        ::= { topCcmtsGlobal 1 }
topCcmtsCmPollingPeriod OBJECT-TYPE
 	SYNTAX		INTEGER
	MAX-ACCESS  read-write
	STATUS      current   
	DESCRIPTION
		"CM Polling period.
		You will get real-time docsIfCmtsCmStatusTable if set the node to zero."
	::= { topCcmtsGlobal 2 }

------------------------------------------------     
--topCcmtsCmNumMonitorObject
--added by liubin at Sept.5 2013
------------------------------------------------
topCcmtsCmMonitorObject OBJECT IDENTIFIER ::={ topCcmtsMibObject 20 }

topCcmtsCmMonitorDroppedObject OBJECT IDENTIFIER ::={ topCcmtsCmMonitorObject 1 }

topCcmtsCmMonitorDroppedAdminStatus OBJECT-TYPE
    SYNTAX INTEGER {
    				enable(1),
    				disable(2)
    				}
    MAX-ACCESS read-write
    STATUS current
    DESCRIPTION
		"Global switch status ,set enable(1) to enable disable(2) to disable"
	DEFVAL          { disable }
    ::= { topCcmtsCmMonitorDroppedObject 1 }
    
topCcmtsCmMonitorDroppedReference OBJECT-TYPE
    SYNTAX INTEGER  (1..512)
    MAX-ACCESS read-write
    STATUS current
    DESCRIPTION
		"Reference cm number used to select the appropriate threshold"
	DEFVAL          { 50 }
    ::= { topCcmtsCmMonitorDroppedObject 2 }
	
topCcmtsCmMonitorDroppedThresholdNum OBJECT-TYPE
    SYNTAX INTEGER  (1..512)
    MAX-ACCESS read-write
    STATUS current
    DESCRIPTION
		"Num threshold"
	DEFVAL          { 10 }
    ::= { topCcmtsCmMonitorDroppedObject 3 }

topCcmtsCmMonitorDroppedThresholdPercent OBJECT-TYPE
    SYNTAX INTEGER  (1..100)
    MAX-ACCESS read-write
    STATUS current
    DESCRIPTION
		"Percent threshold"
	DEFVAL          { 20 }
    ::= { topCcmtsCmMonitorDroppedObject 4 }   
    
topCcmtsCmMonitorDroppedInterval OBJECT-TYPE
    SYNTAX INTEGER  (30..1800)
    MAX-ACCESS read-write
    STATUS current
    DESCRIPTION
		"Polling interval for cm num monitor"
	DEFVAL          { 60 }
    ::= { topCcmtsCmMonitorDroppedObject 5 }   
    
topCcmtsCmMonitorDroppedTimeStart OBJECT-TYPE
    SYNTAX INTEGER  (0..86400)
    MAX-ACCESS read-write
    STATUS current
    DESCRIPTION
		"Start time of monitor time"
	DEFVAL          { 0 }
    ::= { topCcmtsCmMonitorDroppedObject 6 }

topCcmtsCmMonitorDroppedTimeEnd OBJECT-TYPE
    SYNTAX INTEGER  (0..86400)
    MAX-ACCESS read-write
    STATUS current
    DESCRIPTION
		"End time of monitor time"
	DEFVAL          { 86400 }
    ::= { topCcmtsCmMonitorDroppedObject 7 }   
    
------------------------------------------------     
--topCcmtsCmNumMonitorObject
--added by lvhaiting at Sept.11 2013
------------------------------------------------

topCcmtsCmMonitorSpecificObject OBJECT IDENTIFIER ::={ topCcmtsCmMonitorObject 2 }

topCcmtsCmMonitorSpecificGlobalCfgObject OBJECT IDENTIFIER ::={ topCcmtsCmMonitorSpecificObject 1 }

topCcmtsCmMonitorSpecificAdminStatus OBJECT-TYPE
    SYNTAX INTEGER {
    				enable(1),
    				disable(2)
    				}
    MAX-ACCESS read-write
    STATUS current
    DESCRIPTION
		"specific cable modem monitor global switch status 
		set enable(1) to enable disable(2) to disable"
	DEFVAL          { disable }
    ::= { topCcmtsCmMonitorSpecificGlobalCfgObject 1 } 
    
topCcmtsCmMonitorSpecificMode OBJECT-TYPE
    SYNTAX INTEGER {
    				all(1),
    				normal(2)
    				}
    MAX-ACCESS read-write
    STATUS current
    DESCRIPTION
		"specific cable modem monitor global working mode 
		set all(1) to monitor all the modems, normal(2) to monitor modems in specified list"
	DEFVAL          { normal }
    ::= { topCcmtsCmMonitorSpecificGlobalCfgObject 2 } 

    
topCcmtsCmMonitorSpecificCmTable OBJECT-TYPE
	SYNTAX		SEQUENCE OF TopCcmtsCmMonitorSpecificCmEntry	
	MAX-ACCESS	not-accessible
	STATUS		current
	DESCRIPTION
		"specify a list indicates which modems will be monitored"
	::={ topCcmtsCmMonitorSpecificObject 2 } 
		
topCcmtsCmMonitorSpecificCmEntry OBJECT-TYPE
	SYNTAX		TopCcmtsCmMonitorSpecificCmEntry
	MAX-ACCESS	not-accessible
	STATUS		current
	DESCRIPTION
		"specify a list indicates which modems will be monitored"
	INDEX { topCcmtsSpecificCmMac }
	::= { topCcmtsCmMonitorSpecificCmTable 1 }
	
TopCcmtsCmMonitorSpecificCmEntry ::=SEQUENCE{
	topCcmtsSpecificCmMac	MacAddress,
	topCcmtsSpecificDesc	OCTET STRING,
    topCcmtsSpecificRowStatus	RowStatus
	}

topCcmtsSpecificCmMac OBJECT-TYPE
	SYNTAX		MacAddress
	MAX-ACCESS	not-accessible
	STATUS		current
	DESCRIPTION
		"the MAC address of cable modem which will be monitored"
	::={ topCcmtsCmMonitorSpecificCmEntry 1 }
	
topCcmtsSpecificDesc OBJECT-TYPE
	SYNTAX		OCTET STRING (SIZE (1..36))
	MAX-ACCESS	read-create
	STATUS		current
	DESCRIPTION
		"description of cable modem which will be monitored, optional"
	::={ topCcmtsCmMonitorSpecificCmEntry 2 }
	
topCcmtsSpecificRowStatus OBJECT-TYPE
	SYNTAX		RowStatus
	MAX-ACCESS	read-create
	STATUS		current
	DESCRIPTION
		"rowstatus"
	::={ topCcmtsCmMonitorSpecificCmEntry 3 }	


------------------------------------------------     
--topCcmtsVpnObject
--added by lixian at Oct.30 2015
------------------------------------------------
topCcmtsVpnObject OBJECT IDENTIFIER ::={ topCcmtsMibObject 25 }

topCcmtsL2VpnCableSourceVerifyTable OBJECT IDENTIFIER ::={ topCcmtsVpnObject 1 }

topCcmtsL2VpnCableSourceVerifyEntry OBJECT IDENTIFIER ::={ topCcmtsL2VpnCableSourceVerifyTable 1 }

topCcmtsL2VpnCableSourceVerifyIPv4 OBJECT-TYPE
    SYNTAX INTEGER {
    				enable(1),
    				disable(2)
    				}
    MAX-ACCESS read-write
    STATUS deprecated
    DESCRIPTION
		"Global switch for l2vpn cable source verify in IPv4,
		set enable(1) to enable or disable(2) to disable."
	DEFVAL          { enable }
    ::= { topCcmtsL2VpnCableSourceVerifyEntry 1 }

topCcmtsL2VpnCableSourceVerifyIPv6 OBJECT-TYPE
    SYNTAX INTEGER {
    				enable(1),
    				disable(2)
    				}
    MAX-ACCESS read-write
    STATUS deprecated
    DESCRIPTION
		"Global switch for l2vpn cable source verify in IPv6,
		set enable(1) to enable or disable(2) to disable."
	DEFVAL          { enable }
    ::= { topCcmtsL2VpnCableSourceVerifyEntry 2 }

topCcmtsMdL2VpnCableSourceVerifyTable OBJECT-TYPE
	SYNTAX		SEQUENCE OF TopCcmtsMdL2VpnCableSourceVerifyEntry	
	MAX-ACCESS	not-accessible
	STATUS		current
	DESCRIPTION
		"MAC domain's L2vpn cable source verify swtich table."
	::={ topCcmtsVpnObject 2 }

----
topCcmtsMdL2VpnCableSourceVerifyEntry OBJECT-TYPE
	SYNTAX		TopCcmtsMdL2VpnCableSourceVerifyEntry
	MAX-ACCESS	not-accessible
	STATUS		current
	DESCRIPTION	
		"L2vpn cable source verify swtich Entry"
	INDEX  { ifIndex }
	::={ topCcmtsMdL2VpnCableSourceVerifyTable 1 }  

TopCcmtsMdL2VpnCableSourceVerifyEntry ::=SEQUENCE{
	topCcmtsMdL2VpnCableSourceVerifyIPv4		       INTEGER,  
	topCcmtsMdL2VpnCableSourceVerifyIPv6       	       INTEGER
} 

topCcmtsMdL2VpnCableSourceVerifyIPv4 OBJECT-TYPE
    SYNTAX INTEGER {
    				enable(1),
    				disable(2)
    				}
    MAX-ACCESS read-write
    STATUS current
    DESCRIPTION
		"MAC domain switch for l2vpn cable source verify in IPv4,
		set enable(1) to enable or disable(2) to disable."
	DEFVAL          { enable }
    ::= { topCcmtsMdL2VpnCableSourceVerifyEntry 1 }

topCcmtsMdL2VpnCableSourceVerifyIPv6 OBJECT-TYPE
    SYNTAX INTEGER {
    				enable(1),
    				disable(2)
    				}
    MAX-ACCESS read-write
    STATUS current
    DESCRIPTION
		"MAC domain switch for l2vpn cable source verify in IPv6,
		set enable(1) to enable or disable(2) to disable."
	DEFVAL          { enable }
    ::= { topCcmtsMdL2VpnCableSourceVerifyEntry 2 }

topCcmtsNetSecurityObject OBJECT IDENTIFIER ::={ topCcmtsMibObject 26 }
topCcmtsSavObject OBJECT IDENTIFIER ::={ topCcmtsNetSecurityObject 1 }
                                                                    
topCcmtsSavExceptionTable OBJECT-TYPE
	SYNTAX		SEQUENCE OF TopCcmtsSavExceptionListEntry	
	MAX-ACCESS	not-accessible
	STATUS		current
	DESCRIPTION
		"Specify a SAV Exception IP"
	::={ topCcmtsSavObject 1 } 
                                                                                          
----
topCcmtsSavExceptionListEntry OBJECT-TYPE
	SYNTAX		TopCcmtsSavExceptionListEntry
	MAX-ACCESS	not-accessible
	STATUS		current
	DESCRIPTION	
		"SAV Exception IP Entry"
	INDEX  { ifIndex, topCcmtsSavExceptionIpType , topCcmtsSavExceptionIp }
	::={ topCcmtsSavExceptionTable 1 }  

TopCcmtsSavExceptionListEntry ::=SEQUENCE{
	topCcmtsSavExceptionIpType		       InetAddressType,  
	topCcmtsSavExceptionIp       	       InetAddress,
	topCcmtsSavExceptionIpMaskType         InetAddressType,
	topCcmtsSavExceptionIpMask             InetAddress,
	topCcmtsSavExceptionListRowstatus      RowStatus
}

topCcmtsSavExceptionIpType OBJECT-TYPE
	SYNTAX		InetAddressType
	MAX-ACCESS	not-accessible
	STATUS		current
	DESCRIPTION
		"SAV Exception IP Type"
	::={ topCcmtsSavExceptionListEntry 1 }  
	
topCcmtsSavExceptionIp OBJECT-TYPE
	SYNTAX		InetAddress
	MAX-ACCESS	not-accessible
	STATUS		current
	DESCRIPTION
		"SAV Exception IP."
	::={ topCcmtsSavExceptionListEntry 2 }

topCcmtsSavExceptionIpMaskType OBJECT-TYPE
	SYNTAX		InetAddressType
	MAX-ACCESS	read-create
	STATUS		current
	DESCRIPTION
		"SAV Exception IP Mask Type"
	::={ topCcmtsSavExceptionListEntry 3 }

topCcmtsSavExceptionIpMask OBJECT-TYPE
	SYNTAX		InetAddress
	MAX-ACCESS	read-create
	STATUS		current
	DESCRIPTION
		"SAV Exception IP Mask Address"
	::={ topCcmtsSavExceptionListEntry 4 }

topCcmtsSavExceptionListRowstatus OBJECT-TYPE
	SYNTAX		RowStatus
	MAX-ACCESS	read-create
	STATUS		current
	DESCRIPTION
		"Row Status."
	::={ topCcmtsSavExceptionListEntry 5 } 
		
----------------------------------------------     
--topCcmtsCmUpgradeObject
--added by lihuanyong at oct.6 2016
----------------------------------------------
topCcmtsCmUpgradeObject OBJECT IDENTIFIER ::={ topCcmtsMibObject 28 } 

topCcmtsSingleCmUpgradeObject OBJECT IDENTIFIER ::={ topCcmtsCmUpgradeObject 1 }

topCcmtsSingleCmUpgradeCmMac OBJECT-TYPE
	SYNTAX		MacAddress
	MAX-ACCESS	read-write
	STATUS		current
	DESCRIPTION
		"the MAC address of cable modem which will be upgraded"
	::={ topCcmtsSingleCmUpgradeObject 1 } 
    
topCcmtsSingleCmUpgradeImageFileName OBJECT-TYPE
    SYNTAX          DisplayString (SIZE (0..64))
    MAX-ACCESS      read-write
    STATUS          current
    DESCRIPTION
        "the name of the image file used to upgrade." 
    ::= { topCcmtsSingleCmUpgradeObject 2 }
 	
topCcmtsSingleCmUpgradeAction OBJECT-TYPE
    SYNTAX          INTEGER  { 
			noOperation(0),
			upgrade(1)
			}
    MAX-ACCESS      read-write
    STATUS          current
    DESCRIPTION
        "This object is used to trigger an upgrade operation." 
    ::= { topCcmtsSingleCmUpgradeObject 3 }  
    
topCcmtsCmAutoUpgradeObject OBJECT IDENTIFIER ::={ topCcmtsCmUpgradeObject 2 }

topCcmtsCmAutoUpgradeEnable OBJECT-TYPE
    SYNTAX          INTEGER  { 
			enable(1),
			disable(2)
			}
    MAX-ACCESS      read-write
    STATUS          current
    DESCRIPTION
        "This object is used to enable/disable auto upgrade CM." 
    ::= { topCcmtsCmAutoUpgradeObject 1 } 
    
topCcmtsCmAutoUpgradeCfgTable OBJECT-TYPE
	SYNTAX		SEQUENCE OF TopCcmtsCmAutoUpgradeCfgEntry	
	MAX-ACCESS	not-accessible
	STATUS		current
	DESCRIPTION
		"The entry of cm auto upgrade configuration."
	::={ topCcmtsCmAutoUpgradeObject 2 } 
	
topCcmtsCmAutoUpgradeCfgEntry OBJECT-TYPE
	SYNTAX		TopCcmtsCmAutoUpgradeCfgEntry
	MAX-ACCESS	not-accessible
	STATUS		current
	DESCRIPTION
		"the row define of the table."
	INDEX { topCcmtsCmAutoUpgradeCmModelNum }
	::= { topCcmtsCmAutoUpgradeCfgTable 1 } 

TopCcmtsCmAutoUpgradeCfgEntry ::=SEQUENCE{
	topCcmtsCmAutoUpgradeCmModelNum	OCTET STRING,
	topCcmtsCmAutoUpgradeSwVersion	OCTET STRING,
	topCcmtsCmAutoUpgradeImageFileName OCTET STRING,
	topCcmtsCmAutoUpgradeRowStatus	RowStatus
	} 
	
topCcmtsCmAutoUpgradeCmModelNum OBJECT-TYPE
	SYNTAX		OCTET STRING (SIZE (1..32))
	MAX-ACCESS	read-only
	STATUS		current
	DESCRIPTION
		"the model number of CM."
	::={ topCcmtsCmAutoUpgradeCfgEntry 1 } 
	
topCcmtsCmAutoUpgradeSwVersion OBJECT-TYPE
	SYNTAX		OCTET STRING (SIZE (1..32))
	MAX-ACCESS	read-create
	STATUS		current
	DESCRIPTION
		"the software version number of image file."
	::={ topCcmtsCmAutoUpgradeCfgEntry 2 }
	
topCcmtsCmAutoUpgradeImageFileName OBJECT-TYPE
	SYNTAX		OCTET STRING (SIZE (1..64))
	MAX-ACCESS	read-create
	STATUS		current
	DESCRIPTION
		"the name of the image file used to upgrade."
	::={ topCcmtsCmAutoUpgradeCfgEntry 3 }	

topCcmtsCmAutoUpgradeRowStatus OBJECT-TYPE
	SYNTAX		RowStatus
	MAX-ACCESS	read-create
	STATUS		current
	DESCRIPTION
		"The conceptual row status of this object."
	::={ topCcmtsCmAutoUpgradeCfgEntry 4 }
	
topCcmtsCmUpgradeStatusTable OBJECT-TYPE
    SYNTAX SEQUENCE OF TopCcmtsCmUpgradeStatusEntry
    MAX-ACCESS not-accessible
    STATUS current
    DESCRIPTION
		" "
    ::= { topCcmtsCmUpgradeObject 3 }  
    
topCcmtsCmUpgradeStatusEntry OBJECT-TYPE
    SYNTAX TopCcmtsCmUpgradeStatusEntry
    MAX-ACCESS not-accessible
    STATUS current
    DESCRIPTION
		" "
	INDEX { docsIfCmtsCmStatusIndex }
    ::= { topCcmtsCmUpgradeStatusTable 1 } 
    
TopCcmtsCmUpgradeStatusEntry     ::= SEQUENCE {
	 topCcmtsCmUpgradeStatusLastSwVers OCTET STRING,
	 topCcmtsCmUpgradeStatusCurrSwVers OCTET STRING,
	 topCcmtsCmUpgradeStatusImageFileName OCTET STRING,	
     topCcmtsCmUpgradeStatusUpgradeResult INTEGER,
     topCcmtsCmUpgradeStatusUpgradeBeginTime OCTET STRING,
     topCcmtsCmUpgradeStatusUpgradeEndTime OCTET STRING		
	}
	 
topCcmtsCmUpgradeStatusLastSwVers OBJECT-TYPE
 	SYNTAX		OCTET STRING (SIZE (0..32))
 	MAX-ACCESS	read-only
	STATUS		current
    DESCRIPTION
		"the last software version of the CM." 
	::={ topCcmtsCmUpgradeStatusEntry 1 }

topCcmtsCmUpgradeStatusCurrSwVers OBJECT-TYPE
 	SYNTAX		OCTET STRING (SIZE (0..32))
 	MAX-ACCESS	read-only
	STATUS		current
    DESCRIPTION
		"the current software version of the CM." 
	::={ topCcmtsCmUpgradeStatusEntry 2 }	

topCcmtsCmUpgradeStatusImageFileName OBJECT-TYPE
	SYNTAX		OCTET STRING (SIZE (0..64))
	MAX-ACCESS	read-only
	STATUS		current
	DESCRIPTION
		"the name of the used image file"
	::={ topCcmtsCmUpgradeStatusEntry 3 }  	
	
topCcmtsCmUpgradeStatusUpgradeResult OBJECT-TYPE
    SYNTAX          INTEGER  { 
			succeed(1),
			failed(2),
			upgrading(3),
			other(4),
			timeout(5)
			}
    MAX-ACCESS      read-only
    STATUS          current
    DESCRIPTION
        "The result of upgrade cm operation." 
    ::= { topCcmtsCmUpgradeStatusEntry 4 } 
    
topCcmtsCmUpgradeStatusUpgradeBeginTime OBJECT-TYPE
	SYNTAX          OCTET STRING (SIZE (0..32))
    MAX-ACCESS      read-only
    STATUS          current
    DESCRIPTION
        "The begin time of upgrade cm operation." 
    ::= { topCcmtsCmUpgradeStatusEntry 5 }  
    
topCcmtsCmUpgradeStatusUpgradeEndTime OBJECT-TYPE
	SYNTAX          OCTET STRING (SIZE (0..32))
    MAX-ACCESS      read-only
    STATUS          current
    DESCRIPTION
        "The end time of upgrade cm operation." 
    ::= { topCcmtsCmUpgradeStatusEntry 6 } 
    
----------------------------------------------     
--topCcmtsCmSwVersionObject
--added by lihuanyong at oct.6 2016
----------------------------------------------
topCcmtsCmSwVersionObject OBJECT IDENTIFIER ::={ topCcmtsMibObject 29 }
 
topCcmtsCmSwVersionTable OBJECT-TYPE
	SYNTAX		SEQUENCE OF TopCcmtsCmSwVersionEntry	
	MAX-ACCESS	not-accessible
	STATUS		current
	DESCRIPTION
		"The entry of cm auto upgrade configuration."
	::={ topCcmtsCmSwVersionObject 1 } 
		
topCcmtsCmSwVersionEntry OBJECT-TYPE
	SYNTAX		TopCcmtsCmSwVersionEntry
	MAX-ACCESS	not-accessible
	STATUS		current
	DESCRIPTION
		"the row define of the table."
	INDEX { docsIfCmtsCmStatusIndex }
	::= { topCcmtsCmSwVersionTable 1 } 

TopCcmtsCmSwVersionEntry ::=SEQUENCE{
	topCcmtsCmModelNum	OCTET STRING,
	topCcmtsCmSwVersion	OCTET STRING
	} 
	
topCcmtsCmModelNum OBJECT-TYPE
	SYNTAX		OCTET STRING (SIZE (0..32))
	MAX-ACCESS	read-only
	STATUS		current
	DESCRIPTION
		"the model number of CM."
	::={ topCcmtsCmSwVersionEntry 1 } 
	
topCcmtsCmSwVersion OBJECT-TYPE
	SYNTAX		OCTET STRING (SIZE (0..32))
	MAX-ACCESS	read-only
	STATUS		current
	DESCRIPTION
		"the software version number of CM"
	::={ topCcmtsCmSwVersionEntry 2 }              
END
