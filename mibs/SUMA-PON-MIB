--
-- SUMA-PON-MIB.my
-- MIB generated by MG-SOFT Visual MIB Builder Version 4.0 Build 349
-- Wednesday, June 14, 2017 at 16:53:48
--

--  SUMA-PON-MIB.mib
-- MIB generated by MG-SOFT Visual MIB Builder Version 4.0 Build 349
-- Wednesday, October 19, 2011 at 15:54:31
-- 

	SUMA-PON-MIB DEFINITIONS ::= BEGIN
 
		IMPORTS
			enterprises, TimeTicks, IpAddress, Unsigned32, Counter32, 
			Counter64, OBJECT-TYPE, OBJECT-IDENTITY			
				FROM SNMPv2-SMI			
			MacAddress, DisplayString, RowStatus, DateAndTime, TEXTUAL-CONVENTION			
				FROM SNMPv2-TC;
	
	
--
-- Textual conventions
--
		
--
-- Node definitions
--
	
--  Node definitions
-- 
-- 1.3.6.1.4.1.32285
		-- 1.3.6.1.4.1.32285
		sumaRoot OBJECT IDENTIFIER ::= { enterprises 32285 }

		
--  1.3.6.1.4.1.32285.11
		-- 1.3.6.1.4.1.32285.11
		topvisionRoot OBJECT IDENTIFIER ::= { sumaRoot 11 }

		-- 1.3.6.1.4.1.32285.11.8
		topvisionPonTree OBJECT IDENTIFIER ::= { topvisionRoot 8 }

		
		-- 1.3.6.1.4.1.32285.11.8.1
		topPonOnuObjects OBJECT IDENTIFIER ::= { topvisionPonTree 1 }

		
		-- 1.3.6.1.4.1.32285.11.8.1.1
		topOnuEventLogTable OBJECT-TYPE
			SYNTAX SEQUENCE OF TopOnuEventLogEntry
			MAX-ACCESS not-accessible
			STATUS current
			DESCRIPTION
				"Description."
			::= { topPonOnuObjects 1 }

		
		-- 1.3.6.1.4.1.32285.11.8.1.1.1
		topOnuEventLogEntry OBJECT-TYPE
			SYNTAX TopOnuEventLogEntry
			MAX-ACCESS not-accessible
			STATUS current
			DESCRIPTION
				"Description."
			INDEX { topOnuEventLogCardIndex, topOnuEventLogPonIndex, topOnuEventLogOnuIndex }
			::= { topOnuEventLogTable 1 }

		
		TopOnuEventLogEntry ::=
			SEQUENCE { 
				topOnuEventLogCardIndex
					INTEGER,
				topOnuEventLogPonIndex
					INTEGER,
				topOnuEventLogOnuIndex
					INTEGER,
				topOnuEventLogList
					OCTET STRING
			 }

		-- 1.3.6.1.4.1.32285.11.8.1.1.1.1
		topOnuEventLogCardIndex OBJECT-TYPE
			SYNTAX INTEGER
			MAX-ACCESS not-accessible
			STATUS current
			DESCRIPTION
				"Description."
			::= { topOnuEventLogEntry 1 }

		
		-- 1.3.6.1.4.1.32285.11.8.1.1.1.2
		topOnuEventLogPonIndex OBJECT-TYPE
			SYNTAX INTEGER
			MAX-ACCESS not-accessible
			STATUS current
			DESCRIPTION
				"Description."
			::= { topOnuEventLogEntry 2 }

		
		-- 1.3.6.1.4.1.32285.11.8.1.1.1.3
		topOnuEventLogOnuIndex OBJECT-TYPE
			SYNTAX INTEGER
			MAX-ACCESS not-accessible
			STATUS current
			DESCRIPTION
				"Description."
			::= { topOnuEventLogEntry 3 }

		
		-- 1.3.6.1.4.1.32285.11.8.1.1.1.4
		topOnuEventLogList OBJECT-TYPE
			SYNTAX OCTET STRING (SIZE (0..96))
			MAX-ACCESS read-only
			STATUS current
			DESCRIPTION
				"Description."
			::= { topOnuEventLogEntry 4 }

		
		-- 1.3.6.1.4.1.32285.11.8.1.2
		topOnuLaserTable OBJECT-TYPE
			SYNTAX SEQUENCE OF TopOnuLaserEntry
			MAX-ACCESS not-accessible
			STATUS current
			DESCRIPTION
				"Description."
			::= { topPonOnuObjects 2 }

		
		-- 1.3.6.1.4.1.32285.11.8.1.2.1
		topOnuLaserEntry OBJECT-TYPE
			SYNTAX TopOnuLaserEntry
			MAX-ACCESS not-accessible
			STATUS current
			DESCRIPTION
				"Description."
			INDEX { topOnuLaserCardIndex, topOnuLaserPortIndex, topOnuLaserOnuIndex }
			::= { topOnuLaserTable 1 }

		
		TopOnuLaserEntry ::=
			SEQUENCE { 
				topOnuLaserCardIndex
					Integer32,
				topOnuLaserPortIndex
					Integer32,
				topOnuLaserOnuIndex
					Integer32,
				topOnuLaserSwitch
					INTEGER
			 }

		-- 1.3.6.1.4.1.32285.11.8.1.2.1.1
		topOnuLaserCardIndex OBJECT-TYPE
			SYNTAX Integer32
			MAX-ACCESS not-accessible
			STATUS current
			DESCRIPTION
				"Description."
			::= { topOnuLaserEntry 1 }

		
		-- 1.3.6.1.4.1.32285.11.8.1.2.1.2
		topOnuLaserPortIndex OBJECT-TYPE
			SYNTAX Integer32
			MAX-ACCESS not-accessible
			STATUS current
			DESCRIPTION
				"Description."
			::= { topOnuLaserEntry 2 }

		
		-- 1.3.6.1.4.1.32285.11.8.1.2.1.3
		topOnuLaserOnuIndex OBJECT-TYPE
			SYNTAX Integer32
			MAX-ACCESS not-accessible
			STATUS current
			DESCRIPTION
				"Description."
			::= { topOnuLaserEntry 3 }

		
		-- 1.3.6.1.4.1.32285.11.8.1.2.1.4
		topOnuLaserSwitch OBJECT-TYPE
			SYNTAX INTEGER
				{
				on(1),
				off(2)
				}
			MAX-ACCESS read-write
			STATUS current
			DESCRIPTION
				"Description."
			::= { topOnuLaserEntry 4 }

		
		-- 1.3.6.1.4.1.32285.11.8.2
		topPonPortObjects OBJECT IDENTIFIER ::= { topvisionPonTree 2 }

		
		-- 1.3.6.1.4.1.32285.11.8.2.1
		topPonPortRogueTable OBJECT-TYPE
			SYNTAX SEQUENCE OF TopPonPortRogueEntry
			MAX-ACCESS not-accessible
			STATUS current
			DESCRIPTION
				"Description."
			::= { topPonPortObjects 1 }

		
		-- 1.3.6.1.4.1.32285.11.8.2.1.1
		topPonPortRogueEntry OBJECT-TYPE
			SYNTAX TopPonPortRogueEntry
			MAX-ACCESS not-accessible
			STATUS current
			DESCRIPTION
				"Description."
			INDEX { topPonPortRogueCardIndex, topPonPortRoguePortIndex }
			::= { topPonPortRogueTable 1 }

		
		TopPonPortRogueEntry ::=
			SEQUENCE { 
				topPonPortRogueCardIndex
					Integer32,
				topPonPortRoguePortIndex
					Integer32,
				topPonPortRogueSwitch
					INTEGER,
				topPonPortRogueOnuList
					OCTET STRING,
				topPonPortRogueOnuCheck
					OCTET STRING
			 }

		-- 1.3.6.1.4.1.32285.11.8.2.1.1.1
		topPonPortRogueCardIndex OBJECT-TYPE
			SYNTAX Integer32
			MAX-ACCESS not-accessible
			STATUS current
			DESCRIPTION
				"Description."
			::= { topPonPortRogueEntry 1 }

		
		-- 1.3.6.1.4.1.32285.11.8.2.1.1.2
		topPonPortRoguePortIndex OBJECT-TYPE
			SYNTAX Integer32
			MAX-ACCESS not-accessible
			STATUS current
			DESCRIPTION
				"Description."
			::= { topPonPortRogueEntry 2 }

		
		-- 1.3.6.1.4.1.32285.11.8.2.1.1.3
		topPonPortRogueSwitch OBJECT-TYPE
			SYNTAX INTEGER
				{
				enable(1),
				disable(2)
				}
			MAX-ACCESS read-write
			STATUS current
			DESCRIPTION
				"Description."
			::= { topPonPortRogueEntry 3 }

		
		-- 1.3.6.1.4.1.32285.11.8.2.1.1.4
		topPonPortRogueOnuList OBJECT-TYPE
			SYNTAX OCTET STRING (SIZE (32))
			MAX-ACCESS read-write
			STATUS current
			DESCRIPTION
				"Description."
			::= { topPonPortRogueEntry 4 }

		
		-- 1.3.6.1.4.1.32285.11.8.2.1.1.5
		topPonPortRogueOnuCheck OBJECT-TYPE
			SYNTAX OCTET STRING (SIZE (32))
			MAX-ACCESS read-write
			STATUS current
			DESCRIPTION
				"Description."
			::= { topPonPortRogueEntry 5 }

		
	
	END

--
-- SUMA-PON-MIB.my
--
