--
-- NSCRTV-EPONEOC-GPON-ONU-MIB.mib
-- MIB generated by MG-SOFT Visual MIB Builder Version 4.0 Build 349
-- Friday, September 30, 2016 at 09:45:40
--

	NSCRTV-EPONEOC-GPON-ONU-MIB DEFINITIONS ::= BEGIN
 
		IMPORTS
			BridgeId, Timeout			
				FROM BRIDGE-MIB			
			enterprises, TimeTicks, IpAddress, Unsigned32, Gauge32, 
			Counter32, Counter64, OBJECT-TYPE, OBJECT-IDENTITY, 
			NOTIFICATION-TYPE			
				FROM SNMPv2-SMI			
			DateAndTime, TruthValue, RowStatus, MacAddress, DisplayString, 
			TimeStamp, TEXTUAL-CONVENTION			
				FROM SNMPv2-TC;

--
-- Textual conventions
--
		GponCardIndex ::= TEXTUAL-CONVENTION
			STATUS current
			DESCRIPTION 
				"     
				For easy presenting the chassis view by NMS, bCardIndex shall be formatted
				in a following manner:                        
				    Four bytes of INTEGER, from the most significant byte to the least significant
				    bytes
				        -----------------------------------------------------------------------------
				Reserved byte Reserved byte   Reserved byte Sub-slot 2-bit Main-slot 6-bit        
				Notes:
				-----         
				1. Reserved bytes shall be set to 0.        
				2. The main-slot shall be started from 1, and shall be in a consecutive manner,
				   for all slots, including service slots, control slots, switch slots, power
				slots,FAN slots, etc.For example, 1, 2, 3          
				3. The sub-slot shall be started from 1, and shall be in a consecutive manner.
				   For example, 1, 2. If no sub-slot concept of a main-slot, set to 0.        
				4. For fixed device, if no slot concept, NE shall set both main-slot and sub-slot
				to 0, to indicate this is meaningless. For modulized device, they MUST not be
				set to 0.This definition shall applied to both OLT and ONU.        
				5. For trunk, since there is no slot concept, set main-slot to all-1 and sub-slot
				to 0. This definition shall applied to both OLT and ONU.
				
				For example, 
				0x00 00 00 0A, represents main-slot 10, no sub-slot
				0x00 00 00 42, represents main-slot 2, sub-slot 1
				0x00 00 00 3F, represents a trunk
				"
			SYNTAX Unsigned32

		GponPortIndex ::= TEXTUAL-CONVENTION
			STATUS current
			DESCRIPTION 
				"       
				The device port number shall start from 1. Nunber 0 had specific meaning, stands
				for portIndex is meaningless, for the situation defined.
				"
			SYNTAX INTEGER (0..255)

		GponDeviceIndex ::= TEXTUAL-CONVENTION
			STATUS current
			DESCRIPTION 
				"
				Gpon olt/onu
				ONU ID       
				Olt device-8bit OLT Card-8bit Pon port-8bit OnuNUM-8bit        
				Note: 
				----        
				1. OLT device must not be 0.        
				2. Card here shall confirm the last byte definition of GponCardIndex
				   to indicate the main-slot and sub-slot index.         
				3. Pon port must not be 0.
				4. The useful ONU logical ID MUST never be set to 0, where NUM of 0 has
				   another meaning, to indicate that the ONU logical ID is meaningless,
				   or said to not applied.
				        
				Usage guide:
				-----------        
				This TC could be used for OLT SNI, OLT PON port, OLT ONU ID
				ONU UNI, OLT device, trunk.         
				If the refered MIB object does not have clear definition,
				refer to the following:
				Applied Obj  - Descriptions of Index
				------------------------------------------------------------------
				OLT Pon Port - OnuNum shall be set to 0,
				OLT SNI    - Same as OLT Pon Port         
				OLT onu ID   - Set OnuNUM to corresponding ONU logical ID         
				ONU UNI    - Same as OLT ONU ID
				OLT device   - Set card, pon port and OnuNUM to 0
				Trunk    - Card to 0x3F, pon port to trunk ID, OnuNUM to 0
				         Olt device to corresponding ONU device       
				"
			SYNTAX Unsigned32

--
-- Node definitions
--
	
		-- 1.3.6.1.4.1.17409
		nscrtvRoot OBJECT IDENTIFIER ::= { enterprises 17409 }

		
		-- 1.3.6.1.4.1.17409.2
		nscrtvFTTxTree OBJECT IDENTIFIER ::= { nscrtvRoot 2 }

		
--      DESCRIPTION
		-- 1.3.6.1.4.1.17409.2.8
		gponTree OBJECT IDENTIFIER ::= { nscrtvFTTxTree 8 }
		

		
-- ------------------------------------------------------------------------------
-- onuObjects(1.3.6.1.4.1.17409.2.8.4)
-- ------------------------------------------------------------------------------  
        -- 1.3.6.1.4.1.17409.2.8.4
		onuObjects OBJECT IDENTIFIER ::= { gponTree 4 }
		
		
		-- 1.3.6.1.4.1.17409.2.8.4.1
		onuInfoTable OBJECT-TYPE
			SYNTAX SEQUENCE OF OnuInfoEntry
			MAX-ACCESS not-accessible
			STATUS current
			DESCRIPTION
				"A list of onuInfoTable entries. "
			::= { onuObjects 1 }

		
		-- 1.3.6.1.4.1.17409.2.8.4.1.1
		onuInfoEntry OBJECT-TYPE
			SYNTAX OnuInfoEntry
			MAX-ACCESS not-accessible
			STATUS current
			DESCRIPTION
				"The onuInfoEntry Information"
			INDEX { onuDeviceIndex }
			::= { onuInfoTable 1 }

		
		OnuInfoEntry ::=
			SEQUENCE { 
				onuDeviceIndex
					GponDeviceIndex,
				onuName
					DisplayString,
				onuSerialNum
					OCTET STRING,
				onuType
					INTEGER,
				onuVendorID
					OCTET STRING,
				onuEquipmentID
					OCTET STRING,
				onuOperationStatus
					INTEGER,
				onuAdminStatus
					INTEGER,
				onuTestDistance
					INTEGER,
				resetONU
					INTEGER,
				onuDeactive
					INTEGER,
				onuTimeSinceLastRegister
					Counter32,
				onuSysUpTime
					Counter32,
				onuHardwareVersion
					DisplayString,
				onuPerfStats15minuteEnable
					TruthValue,
				onuPerfStats24hourEnable
					TruthValue
			 }

		-- 1.3.6.1.4.1.17409.2.8.4.1.1.1
		onuDeviceIndex OBJECT-TYPE
			SYNTAX GponDeviceIndex
			MAX-ACCESS not-accessible
			STATUS current
			DESCRIPTION
				"onuDevice Index"
			::= { onuInfoEntry 1 }

		
		-- 1.3.6.1.4.1.17409.2.8.4.1.1.2
		onuName OBJECT-TYPE
			SYNTAX DisplayString
			MAX-ACCESS read-write
			STATUS current
			DESCRIPTION
				"onu Name"
			::= { onuInfoEntry 2 }

		
		-- 1.3.6.1.4.1.17409.2.8.4.1.1.3
		onuSerialNum OBJECT-TYPE
			SYNTAX OCTET STRING (SIZE (8))
			MAX-ACCESS read-only
			STATUS current
			DESCRIPTION
				"ONU serial number."
			::= { onuInfoEntry 3 }

		
		-- 1.3.6.1.4.1.17409.2.8.4.1.1.4
		onuType OBJECT-TYPE
			SYNTAX INTEGER
				{
				fixed(1),
				chassisBased(2)
				}
			MAX-ACCESS read-only
			STATUS current
			DESCRIPTION
				"onu Type            
				fixed(1)        - not slot concept
				chassisBased(2) - port is indexed by coupling slot ID"
			::= { onuInfoEntry 4 }

		
		-- 1.3.6.1.4.1.17409.2.8.4.1.1.5
		onuVendorID OBJECT-TYPE
			SYNTAX OCTET STRING (SIZE (4))
			MAX-ACCESS read-only
			STATUS current
			DESCRIPTION
				"ONU vendor id."
			::= { onuInfoEntry 5 }

		
		-- 1.3.6.1.4.1.17409.2.8.4.1.1.6
		onuEquipmentID OBJECT-TYPE
			SYNTAX OCTET STRING (SIZE (20))
			MAX-ACCESS read-only
			STATUS current
			DESCRIPTION
				"ONU model id."
			::= { onuInfoEntry 6 }

		
		-- 1.3.6.1.4.1.17409.2.8.4.1.1.7
		onuOperationStatus OBJECT-TYPE
			SYNTAX INTEGER
				{
				up(1),
				down(2)
				}
			MAX-ACCESS read-only
			STATUS current
			DESCRIPTION
				"onu Operation Status"
			::= { onuInfoEntry 7 }

		
		-- 1.3.6.1.4.1.17409.2.8.4.1.1.8
		onuAdminStatus OBJECT-TYPE
			SYNTAX INTEGER
				{
				up(1),
				down(2)
				}
			MAX-ACCESS read-write
			STATUS current
			DESCRIPTION
				"onu Admin Status"
			::= { onuInfoEntry 8 }

		
		-- 1.3.6.1.4.1.17409.2.8.4.1.1.9
		onuTestDistance OBJECT-TYPE
			SYNTAX INTEGER
			UNITS "Meter"
			MAX-ACCESS read-only
			STATUS current
			DESCRIPTION
				"onu Test Distance"
			::= { onuInfoEntry 9 }

		
		-- 1.3.6.1.4.1.17409.2.8.4.1.1.10
		resetONU OBJECT-TYPE
			SYNTAX INTEGER { reset(1) }
			MAX-ACCESS read-write
			STATUS current
			DESCRIPTION
				"reset ONU"
			::= { onuInfoEntry 10 }

		
		-- 1.3.6.1.4.1.17409.2.8.4.1.1.11
		onuDeactive OBJECT-TYPE
			SYNTAX INTEGER
				{
				active(1),
				deactive(2)
				}
			MAX-ACCESS read-write
			STATUS current
			DESCRIPTION
				"Description."
			::= { onuInfoEntry 11 }

		
		-- 1.3.6.1.4.1.17409.2.8.4.1.1.12
		onuTimeSinceLastRegister OBJECT-TYPE
			SYNTAX Counter32
			UNITS "second"
			MAX-ACCESS read-only
			STATUS current
			DESCRIPTION
				"Description."
			::= { onuInfoEntry 12 }
		
		
		-- 1.3.6.1.4.1.17409.2.8.4.1.1.13
		onuSysUpTime OBJECT-TYPE
			SYNTAX Counter32
			UNITS "second"
			MAX-ACCESS read-only
			STATUS current
			DESCRIPTION
				"Description."
			::= { onuInfoEntry 13 }

		
		-- 1.3.6.1.4.1.17409.2.8.4.1.1.14
		onuHardwareVersion OBJECT-TYPE
			SYNTAX DisplayString
			MAX-ACCESS read-only
			STATUS current
			DESCRIPTION
				"Description."
			::= { onuInfoEntry 14 }
		
		-- 1.3.6.1.4.1.17409.2.8.4.1.1.15
		onuPerfStats15minuteEnable OBJECT-TYPE
			SYNTAX TruthValue
			MAX-ACCESS read-write
			STATUS current
			DESCRIPTION
				"Description."
			::= { onuInfoEntry 15 }

		
		-- 1.3.6.1.4.1.17409.2.8.4.1.1.16
		onuPerfStats24hourEnable OBJECT-TYPE
			SYNTAX TruthValue
			MAX-ACCESS read-write
			STATUS current
			DESCRIPTION
				"Description."
			::= { onuInfoEntry 16 }

		
		-- 1.3.6.1.4.1.17409.2.8.4.2
		onuInfoSoftwareTable OBJECT-TYPE
			SYNTAX SEQUENCE OF OnuInfoSoftwareEntry
			MAX-ACCESS not-accessible
			STATUS current
			DESCRIPTION
				"Description."
			::= { onuObjects 2 }

		
		-- 1.3.6.1.4.1.17409.2.8.4.2.1
		onuInfoSoftwareEntry OBJECT-TYPE
			SYNTAX OnuInfoSoftwareEntry
			MAX-ACCESS not-accessible
			STATUS current
			DESCRIPTION
				"Description."
			INDEX { onuSoftwareDeviceIndex }
			::= { onuInfoSoftwareTable 1 }

		
		OnuInfoSoftwareEntry ::=
			SEQUENCE { 
				onuSoftwareDeviceIndex
					INTEGER,
				onuSoftware0Version
					DisplayString,
				onuSoftware0Valid
					INTEGER,
				onuSoftware0Active
					INTEGER,
				onuSoftware0Commited
					INTEGER,
				onuSoftware1Version
					DisplayString,
				onuSoftware1Valid
					INTEGER,
				onuSoftware1Active
					INTEGER,
				onuSoftware1Commited
					INTEGER
			 }

		-- 1.3.6.1.4.1.17409.2.8.4.2.1.1
		onuSoftwareDeviceIndex OBJECT-TYPE
			SYNTAX INTEGER
			MAX-ACCESS not-accessible
			STATUS current
			DESCRIPTION
				"Description."
			::= { onuInfoSoftwareEntry 1 }

		
		-- 1.3.6.1.4.1.17409.2.8.4.2.1.2
		onuSoftware0Version OBJECT-TYPE
			SYNTAX DisplayString
			MAX-ACCESS read-only
			STATUS current
			DESCRIPTION
				"Description."
			::= { onuInfoSoftwareEntry 2 }

		
		-- 1.3.6.1.4.1.17409.2.8.4.2.1.3
		onuSoftware0Valid OBJECT-TYPE
			SYNTAX INTEGER
				{
				invalid(0),
				valid(1)
				}
			MAX-ACCESS read-only
			STATUS current
			DESCRIPTION
				"Description."
			::= { onuInfoSoftwareEntry 3 }

		
		-- 1.3.6.1.4.1.17409.2.8.4.2.1.4
		onuSoftware0Active OBJECT-TYPE
			SYNTAX INTEGER
				{
				inactive(0),
				active(1)
				}
			MAX-ACCESS read-write
			STATUS current
			DESCRIPTION
				"Description."
			::= { onuInfoSoftwareEntry 4 }

		
		-- 1.3.6.1.4.1.17409.2.8.4.2.1.5
		onuSoftware0Commited OBJECT-TYPE
			SYNTAX INTEGER
				{
				uncommitted(0),
				committed(1)
				}
			MAX-ACCESS read-write
			STATUS current
			DESCRIPTION
				"Description."
			::= { onuInfoSoftwareEntry 5 }

		
		-- 1.3.6.1.4.1.17409.2.8.4.2.1.6
		onuSoftware1Version OBJECT-TYPE
			SYNTAX DisplayString
			MAX-ACCESS read-only
			STATUS current
			DESCRIPTION
				"Description."
			::= { onuInfoSoftwareEntry 6 }

		
		-- 1.3.6.1.4.1.17409.2.8.4.2.1.7
		onuSoftware1Valid OBJECT-TYPE
			SYNTAX INTEGER
				{
				invalid(0),
				valid(1)
				}
			MAX-ACCESS read-only
			STATUS current
			DESCRIPTION
				"Description."
			::= { onuInfoSoftwareEntry 7 }

		
		-- 1.3.6.1.4.1.17409.2.8.4.2.1.8
		onuSoftware1Active OBJECT-TYPE
			SYNTAX INTEGER
				{
				inactive(0),
				active(1)
				}
			MAX-ACCESS read-write
			STATUS current
			DESCRIPTION
				"Description."
			::= { onuInfoSoftwareEntry 8 }

		
		-- 1.3.6.1.4.1.17409.2.8.4.2.1.9
		onuSoftware1Commited OBJECT-TYPE
			SYNTAX INTEGER
				{
				uncommitted(0),
				committed(1)
				}
			MAX-ACCESS read-write
			STATUS current
			DESCRIPTION
				"Description."
			::= { onuInfoSoftwareEntry 9 }

		
		-- 1.3.6.1.4.1.17409.2.8.4.3
		onuIpHostTable OBJECT-TYPE
			SYNTAX SEQUENCE OF OnuIpHostEntry
			MAX-ACCESS not-accessible
			STATUS current
			DESCRIPTION
				"Description."
			::= { onuObjects 3 }

		
		-- 1.3.6.1.4.1.17409.2.8.4.3.1
		onuIpHostEntry OBJECT-TYPE
			SYNTAX OnuIpHostEntry
			MAX-ACCESS not-accessible
			STATUS current
			DESCRIPTION
				"Description."
			INDEX { onuIpHostDeviceIndex, onuIpHostIndex }
			::= { onuIpHostTable 1 }

		
		OnuIpHostEntry ::=
			SEQUENCE { 
				onuIpHostDeviceIndex
					INTEGER,
				onuIpHostIndex
					INTEGER,
				onuIpHostAddressConfigMode
					INTEGER,
				onuIpHostAddress
					IpAddress,
				onuIpHostSubnetMask
					IpAddress,
				onuIpHostGateway
					IpAddress,
				onuIpHostPrimaryDNS
					IpAddress,
				onuIpHostSecondaryDNS
					IpAddress,
				onuIpHostVlanTagPriority
					INTEGER,
				onuIpHostVlanPvid
					INTEGER,
				onuIpHostMacAddress
					MacAddress,
				onuIpHostRowStatus
					RowStatus
			 }

		-- 1.3.6.1.4.1.17409.2.8.4.3.1.1
		onuIpHostDeviceIndex OBJECT-TYPE
			SYNTAX INTEGER
			MAX-ACCESS not-accessible
			STATUS current
			DESCRIPTION
				"Description."
			::= { onuIpHostEntry 1 }

		
		-- 1.3.6.1.4.1.17409.2.8.4.3.1.2
		onuIpHostIndex OBJECT-TYPE
			SYNTAX INTEGER (1..64)
			MAX-ACCESS not-accessible
			STATUS current
			DESCRIPTION
				"Description."
			::= { onuIpHostEntry 2 }

		
		-- 1.3.6.1.4.1.17409.2.8.4.3.1.3
		onuIpHostAddressConfigMode OBJECT-TYPE
			SYNTAX INTEGER
				{
				dhcp(1),
				static(2)
				}
			MAX-ACCESS read-write
			STATUS current
			DESCRIPTION
				"Description."
			::= { onuIpHostEntry 3 }

		
		-- 1.3.6.1.4.1.17409.2.8.4.3.1.4
		onuIpHostAddress OBJECT-TYPE
			SYNTAX IpAddress
			MAX-ACCESS read-write
			STATUS current
			DESCRIPTION
				"Description."
			::= { onuIpHostEntry 4 }

		
		-- 1.3.6.1.4.1.17409.2.8.4.3.1.5
		onuIpHostSubnetMask OBJECT-TYPE
			SYNTAX IpAddress
			MAX-ACCESS read-write
			STATUS current
			DESCRIPTION
				"Description."
			::= { onuIpHostEntry 5 }

		
		-- 1.3.6.1.4.1.17409.2.8.4.3.1.6
		onuIpHostGateway OBJECT-TYPE
			SYNTAX IpAddress
			MAX-ACCESS read-write
			STATUS current
			DESCRIPTION
				"Description."
			::= { onuIpHostEntry 6 }

		
		-- 1.3.6.1.4.1.17409.2.8.4.3.1.7
		onuIpHostPrimaryDNS OBJECT-TYPE
			SYNTAX IpAddress
			MAX-ACCESS read-write
			STATUS current
			DESCRIPTION
				"Description."
			::= { onuIpHostEntry 7 }

		
		-- 1.3.6.1.4.1.17409.2.8.4.3.1.8
		onuIpHostSecondaryDNS OBJECT-TYPE
			SYNTAX IpAddress
			MAX-ACCESS read-write
			STATUS current
			DESCRIPTION
				"Description."
			::= { onuIpHostEntry 8 }

		
		-- 1.3.6.1.4.1.17409.2.8.4.3.1.9
		onuIpHostVlanTagPriority OBJECT-TYPE
			SYNTAX INTEGER (0..7)
			MAX-ACCESS read-write
			STATUS current
			DESCRIPTION
				"Description."
			DEFVAL { 1 }
			::= { onuIpHostEntry 9 }

		
		-- 1.3.6.1.4.1.17409.2.8.4.3.1.10
		onuIpHostVlanPvid OBJECT-TYPE
			SYNTAX INTEGER (1..4094)
			MAX-ACCESS read-write
			STATUS current
			DESCRIPTION
				"Description."
			DEFVAL { 1 }
			::= { onuIpHostEntry 10 }

		
		-- 1.3.6.1.4.1.17409.2.8.4.3.1.11
		onuIpHostMacAddress OBJECT-TYPE
			SYNTAX MacAddress
			MAX-ACCESS read-only
			STATUS current
			DESCRIPTION
				"Description."
			::= { onuIpHostEntry 11 }

		
		-- 1.3.6.1.4.1.17409.2.8.4.3.1.12
		onuIpHostRowStatus OBJECT-TYPE
			SYNTAX RowStatus
			MAX-ACCESS read-create
			STATUS current
			DESCRIPTION
				"Description."
			::= { onuIpHostEntry 12 }


		-- 1.3.6.1.4.1.17409.2.8.4.5
		onuCapabilityTable OBJECT-TYPE
			SYNTAX SEQUENCE OF OnuCapabilityEntry
			MAX-ACCESS not-accessible
			STATUS current
			DESCRIPTION
				"A list of onuInfoTable entries. "
			::= { onuObjects 5 }

		
		-- 1.3.6.1.4.1.17409.2.8.4.5.1
		onuCapabilityEntry OBJECT-TYPE
			SYNTAX OnuCapabilityEntry
			MAX-ACCESS not-accessible
			STATUS current
			DESCRIPTION
				"The onuCapabilityEntry Information"
			INDEX { onuCapabilityDeviceIndex }
			::= { onuCapabilityTable 1 }

		
		OnuCapabilityEntry ::=
			SEQUENCE { 
				onuCapabilityDeviceIndex
					GponDeviceIndex,
				onuOMCCVersion
					INTEGER,
				onuTotalEthNum
					INTEGER,
				onuTotalWlanNum
					INTEGER,
				onuTotalCatvNum
					INTEGER,
				onuTotalVeipNum
					INTEGER,
				onuIpHostNum
					INTEGER,
				onuTrafficMgmtOption
					INTEGER,
				onuTotalGEMPortNum
					INTEGER,
				onuTotalTContNum
					INTEGER,
				onuConnectCapbility
					BITS,
				onuQosFlexibility
					BITS
			 }

		-- 1.3.6.1.4.1.17409.2.8.4.5.1.1
		onuCapabilityDeviceIndex OBJECT-TYPE
			SYNTAX GponDeviceIndex
			MAX-ACCESS not-accessible
			STATUS current
			DESCRIPTION
				"onu Device Index"
			::= { onuCapabilityEntry 1 }

		
		-- 1.3.6.1.4.1.17409.2.8.4.5.1.2
		onuOMCCVersion OBJECT-TYPE
			SYNTAX INTEGER
			MAX-ACCESS read-only
			STATUS current
			DESCRIPTION
				"0x80 	ITU-T G.984.4 (06/04)
						NOTE – For historical reasons, this code point may also appear in
						ONUs that support later versions of [ITU-T G.984.4].				
				0x81 	ITU-T G.984.4 2004 Amd.1 (06/05)
				0x82 	ITU-T G.984.4 2004 Amd.2 (03/06)
				0x83 	ITU-T G.984.4 2004 Amd.3 (12/06)				
				0x84 	ITU-T G.984.4 2008 (02/08)				
				0x85 	ITU-T G.984.4 2008 Amd.1 (06/09)				
				0x86 	ITU-T G.984.4 2008 Amd.2 (2009). 
						Baseline message set only, without the extended message set option
				0x96 	ITU-T G.984.4 2008 Amd.2 (2009). Extended message set option, in addition to the baseline message set.54 Rec. ITU-T G.988 (10/2012)
				0xA0 	ITU-T G.988 (2010). Baseline message set only, without the extended message set option
				0xA1    ITU-T G.988 Amd.1 (2011). Baseline message set only
				0xA2    ITU-T G.988 Amd.2 (2012). Baseline message set only
				0xA3 	ITU-T G.988 (2012). Baseline message set only				
				0xB0 	ITU-T G.988 (2010). Baseline and extended message set				
				0xB1 	ITU-T G.988 Amd.1 (2011). Baseline and extended message set				
				0xB2 	ITU-T G.988 Amd.2 (2012). Baseline and extended message	set				
				0xB3 	ITU-T G.988 (2012). Baseline and extended message set"
			::= { onuCapabilityEntry 2 }

		
		-- 1.3.6.1.4.1.17409.2.8.4.5.1.3
		onuTotalEthNum OBJECT-TYPE
			SYNTAX INTEGER
			MAX-ACCESS read-only
			STATUS current
			DESCRIPTION
				"gePort Bitmap				
				In slot+port pair list manner. Suppose each slot support up to 64 ports.
				One octet to indentify slot and 8 octets to identify portbitmap for
				the slot. The bitmap definition is internet sequence. The most left bit 
				is for port 1 of the slot, the most right bit is for port 64 of the slot.            
				If the slot cannot support 64 ports, set the bits of not supported ports
				to 0.            
				If the port is GE port, set the corresponding bit to 1.                 
				Since the slot num depends on each individual device, the object is variable
				length. If the device is fixed box (not modulized), set the slot number to 
				255. Then the network management system could ignore the slot info.            
				It is not necessary to list the slot doesn't support GE port.                        
				For example, if have 4 GE ports, of: 1/4, 1/6, 2/3, 4/17,
				the object will be presented in:
				01 14 00 00 00 00 00 00 00
				02 20 00 00 00 00 00 00 00
				04 00 00 80 00 00 00 00 00            
				Another example, for fixed box, if have 4 ge ports of 4,6,10,17, the object
				will be presented as:
				FF 14 40 10 00 00 00 00	"
			::= { onuCapabilityEntry 3 }

		
		-- 1.3.6.1.4.1.17409.2.8.4.5.1.4
		onuTotalWlanNum OBJECT-TYPE
			SYNTAX INTEGER
			MAX-ACCESS read-only
			STATUS current
			DESCRIPTION
				"fePort Num"
			::= { onuCapabilityEntry 4 }

		
		-- 1.3.6.1.4.1.17409.2.8.4.5.1.5
		onuTotalCatvNum OBJECT-TYPE
			SYNTAX INTEGER
			MAX-ACCESS read-only
			STATUS current
			DESCRIPTION			" "
			::= { onuCapabilityEntry 5 }

		
		-- 1.3.6.1.4.1.17409.2.8.4.5.1.6
		onuTotalVeipNum OBJECT-TYPE
			SYNTAX INTEGER
			MAX-ACCESS read-only
			STATUS current
			DESCRIPTION			" "
			::= { onuCapabilityEntry 6 }

		
		-- 1.3.6.1.4.1.17409.2.8.4.5.1.7
		onuIpHostNum OBJECT-TYPE
			SYNTAX INTEGER
			MAX-ACCESS read-only
			STATUS current
			DESCRIPTION			" "
			::= { onuCapabilityEntry 7 }

		
		-- 1.3.6.1.4.1.17409.2.8.4.5.1.8
		onuTrafficMgmtOption OBJECT-TYPE
			SYNTAX INTEGER
			MAX-ACCESS read-only
			STATUS current
			DESCRIPTION
				"0:	Priority controlled and flexibly scheduled upstream traffic. 
				
				 1: Rate controlled upstream traffic. 
				 
                 2: Priority and rate controlled. "
			::= { onuCapabilityEntry 8 }

		
		-- 1.3.6.1.4.1.17409.2.8.4.5.1.9
		onuTotalGEMPortNum OBJECT-TYPE
			SYNTAX INTEGER
			MAX-ACCESS read-only
			STATUS current
			DESCRIPTION			" "
			::= { onuCapabilityEntry 9 }

		
		-- 1.3.6.1.4.1.17409.2.8.4.5.1.10
		onuTotalTContNum OBJECT-TYPE
			SYNTAX INTEGER
			MAX-ACCESS read-only
			STATUS current
			DESCRIPTION			" "
			::= { onuCapabilityEntry 10 }

		
		-- 1.3.6.1.4.1.17409.2.8.4.5.1.11
		onuConnectCapbility OBJECT-TYPE
			SYNTAX BITS
				{
				nto1(0),
				ntom(3),
				ntop(5),
				ntomp(6)
				}
			MAX-ACCESS read-only
			STATUS current
			DESCRIPTION
				"1 	(LSB) N:1 bridging, Figure 8.2.2-3
				
				 2  1:M mapping, Figure 8.2.2-4
				 
				 3	1:P filtering, Figure 8.2.2-5
				 
				 4  N:M bridge-mapping, Figure 8.2.2-6
				 
				 5  1:MP map-filtering, Figure 8.2.2-7
				 
				 6  N:P bridge-filtering, Figure 8.2.2-8
				 
				 7	N:MP bridge-map-filtering, Figure 8.2.2-9
				 
				 8-16 Reserved"
			::= { onuCapabilityEntry 11 }

		
		-- 1.3.6.1.4.1.17409.2.8.4.5.1.12
		onuQosFlexibility OBJECT-TYPE
			SYNTAX BITS { priorityQueueME(1) }
			MAX-ACCESS read-only
			STATUS current
			DESCRIPTION
				"1	(LSB) Priority queue ME: Port field of related port attribute is read-write and
					can point to any T-CONT or UNI port in the same slot
					
				 2	Priority queue ME: The traffic scheduler pointer is permitted to refer to
					any other traffic scheduler in the same slot

				 3	Traffic scheduler ME: T-CONT pointer is read-write
				
				 4	Traffic scheduler ME: Policy attribute is read-write
								
				 5	T-CONT ME: Policy attribute is read-write
								
				 6	Priority queue ME: Priority field of related port attribute is read-write
								
				 7..16 Reserved"
			::= { onuCapabilityEntry 12 }


		-- 1.3.6.1.4.1.17409.2.8.4.6
		onuAuthenticationManagement OBJECT-IDENTITY
			STATUS current
			DESCRIPTION 
				" "
			::= { onuObjects 6 }

		
		-- 1.3.6.1.4.1.17409.2.8.4.6.1
		onuAuthenticationConfigTable OBJECT-TYPE
			SYNTAX SEQUENCE OF OnuAuthenticationConfigEntry
			MAX-ACCESS not-accessible
			STATUS current
			DESCRIPTION
				"A list of onuAuthenticationPreConfigTable entries. "
			::= { onuAuthenticationManagement 1 }

		
		-- 1.3.6.1.4.1.17409.2.8.4.6.1.1
		onuAuthenticationConfigEntry OBJECT-TYPE
			SYNTAX OnuAuthenticationConfigEntry
			MAX-ACCESS not-accessible
			STATUS current
			DESCRIPTION
				"The onuAuthenticationPreConfigEntry Information"
			INDEX { onuAuthenOnuId }
			::= { onuAuthenticationConfigTable 1 }

		
		OnuAuthenticationConfigEntry ::=
			SEQUENCE { 
				onuAuthenOnuId
					INTEGER,
				onuAuthenSN
					OCTET STRING,
				onuAuthenPassword
					DisplayString,
				onuAuthenLoid
					DisplayString,
				onuAuthenLoidPassword
					DisplayString,
				onuAuthenLineProfileId
					INTEGER,
				onuAuthenSrvProfileId
					INTEGER,
				onuAuthenRowStatus
					RowStatus
			 }

		-- 1.3.6.1.4.1.17409.2.8.4.6.1.1.1
		onuAuthenOnuId OBJECT-TYPE
			SYNTAX INTEGER
			MAX-ACCESS not-accessible
			STATUS current
			DESCRIPTION
				"onu logical ID"
			::= { onuAuthenticationConfigEntry 1 }

		
		-- 1.3.6.1.4.1.17409.2.8.4.6.1.1.2
		onuAuthenSN OBJECT-TYPE
			SYNTAX OCTET STRING (SIZE (8))
			MAX-ACCESS read-create
			STATUS current
			DESCRIPTION
				"onu Mac Address"
			::= { onuAuthenticationConfigEntry 2 }

		
		-- 1.3.6.1.4.1.17409.2.8.4.6.1.1.3
		onuAuthenPassword OBJECT-TYPE
			SYNTAX DisplayString
			MAX-ACCESS read-create
			STATUS current
			DESCRIPTION
				"Authen Action
				
				This is optional in function"
			::= { onuAuthenticationConfigEntry 3 }

		
		-- 1.3.6.1.4.1.17409.2.8.4.6.1.1.4
		onuAuthenLoid OBJECT-TYPE
			SYNTAX DisplayString
			MAX-ACCESS read-create
			STATUS current
			DESCRIPTION
				"Description."
			::= { onuAuthenticationConfigEntry 4 }

		
		-- 1.3.6.1.4.1.17409.2.8.4.6.1.1.5
		onuAuthenLoidPassword OBJECT-TYPE
			SYNTAX DisplayString
			MAX-ACCESS read-create
			STATUS current
			DESCRIPTION
				"Description."
			::= { onuAuthenticationConfigEntry 5 }

		
		-- 1.3.6.1.4.1.17409.2.8.4.6.1.1.6
		onuAuthenLineProfileId OBJECT-TYPE
			SYNTAX INTEGER
			MAX-ACCESS read-create
			STATUS current
			DESCRIPTION
				"Description."
			::= { onuAuthenticationConfigEntry 6 }

		
		-- 1.3.6.1.4.1.17409.2.8.4.6.1.1.7
		onuAuthenSrvProfileId OBJECT-TYPE
			SYNTAX INTEGER
			MAX-ACCESS read-create
			STATUS current
			DESCRIPTION
				"Description."
			::= { onuAuthenticationConfigEntry 7 }

		
		-- 1.3.6.1.4.1.17409.2.8.4.6.1.1.8
		onuAuthenRowStatus OBJECT-TYPE
			SYNTAX RowStatus
			MAX-ACCESS read-create
			STATUS current
			DESCRIPTION
				"authen Row Status"
			::= { onuAuthenticationConfigEntry 8 }

		
		-- 1.3.6.1.4.1.17409.2.8.4.7
		onuAutoFindTable OBJECT-TYPE
			SYNTAX SEQUENCE OF OnuAutoFindEntry
			MAX-ACCESS not-accessible
			STATUS current
			DESCRIPTION
				"Description."
			::= { onuObjects 7 }

		
		-- 1.3.6.1.4.1.17409.2.8.4.7.1
		onuAutoFindEntry OBJECT-TYPE
			SYNTAX OnuAutoFindEntry
			MAX-ACCESS not-accessible
			STATUS current
			DESCRIPTION
				"Description."
			INDEX { onuAutoFindOnuIndex }
			::= { onuAutoFindTable 1 }

		
		OnuAutoFindEntry ::=
			SEQUENCE { 
				onuAutoFindOnuIndex
					INTEGER,
				onuAutoFindOnuType
					DisplayString,
				onuAutoFindSerialNumber
					DisplayString,
				onuAutoFindPassword
					DisplayString,
				onuAutoFindLoid
					DisplayString,
				onuAutoFindLoidPassword
					DisplayString,
				onuAutoFindTime
					DateAndTime,
				onuAutoSoftwareVersion
					DisplayString,
				onuAutoHardwareVersion
					DisplayString
			 }

		-- 1.3.6.1.4.1.17409.2.8.4.7.1.1
		onuAutoFindOnuIndex OBJECT-TYPE
			SYNTAX INTEGER
			MAX-ACCESS not-accessible
			STATUS current
			DESCRIPTION
				"Description."
			::= { onuAutoFindEntry 1 }

		
		-- 1.3.6.1.4.1.17409.2.8.4.7.1.2
		onuAutoFindOnuType OBJECT-TYPE
			SYNTAX DisplayString
			MAX-ACCESS read-only
			STATUS current
			DESCRIPTION
				"Description."
			::= { onuAutoFindEntry 2 }

		
		-- 1.3.6.1.4.1.17409.2.8.4.7.1.3
		onuAutoFindSerialNumber OBJECT-TYPE
			SYNTAX DisplayString
			MAX-ACCESS read-only
			STATUS current
			DESCRIPTION
				"Description."
			::= { onuAutoFindEntry 3 }

		
		-- 1.3.6.1.4.1.17409.2.8.4.7.1.4
		onuAutoFindPassword OBJECT-TYPE
			SYNTAX DisplayString
			MAX-ACCESS read-only
			STATUS current
			DESCRIPTION
				"Description."
			::= { onuAutoFindEntry 4 }

		
		-- 1.3.6.1.4.1.17409.2.8.4.7.1.5
		onuAutoFindLoid OBJECT-TYPE
			SYNTAX DisplayString
			MAX-ACCESS read-only
			STATUS current
			DESCRIPTION
				"Description."
			::= { onuAutoFindEntry 5 }

		
		-- 1.3.6.1.4.1.17409.2.8.4.7.1.6
		onuAutoFindLoidPassword OBJECT-TYPE
			SYNTAX DisplayString
			MAX-ACCESS read-only
			STATUS current
			DESCRIPTION
				"Description."
			::= { onuAutoFindEntry 6 }

		
		-- 1.3.6.1.4.1.17409.2.8.4.7.1.7
		onuAutoFindTime OBJECT-TYPE
			SYNTAX DateAndTime
			MAX-ACCESS read-only
			STATUS current
			DESCRIPTION
				"Description."
			::= { onuAutoFindEntry 7 }

		
		-- 1.3.6.1.4.1.17409.2.8.4.7.1.8
		onuAutoSoftwareVersion OBJECT-TYPE
			SYNTAX DisplayString
			MAX-ACCESS read-only
			STATUS current
			DESCRIPTION
				"Description."
			::= { onuAutoFindEntry 8 }

		
		-- 1.3.6.1.4.1.17409.2.8.4.7.1.9
		onuAutoHardwareVersion OBJECT-TYPE
			SYNTAX DisplayString
			MAX-ACCESS read-only
			STATUS current
			DESCRIPTION
				"Description."
			::= { onuAutoFindEntry 9 }

		
		-- 1.3.6.1.4.1.17409.2.8.4.8
		onuAutoAuthenticationTable OBJECT-TYPE
			SYNTAX SEQUENCE OF OnuAutoAuthenticationEntry
			MAX-ACCESS not-accessible
			STATUS current
			DESCRIPTION
				"Description."
			::= { onuObjects 8 }

		
		-- 1.3.6.1.4.1.17409.2.8.4.8.1
		onuAutoAuthenticationEntry OBJECT-TYPE
			SYNTAX OnuAutoAuthenticationEntry
			MAX-ACCESS not-accessible
			STATUS current
			DESCRIPTION
				"Description."
			INDEX { onuAutoAuthenIndex }
			::= { onuAutoAuthenticationTable 1 }

		
		OnuAutoAuthenticationEntry ::=
			SEQUENCE { 
				onuAutoAuthenIndex
					INTEGER,
				onuAutoAuthenPortlist
					DisplayString,
				onuAutoAuthenOnuType
					DisplayString,
				onuAutoAuthenEthNum
					INTEGER,
				onuAutoAuthenWlanNum
					INTEGER,
				onuAutoAuthenCatvNum
					INTEGER,
				onuAutoAuthenVeipNum
					INTEGER,
				onuAutoAuthenLineProfileId
					INTEGER,
				onuAutoAuthenSrvProfileId
					INTEGER,
				onuAutoAuthenRowStatus
					RowStatus
			 }

		-- 1.3.6.1.4.1.17409.2.8.4.8.1.1
		onuAutoAuthenIndex OBJECT-TYPE
			SYNTAX INTEGER
			MAX-ACCESS not-accessible
			STATUS current
			DESCRIPTION
				"Description."
			::= { onuAutoAuthenticationEntry 1 }

		
		-- 1.3.6.1.4.1.17409.2.8.4.8.1.2
		onuAutoAuthenPortlist OBJECT-TYPE
			SYNTAX DisplayString
			MAX-ACCESS read-write
			STATUS current
			DESCRIPTION
				"Description."
			::= { onuAutoAuthenticationEntry 2 }
			
			
		-- 1.3.6.1.4.1.17409.2.8.4.8.1.3
		onuAutoAuthenOnuType OBJECT-TYPE
			SYNTAX DisplayString
			MAX-ACCESS read-write
			STATUS current
			DESCRIPTION
				"Description."
			::= { onuAutoAuthenticationEntry 3 }

		
		-- 1.3.6.1.4.1.17409.2.8.4.8.1.4
		onuAutoAuthenEthNum OBJECT-TYPE
			SYNTAX INTEGER
			MAX-ACCESS read-write
			STATUS current
			DESCRIPTION
				"Description."
			::= { onuAutoAuthenticationEntry 4 }

		
		-- 1.3.6.1.4.1.17409.2.8.4.8.1.5
		onuAutoAuthenWlanNum OBJECT-TYPE
			SYNTAX INTEGER
			MAX-ACCESS read-write
			STATUS current
			DESCRIPTION
				"Description."
			::= { onuAutoAuthenticationEntry 5 }

		
		-- 1.3.6.1.4.1.17409.2.8.4.8.1.6
		onuAutoAuthenCatvNum OBJECT-TYPE
			SYNTAX INTEGER
			MAX-ACCESS read-write
			STATUS current
			DESCRIPTION
				"Description."
			::= { onuAutoAuthenticationEntry 6 }

		
		-- 1.3.6.1.4.1.17409.2.8.4.8.1.7
		onuAutoAuthenVeipNum OBJECT-TYPE
			SYNTAX INTEGER
			MAX-ACCESS read-write
			STATUS current
			DESCRIPTION
				"Description."
			::= { onuAutoAuthenticationEntry 7 }

		
		-- 1.3.6.1.4.1.17409.2.8.4.8.1.8
		onuAutoAuthenLineProfileId OBJECT-TYPE
			SYNTAX INTEGER
			MAX-ACCESS read-write
			STATUS current
			DESCRIPTION
				"Description."
			::= { onuAutoAuthenticationEntry 8 }

		
		-- 1.3.6.1.4.1.17409.2.8.4.8.1.9
		onuAutoAuthenSrvProfileId OBJECT-TYPE
			SYNTAX INTEGER
			MAX-ACCESS read-write
			STATUS current
			DESCRIPTION
				"Description."
			::= { onuAutoAuthenticationEntry 9}

		
		-- 1.3.6.1.4.1.17409.2.8.4.8.1.10
		onuAutoAuthenRowStatus OBJECT-TYPE
			SYNTAX RowStatus
			MAX-ACCESS read-create
			STATUS current
			DESCRIPTION
				"Description."
			::= { onuAutoAuthenticationEntry 10 }
	
	END

--
-- NSCRTV-EPONEOC-GPON-ONU-MIB.my
--
