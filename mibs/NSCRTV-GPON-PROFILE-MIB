--
-- NSCRTV-EPONEOC-GPON-PROFILE-MIB.mib
-- MIB generated by MG-SOFT Visual MIB Builder Version 4.0 Build 349
-- Friday, September 30, 2016 at 09:45:40
--

	NSCRTV-EPONEOC-GPON-PROFILE-MIB DEFINITIONS ::= BEGIN
 
		IMPORTS
			BridgeId, Timeout			
				FROM BRIDGE-MIB			
			enterprises, TimeTicks, IpAddress, Unsigned32, Gauge32, 
			Counter32, Counter64, OBJECT-TYPE, OBJECT-IDENTITY, 
			NOTIFICATION-TYPE			
				FROM SNMPv2-SMI			
			DateAndTime, TruthValue, RowStatus, MacAddress, DisplayString, 
			TimeStamp, TEXTUAL-CONVENTION			
				FROM SNMPv2-TC;

--
-- Textual conventions
--
		
--
-- Node definitions
--
	
		-- 1.3.6.1.4.1.17409
		nscrtvRoot OBJECT IDENTIFIER ::= { enterprises 17409 }

		
		-- 1.3.6.1.4.1.17409.2
		nscrtvFTTxTree OBJECT IDENTIFIER ::= { nscrtvRoot 2 }

		
--      DESCRIPTION
		-- 1.3.6.1.4.1.17409.2.8
		gponTree OBJECT IDENTIFIER ::= { nscrtvFTTxTree 8 }
				
		

-- ------------------------------------------------------------------------------
-- gponProfileObjects(1.3.6.1.4.1.17409.2.8.11)
-- ------------------------------------------------------------------------------ 
		-- 1.3.6.1.4.1.17409.2.8.11
		gponProfileObjects OBJECT IDENTIFIER ::= { gponTree 11 }

		
		-- 1.3.6.1.4.1.17409.2.8.11.1
		gponDbaProfileObjects OBJECT IDENTIFIER ::= { gponProfileObjects 1 }

		
		-- 1.3.6.1.4.1.17409.2.8.11.1.1
		gponDbaProfileInfoTable OBJECT-TYPE
			SYNTAX SEQUENCE OF GponDbaProfileInfoEntry
			MAX-ACCESS not-accessible
			STATUS current
			DESCRIPTION
				"Description."
			::= { gponDbaProfileObjects 1 }

		
		-- 1.3.6.1.4.1.17409.2.8.11.1.1.1
		gponDbaProfileInfoEntry OBJECT-TYPE
			SYNTAX GponDbaProfileInfoEntry
			MAX-ACCESS not-accessible
			STATUS current
			DESCRIPTION
				"Description."
			INDEX { gponDbaProfileId }
			::= { gponDbaProfileInfoTable 1 }

		
		GponDbaProfileInfoEntry ::=
			SEQUENCE { 
				gponDbaProfileId
					INTEGER,
				gponDbaProfileName
					DisplayString,
				gponDbaProfileType
					INTEGER,
				gponDbaProfileFixRate
					INTEGER,
				gponDbaProfileAssureRate
					INTEGER,
				gponDbaProfileMaxRate
					INTEGER,
				gponDbaProfileBindNum
					INTEGER,
				gponDbaProfileRowStatus
					RowStatus
			 }

		-- 1.3.6.1.4.1.17409.2.8.11.1.1.1.1
		gponDbaProfileId OBJECT-TYPE
			SYNTAX INTEGER
			MAX-ACCESS not-accessible
			STATUS current
			DESCRIPTION
				"Description."
			::= { gponDbaProfileInfoEntry 1 }

		
		-- 1.3.6.1.4.1.17409.2.8.11.1.1.1.2
		gponDbaProfileName OBJECT-TYPE
			SYNTAX DisplayString
			MAX-ACCESS read-write
			STATUS current
			DESCRIPTION
				"Description."
			::= { gponDbaProfileInfoEntry 2 }

		
		-- 1.3.6.1.4.1.17409.2.8.11.1.1.1.3
		gponDbaProfileType OBJECT-TYPE
			SYNTAX INTEGER
				{
				invalid(0),
				type-1(1),
				type-2(2),
				type-3(3),
				type-4(4),
				type-5(5)
				}
			MAX-ACCESS read-write
			STATUS current
			DESCRIPTION
				"Description."
			::= { gponDbaProfileInfoEntry 3 }

		
		-- 1.3.6.1.4.1.17409.2.8.11.1.1.1.4
		gponDbaProfileFixRate OBJECT-TYPE
			SYNTAX INTEGER
			UNITS "kbit/s"
			MAX-ACCESS read-write
			STATUS current
			DESCRIPTION
				"Description."
			::= { gponDbaProfileInfoEntry 4 }

		
		-- 1.3.6.1.4.1.17409.2.8.11.1.1.1.5
		gponDbaProfileAssureRate OBJECT-TYPE
			SYNTAX INTEGER
			UNITS "kbit/s"
			MAX-ACCESS read-write
			STATUS current
			DESCRIPTION
				"Description."
			::= { gponDbaProfileInfoEntry 5 }

		
		-- 1.3.6.1.4.1.17409.2.8.11.1.1.1.6
		gponDbaProfileMaxRate OBJECT-TYPE
			SYNTAX INTEGER
			UNITS "kbit/s"
			MAX-ACCESS read-write
			STATUS current
			DESCRIPTION
				"Description."
			::= { gponDbaProfileInfoEntry 6 }

		
		-- 1.3.6.1.4.1.17409.2.8.11.1.1.1.7
		gponDbaProfileBindNum OBJECT-TYPE
			SYNTAX INTEGER
			MAX-ACCESS read-only
			STATUS current
			DESCRIPTION
				"Description."
			::= { gponDbaProfileInfoEntry 7 }

		
		-- 1.3.6.1.4.1.17409.2.8.11.1.1.1.8
		gponDbaProfileRowStatus OBJECT-TYPE
			SYNTAX RowStatus
			MAX-ACCESS read-create
			STATUS current
			DESCRIPTION
				"Description."
			::= { gponDbaProfileInfoEntry 8 }

		
		-- 1.3.6.1.4.1.17409.2.8.11.2
		gponLineProfileObjects OBJECT IDENTIFIER ::= { gponProfileObjects 2 }

		
		-- 1.3.6.1.4.1.17409.2.8.11.2.1
		gponLineProfileInfoTable OBJECT-TYPE
			SYNTAX SEQUENCE OF GponLineProfileInfoEntry
			MAX-ACCESS not-accessible
			STATUS current
			DESCRIPTION
				"Description."
			::= { gponLineProfileObjects 1 }

		
		-- 1.3.6.1.4.1.17409.2.8.11.2.1.1
		gponLineProfileInfoEntry OBJECT-TYPE
			SYNTAX GponLineProfileInfoEntry
			MAX-ACCESS not-accessible
			STATUS current
			DESCRIPTION
				"Description."
			INDEX { gponLineProfileId }
			::= { gponLineProfileInfoTable 1 }

		
		GponLineProfileInfoEntry ::=
			SEQUENCE { 
				gponLineProfileId
					INTEGER,
				gponLineProfileName
					DisplayString,
				gponLineProfileUpstreamFECMode
					INTEGER,
				gponLineProfileMappingMode
					INTEGER,
				gponLineProfileTcontNum
					INTEGER,
				gponLineProfileGemNum
					INTEGER,
				gponLineProfileBindNum
					INTEGER,
				gponLineProfileRowStatus
					RowStatus
			 }

		-- 1.3.6.1.4.1.17409.2.8.11.2.1.1.1
		gponLineProfileId OBJECT-TYPE
			SYNTAX INTEGER
			MAX-ACCESS not-accessible
			STATUS current
			DESCRIPTION
				"Description."
			::= { gponLineProfileInfoEntry 1 }

		
		-- 1.3.6.1.4.1.17409.2.8.11.2.1.1.2
		gponLineProfileName OBJECT-TYPE
			SYNTAX DisplayString
			MAX-ACCESS read-write
			STATUS current
			DESCRIPTION
				"Description."
			::= { gponLineProfileInfoEntry 2 }

		
		-- 1.3.6.1.4.1.17409.2.8.11.2.1.1.3
		gponLineProfileUpstreamFECMode OBJECT-TYPE
			SYNTAX INTEGER
				{
				on(1),
				off(2)
				}
			MAX-ACCESS read-write
			STATUS current
			DESCRIPTION
				"Description."
			DEFVAL { off }
			::= { gponLineProfileInfoEntry 3 }

		
		-- 1.3.6.1.4.1.17409.2.8.11.2.1.1.4
		gponLineProfileMappingMode OBJECT-TYPE
			SYNTAX INTEGER
				{
				vlan(1),
				priority(2),
				vlan-priority(3),
				port(4)
				}
			MAX-ACCESS read-write
			STATUS current
			DESCRIPTION
				"Description."
			::= { gponLineProfileInfoEntry 4 }

		
		-- 1.3.6.1.4.1.17409.2.8.11.2.1.1.5
		gponLineProfileTcontNum OBJECT-TYPE
			SYNTAX INTEGER
			MAX-ACCESS read-only
			STATUS current
			DESCRIPTION
				"Description."
			::= { gponLineProfileInfoEntry 5 }

		
		-- 1.3.6.1.4.1.17409.2.8.11.2.1.1.6
		gponLineProfileGemNum OBJECT-TYPE
			SYNTAX INTEGER
			MAX-ACCESS read-only
			STATUS current
			DESCRIPTION
				"Description."
			::= { gponLineProfileInfoEntry 6 }

		
		-- 1.3.6.1.4.1.17409.2.8.11.2.1.1.7
		gponLineProfileBindNum OBJECT-TYPE
			SYNTAX INTEGER
			MAX-ACCESS read-only
			STATUS current
			DESCRIPTION
				"Description."
			::= { gponLineProfileInfoEntry 7 }

		
		-- 1.3.6.1.4.1.17409.2.8.11.2.1.1.8
		gponLineProfileRowStatus OBJECT-TYPE
			SYNTAX RowStatus
			MAX-ACCESS read-create
			STATUS current
			DESCRIPTION
				"Description."
			::= { gponLineProfileInfoEntry 8 }

		
		-- 1.3.6.1.4.1.17409.2.8.11.2.2
		gponLineProfileTcontTable OBJECT-TYPE
			SYNTAX SEQUENCE OF GponLineProfileTcontEntry
			MAX-ACCESS not-accessible
			STATUS current
			DESCRIPTION
				"Description."
			::= { gponLineProfileObjects 2 }

		
		-- 1.3.6.1.4.1.17409.2.8.11.2.2.1
		gponLineProfileTcontEntry OBJECT-TYPE
			SYNTAX GponLineProfileTcontEntry
			MAX-ACCESS not-accessible
			STATUS current
			DESCRIPTION
				"Description."
			INDEX { gponLineProfileTcontProfileIndex, gponLineProfileTcontIndex }
			::= { gponLineProfileTcontTable 1 }

		
		GponLineProfileTcontEntry ::=
			SEQUENCE { 
				gponLineProfileTcontProfileIndex
					INTEGER,
				gponLineProfileTcontIndex
					INTEGER,
				gponLineProfileTcontDbaProfileId
					INTEGER,
				gponLineProfileTcontRowStatus
					RowStatus
			 }

		-- 1.3.6.1.4.1.17409.2.8.11.2.2.1.1
		gponLineProfileTcontProfileIndex OBJECT-TYPE
			SYNTAX INTEGER
			MAX-ACCESS not-accessible
			STATUS current
			DESCRIPTION
				"Description."
			::= { gponLineProfileTcontEntry 1 }

		
		-- 1.3.6.1.4.1.17409.2.8.11.2.2.1.2
		gponLineProfileTcontIndex OBJECT-TYPE
			SYNTAX INTEGER
			MAX-ACCESS not-accessible
			STATUS current
			DESCRIPTION
				"Description."
			::= { gponLineProfileTcontEntry 2 }

		
		-- 1.3.6.1.4.1.17409.2.8.11.2.2.1.3
		gponLineProfileTcontDbaProfileId OBJECT-TYPE
			SYNTAX INTEGER
			MAX-ACCESS read-write
			STATUS current
			DESCRIPTION
				"Description."
			::= { gponLineProfileTcontEntry 3 }

		
		-- 1.3.6.1.4.1.17409.2.8.11.2.2.1.4
		gponLineProfileTcontRowStatus OBJECT-TYPE
			SYNTAX RowStatus
			MAX-ACCESS read-create
			STATUS current
			DESCRIPTION
				"Description."
			::= { gponLineProfileTcontEntry 4 }

		
		-- 1.3.6.1.4.1.17409.2.8.11.2.3
		gponLineProfileGemTable OBJECT-TYPE
			SYNTAX SEQUENCE OF GponLineProfileGemEntry
			MAX-ACCESS not-accessible
			STATUS current
			DESCRIPTION
				"Description."
			::= { gponLineProfileObjects 3 }

		
		-- 1.3.6.1.4.1.17409.2.8.11.2.3.1
		gponLineProfileGemEntry OBJECT-TYPE
			SYNTAX GponLineProfileGemEntry
			MAX-ACCESS not-accessible
			STATUS current
			DESCRIPTION
				"Description."
			INDEX { gponLineProfileGemProfileIndex, gponLineProfileGemIndex }
			::= { gponLineProfileGemTable 1 }

		
		GponLineProfileGemEntry ::=
			SEQUENCE { 
				gponLineProfileGemProfileIndex
					INTEGER,
				gponLineProfileGemIndex
					INTEGER,
				gponLineProfileGemEncrypt
					INTEGER,
				gponLineProfileGemTcontId
					INTEGER,
				gponLineProfileGemQueuePri
					INTEGER,
				gponLineProfileGemUpCar
					INTEGER,
				gponLineProfileGemDownCar
					INTEGER,
				gponLineProfileGemMapNum
					INTEGER,
				gponLineProfileGemRowStatus
					RowStatus
			 }

		-- 1.3.6.1.4.1.17409.2.8.11.2.3.1.1
		gponLineProfileGemProfileIndex OBJECT-TYPE
			SYNTAX INTEGER
			MAX-ACCESS not-accessible
			STATUS current
			DESCRIPTION
				"Description."
			::= { gponLineProfileGemEntry 1 }

		
		-- 1.3.6.1.4.1.17409.2.8.11.2.3.1.2
		gponLineProfileGemIndex OBJECT-TYPE
			SYNTAX INTEGER
			MAX-ACCESS not-accessible
			STATUS current
			DESCRIPTION
				"Description."
			::= { gponLineProfileGemEntry 2 }

		
		-- 1.3.6.1.4.1.17409.2.8.11.2.3.1.3
		gponLineProfileGemEncrypt OBJECT-TYPE
			SYNTAX INTEGER
				{
				unconcern(0),
				enable(1),
				disable(2)
				}
			MAX-ACCESS read-write
			STATUS current
			DESCRIPTION
				"Description."
			::= { gponLineProfileGemEntry 3 }

		
		-- 1.3.6.1.4.1.17409.2.8.11.2.3.1.4
		gponLineProfileGemTcontId OBJECT-TYPE
			SYNTAX INTEGER
			MAX-ACCESS read-write
			STATUS current
			DESCRIPTION
				"Description."
			::= { gponLineProfileGemEntry 4 }

		
		-- 1.3.6.1.4.1.17409.2.8.11.2.3.1.5
		gponLineProfileGemQueuePri OBJECT-TYPE
			SYNTAX INTEGER (0..7)
			MAX-ACCESS read-write
			STATUS current
			DESCRIPTION
				"Description."
			DEFVAL { 0 }
			::= { gponLineProfileGemEntry 5 }


		-- 1.3.6.1.4.1.17409.2.8.11.2.3.1.6
		gponLineProfileGemUpCar OBJECT-TYPE
			SYNTAX INTEGER (0 | 1..1024)
			MAX-ACCESS read-write
			STATUS current
			DESCRIPTION
				"0:unconcern"
			::= { gponLineProfileGemEntry 6 }

		
		-- 1.3.6.1.4.1.17409.2.8.11.2.3.1.7
		gponLineProfileGemDownCar OBJECT-TYPE
			SYNTAX INTEGER (0 | 1..1024)
			MAX-ACCESS read-write
			STATUS current
			DESCRIPTION
				"0:unconcern"
			::= { gponLineProfileGemEntry 7 }

		
		-- 1.3.6.1.4.1.17409.2.8.11.2.3.1.8
		gponLineProfileGemMapNum OBJECT-TYPE
			SYNTAX INTEGER
			MAX-ACCESS read-only
			STATUS current
			DESCRIPTION
				"Description."
			::= { gponLineProfileGemEntry 8 }

		
		-- 1.3.6.1.4.1.17409.2.8.11.2.3.1.9
		gponLineProfileGemRowStatus OBJECT-TYPE
			SYNTAX RowStatus
			MAX-ACCESS read-create
			STATUS current
			DESCRIPTION
				"Description."
			::= { gponLineProfileGemEntry 9 }

		
		-- 1.3.6.1.4.1.17409.2.8.11.2.4
		gponLineProfileGemMapTable OBJECT-TYPE
			SYNTAX SEQUENCE OF GponLineProfileGemMapEntry
			MAX-ACCESS not-accessible
			STATUS current
			DESCRIPTION
				"Description."
			::= { gponLineProfileObjects 4 }

		
		-- 1.3.6.1.4.1.17409.2.8.11.2.4.1
		gponLineProfileGemMapEntry OBJECT-TYPE
			SYNTAX GponLineProfileGemMapEntry
			MAX-ACCESS not-accessible
			STATUS current
			DESCRIPTION
				"Description."
			INDEX { gponLineProfileGemMapProfileIndex, gponLineProfileGemMapGemIndex, gponLineProfileGemMapIndex }
			::= { gponLineProfileGemMapTable 1 }

		
		GponLineProfileGemMapEntry ::=
			SEQUENCE { 
				gponLineProfileGemMapProfileIndex
					INTEGER,
				gponLineProfileGemMapGemIndex
					INTEGER,
				gponLineProfileGemMapIndex
					INTEGER,
				gponLineProfileGemMapVlan
					INTEGER,
				gponLineProfileGemMapPriority
					INTEGER,
				gponLineProfileGemMapPortType
					INTEGER,
				gponLineProfileGemMapPortId
					INTEGER,
				gponLineProfileGemMapRowStatus
					RowStatus
			 }

		-- 1.3.6.1.4.1.17409.2.8.11.2.4.1.1
		gponLineProfileGemMapProfileIndex OBJECT-TYPE
			SYNTAX INTEGER
			MAX-ACCESS not-accessible
			STATUS current
			DESCRIPTION
				"Description."
			::= { gponLineProfileGemMapEntry 1 }

		
		-- 1.3.6.1.4.1.17409.2.8.11.2.4.1.2
		gponLineProfileGemMapGemIndex OBJECT-TYPE
			SYNTAX INTEGER
			MAX-ACCESS not-accessible
			STATUS current
			DESCRIPTION
				"Description."
			::= { gponLineProfileGemMapEntry 2 }

		
		-- 1.3.6.1.4.1.17409.2.8.11.2.4.1.3
		gponLineProfileGemMapIndex OBJECT-TYPE
			SYNTAX INTEGER
			MAX-ACCESS not-accessible
			STATUS current
			DESCRIPTION
				"Description."
			::= { gponLineProfileGemMapEntry 3 }

		
		-- 1.3.6.1.4.1.17409.2.8.11.2.4.1.4
		gponLineProfileGemMapVlan OBJECT-TYPE
			SYNTAX INTEGER
			MAX-ACCESS read-create
			STATUS current
			DESCRIPTION
				"Description."
			::= { gponLineProfileGemMapEntry 4 }

		
		-- 1.3.6.1.4.1.17409.2.8.11.2.4.1.5
		gponLineProfileGemMapPriority OBJECT-TYPE
			SYNTAX INTEGER
			MAX-ACCESS read-create
			STATUS current
			DESCRIPTION
				"Description."
			::= { gponLineProfileGemMapEntry 5 }

		
		-- 1.3.6.1.4.1.17409.2.8.11.2.4.1.6
		gponLineProfileGemMapPortType OBJECT-TYPE
			SYNTAX INTEGER
				{
				eth(1),
				iphost(2)
				}
			MAX-ACCESS read-write
			STATUS current
			DESCRIPTION
				"Description."
			::= { gponLineProfileGemMapEntry 6 }

		
		-- 1.3.6.1.4.1.17409.2.8.11.2.4.1.7
		gponLineProfileGemMapPortId OBJECT-TYPE
			SYNTAX INTEGER
			MAX-ACCESS read-create
			STATUS current
			DESCRIPTION
				"Description."
			::= { gponLineProfileGemMapEntry 7 }

		
		-- 1.3.6.1.4.1.17409.2.8.11.2.4.1.8
		gponLineProfileGemMapRowStatus OBJECT-TYPE
			SYNTAX RowStatus
			MAX-ACCESS read-create
			STATUS current
			DESCRIPTION
				"Description."
			::= { gponLineProfileGemMapEntry 8 }

		
		-- 1.3.6.1.4.1.17409.2.8.11.3
		gponSrvProfileObjects OBJECT IDENTIFIER ::= { gponProfileObjects 3 }

		
		-- 1.3.6.1.4.1.17409.2.8.11.3.1
		gponSrvProfileInfoTable OBJECT-TYPE
			SYNTAX SEQUENCE OF GponSrvProfileInfoEntry
			MAX-ACCESS not-accessible
			STATUS current
			DESCRIPTION
				"Description."
			::= { gponSrvProfileObjects 1 }

		
		-- 1.3.6.1.4.1.17409.2.8.11.3.1.1
		gponSrvProfileInfoEntry OBJECT-TYPE
			SYNTAX GponSrvProfileInfoEntry
			MAX-ACCESS not-accessible
			STATUS current
			DESCRIPTION
				"Description."
			INDEX { gponSrvProfileId }
			::= { gponSrvProfileInfoTable 1 }

		
		GponSrvProfileInfoEntry ::=
			SEQUENCE { 
				gponSrvProfileId
					INTEGER,
				gponSrvProfileName
					DisplayString,
				gponSrvProfileBindNum
					INTEGER,
				gponSrvProfileRowStatus
					RowStatus
			 }

		-- 1.3.6.1.4.1.17409.2.8.11.3.1.1.1
		gponSrvProfileId OBJECT-TYPE
			SYNTAX INTEGER
			MAX-ACCESS not-accessible
			STATUS current
			DESCRIPTION
				"Description."
			::= { gponSrvProfileInfoEntry 1 }

		
		-- 1.3.6.1.4.1.17409.2.8.11.3.1.1.2
		gponSrvProfileName OBJECT-TYPE
			SYNTAX DisplayString
			MAX-ACCESS read-write
			STATUS current
			DESCRIPTION
				"Description."
			::= { gponSrvProfileInfoEntry 2 }

		
		-- 1.3.6.1.4.1.17409.2.8.11.3.1.1.3
		gponSrvProfileBindNum OBJECT-TYPE
			SYNTAX INTEGER
			MAX-ACCESS read-only
			STATUS current
			DESCRIPTION
				"Description."
			::= { gponSrvProfileInfoEntry 3 }

		
		-- 1.3.6.1.4.1.17409.2.8.11.3.1.1.4
		gponSrvProfileRowStatus OBJECT-TYPE
			SYNTAX RowStatus
			MAX-ACCESS read-create
			STATUS current
			DESCRIPTION
				"Description."
			::= { gponSrvProfileInfoEntry 4 }

		
		-- 1.3.6.1.4.1.17409.2.8.11.3.2
		gponSrvProfileCfgTable OBJECT-TYPE
			SYNTAX SEQUENCE OF GponSrvProfileCfgEntry
			MAX-ACCESS not-accessible
			STATUS current
			DESCRIPTION
				"Description."
			::= { gponSrvProfileObjects 2 }

		
		-- 1.3.6.1.4.1.17409.2.8.11.3.2.1
		gponSrvProfileCfgEntry OBJECT-TYPE
			SYNTAX GponSrvProfileCfgEntry
			MAX-ACCESS not-accessible
			STATUS current
			DESCRIPTION
				"Description."
			INDEX { gponSrvProfileIndex }
			::= { gponSrvProfileCfgTable 1 }

		
		GponSrvProfileCfgEntry ::=
			SEQUENCE { 
				gponSrvProfileIndex
					INTEGER,
				gponSrvProfileMacLearning
					INTEGER,
				gponSrvProfileMacAgeSeconds
					INTEGER,
				gponSrvProfileLoopbackDetectCheck
					INTEGER,
				gponSrvProfileMcMode
					INTEGER,
				gponSrvProfileMcFastLeave
					INTEGER,
				gponSrvProfileUpIgmpFwdMode
					INTEGER,
				gponSrvProfileUpIgmpTCI
					INTEGER
			 }

		-- 1.3.6.1.4.1.17409.2.8.11.3.2.1.1
		gponSrvProfileIndex OBJECT-TYPE
			SYNTAX INTEGER
			MAX-ACCESS not-accessible
			STATUS current
			DESCRIPTION
				"Description."
			::= { gponSrvProfileCfgEntry 1 }

		
		-- 1.3.6.1.4.1.17409.2.8.11.3.2.1.2
		gponSrvProfileMacLearning OBJECT-TYPE
			SYNTAX INTEGER
				{
				unconcern(0),
				enable(1),
				disable(2)
				}
			MAX-ACCESS read-write
			STATUS current
			DESCRIPTION
				"Description."
			::= { gponSrvProfileCfgEntry 2 }

		
		-- 1.3.6.1.4.1.17409.2.8.11.3.2.1.3
		gponSrvProfileMacAgeSeconds OBJECT-TYPE
			SYNTAX INTEGER (-1 | 0 | 10..1000000)
			UNITS "second"
			MAX-ACCESS read-write
			STATUS current
			DESCRIPTION
				"0:unconcern;
				-1:unlimited;
				10-1000000:实际老化时间 "
			::= { gponSrvProfileCfgEntry 3 }

		
		-- 1.3.6.1.4.1.17409.2.8.11.3.2.1.4
		gponSrvProfileLoopbackDetectCheck OBJECT-TYPE
			SYNTAX INTEGER
				{
				unconcern(0),
				enable(1),
				disable(2)
				}
			MAX-ACCESS read-write
			STATUS current
			DESCRIPTION
				"Description."
			::= { gponSrvProfileCfgEntry 4 }

		
		-- 1.3.6.1.4.1.17409.2.8.11.3.2.1.5
		gponSrvProfileMcMode OBJECT-TYPE
			SYNTAX INTEGER
				{
				unconcern(0),
				igmpSnooping(1),
				olt-control(2)
				}
			MAX-ACCESS read-write
			STATUS current
			DESCRIPTION
				"Description."
			::= { gponSrvProfileCfgEntry 5 }

		
		-- 1.3.6.1.4.1.17409.2.8.11.3.2.1.6
		gponSrvProfileMcFastLeave OBJECT-TYPE
			SYNTAX INTEGER
				{
				unconcern(0),
				enable(1),
				disable(2)
				}
			MAX-ACCESS read-write
			STATUS current
			DESCRIPTION
				"Description."
			::= { gponSrvProfileCfgEntry 6 }

		
		-- 1.3.6.1.4.1.17409.2.8.11.3.2.1.7
		gponSrvProfileUpIgmpFwdMode OBJECT-TYPE
			SYNTAX INTEGER
				{
				unconcern(0),
				translation(1),
				vlan(2),
				transparent(3)
				}
			MAX-ACCESS read-write
			STATUS current
			DESCRIPTION
				"Description."
			::= { gponSrvProfileCfgEntry 7 }

		
		-- 1.3.6.1.4.1.17409.2.8.11.3.2.1.8
		gponSrvProfileUpIgmpTCI OBJECT-TYPE
			SYNTAX INTEGER
			MAX-ACCESS read-write
			STATUS current
			DESCRIPTION
				"0：unconcern;
				0-15bit:vlan, 16-31bit:pri"
			::= { gponSrvProfileCfgEntry 8 }

		
		-- 1.3.6.1.4.1.17409.2.8.11.3.3
		gponSrvProfilePortNumTable OBJECT-TYPE
			SYNTAX SEQUENCE OF GponSrvProfilePortNumEntry
			MAX-ACCESS not-accessible
			STATUS current
			DESCRIPTION
				"Description."
			::= { gponSrvProfileObjects 3 }

		
		-- 1.3.6.1.4.1.17409.2.8.11.3.3.1
		gponSrvProfilePortNumEntry OBJECT-TYPE
			SYNTAX GponSrvProfilePortNumEntry
			MAX-ACCESS not-accessible
			STATUS current
			DESCRIPTION
				"Description."
			INDEX { gponSrvProfilePortNumProfileIndex }
			::= { gponSrvProfilePortNumTable 1 }

		
		GponSrvProfilePortNumEntry ::=
			SEQUENCE { 
				gponSrvProfilePortNumProfileIndex
					INTEGER,
				gponSrvProfileEthNum
					INTEGER,
				gponSrvProfileCatvNum
					INTEGER,
				gponSrvProfileWlanNum
					INTEGER,
				gponSrvProfileVeipNum
					INTEGER
			 }

		-- 1.3.6.1.4.1.17409.2.8.11.3.3.1.1
		gponSrvProfilePortNumProfileIndex OBJECT-TYPE
			SYNTAX INTEGER
			MAX-ACCESS not-accessible
			STATUS current
			DESCRIPTION
				"Description."
			::= { gponSrvProfilePortNumEntry 1 }

		
		-- 1.3.6.1.4.1.17409.2.8.11.3.3.1.2
		gponSrvProfileEthNum OBJECT-TYPE
			SYNTAX INTEGER (-1 | 0..24)
			MAX-ACCESS read-write
			STATUS current
			DESCRIPTION
				" -1:adaptive , 
				0-24:port num"
			::= { gponSrvProfilePortNumEntry 2 }

		
		-- 1.3.6.1.4.1.17409.2.8.11.3.3.1.3
		gponSrvProfileCatvNum OBJECT-TYPE
			SYNTAX INTEGER (-1 | 0..2)
			MAX-ACCESS read-write
			STATUS current
			DESCRIPTION
				"-1:adaptive ,	0-2:port num"
			::= { gponSrvProfilePortNumEntry 3 }

		
		-- 1.3.6.1.4.1.17409.2.8.11.3.3.1.4
		gponSrvProfileWlanNum OBJECT-TYPE
			SYNTAX INTEGER (-1 | 0..2)
			MAX-ACCESS read-write
			STATUS current
			DESCRIPTION
				"-1:adaptive, 0-2:port num"
			::= { gponSrvProfilePortNumEntry 4 }

		
		-- 1.3.6.1.4.1.17409.2.8.11.3.3.1.5
		gponSrvProfileVeipNum OBJECT-TYPE
			SYNTAX INTEGER (-1 | 0..8)
			MAX-ACCESS read-write
			STATUS current
			DESCRIPTION
				" -1:adaptive , 0-8:port num"
			::= { gponSrvProfilePortNumEntry 5 }

		
		-- 1.3.6.1.4.1.17409.2.8.11.3.4
		gponSrvProfileEthPortConfigTable OBJECT-TYPE
			SYNTAX SEQUENCE OF GponSrvProfileEthPortConfigEntry
			MAX-ACCESS not-accessible
			STATUS current
			DESCRIPTION
				"Description."
			::= { gponSrvProfileObjects 4 }

		
		-- 1.3.6.1.4.1.17409.2.8.11.3.4.1
		gponSrvProfileEthPortConfigEntry OBJECT-TYPE
			SYNTAX GponSrvProfileEthPortConfigEntry
			MAX-ACCESS not-accessible
			STATUS current
			DESCRIPTION
				"Description."
			INDEX { gponSrvProfileEthPortProfileIndex, gponSrvProfileEthPortIdIndex }
			::= { gponSrvProfileEthPortConfigTable 1 }

		
		GponSrvProfileEthPortConfigEntry ::=
			SEQUENCE { 
				gponSrvProfileEthPortProfileIndex
					INTEGER,
				gponSrvProfileEthPortIdIndex
					INTEGER,
				gponSrvProfileEthPortMacLimited
					INTEGER,
				gponSrvProfileEthPortMtu
					INTEGER,
				gponSrvProfileEthPortFlowCtrl
					INTEGER,
				gponSrvProfileEthPortInTrafficProfileId
					INTEGER,
				gponSrvProfileEthPortOutTrafficProfileId
					INTEGER
			 }

		-- 1.3.6.1.4.1.17409.2.8.11.3.4.1.1
		gponSrvProfileEthPortProfileIndex OBJECT-TYPE
			SYNTAX INTEGER
			MAX-ACCESS not-accessible
			STATUS current
			DESCRIPTION
				"Description."
			::= { gponSrvProfileEthPortConfigEntry 1 }

		
		-- 1.3.6.1.4.1.17409.2.8.11.3.4.1.2
		gponSrvProfileEthPortIdIndex OBJECT-TYPE
			SYNTAX INTEGER
			MAX-ACCESS not-accessible
			STATUS current
			DESCRIPTION
				"Description."
			::= { gponSrvProfileEthPortConfigEntry 2 }

		
		-- 1.3.6.1.4.1.17409.2.8.11.3.4.1.3
		gponSrvProfileEthPortMacLimited OBJECT-TYPE
			SYNTAX INTEGER (-1 | 0..255)
			MAX-ACCESS read-write
			STATUS current
			DESCRIPTION
				"-1:unconcern,
				 0:unlimited"
			::= { gponSrvProfileEthPortConfigEntry 3 }

		
		-- 1.3.6.1.4.1.17409.2.8.11.3.4.1.4
		gponSrvProfileEthPortMtu OBJECT-TYPE
			SYNTAX INTEGER (0 | 1518..2000)
			MAX-ACCESS read-write
			STATUS current
			DESCRIPTION
				"0:unconcern"
			::= { gponSrvProfileEthPortConfigEntry 4 }

		
		-- 1.3.6.1.4.1.17409.2.8.11.3.4.1.5
		gponSrvProfileEthPortFlowCtrl OBJECT-TYPE
			SYNTAX INTEGER
				{
				unconcern(0),
				enable(1),
				disable(2)
				}
			MAX-ACCESS read-write
			STATUS current
			DESCRIPTION
				"Description."
			::= { gponSrvProfileEthPortConfigEntry 5 }

		
		-- 1.3.6.1.4.1.17409.2.8.11.3.4.1.6
		gponSrvProfileEthPortInTrafficProfileId OBJECT-TYPE
			SYNTAX INTEGER (0..1024)
			MAX-ACCESS read-write
			STATUS current
			DESCRIPTION
				"0:unconcern"
			::= { gponSrvProfileEthPortConfigEntry 6 }

		
		-- 1.3.6.1.4.1.17409.2.8.11.3.4.1.7
		gponSrvProfileEthPortOutTrafficProfileId OBJECT-TYPE
			SYNTAX INTEGER (0..1024)
			MAX-ACCESS read-write
			STATUS current
			DESCRIPTION
				"0:unconcern"
			::= { gponSrvProfileEthPortConfigEntry 7 }
		
				
		-- 1.3.6.1.4.1.17409.2.8.11.3.5
		gponSrvProfilePortVlanObjects OBJECT IDENTIFIER ::= { gponSrvProfileObjects 5 }

		
		-- 1.3.6.1.4.1.17409.2.8.11.3.5.1
		gponSrvProfilePortVlanCfgTable OBJECT-TYPE
			SYNTAX SEQUENCE OF GponSrvProfilePortVlanCfgEntry
			MAX-ACCESS not-accessible
			STATUS current
			DESCRIPTION
				"Description."
			::= { gponSrvProfilePortVlanObjects 1 }

		
		-- 1.3.6.1.4.1.17409.2.8.11.3.5.1.1
		gponSrvProfilePortVlanCfgEntry OBJECT-TYPE
			SYNTAX GponSrvProfilePortVlanCfgEntry
			MAX-ACCESS not-accessible
			STATUS current
			DESCRIPTION
				"Description."
			INDEX { gponSrvProfilePortVlanProfileIndex, gponSrvProfilePortVlanPortTypeIndex, gponSrvProfilePortVlanPortIdIndex }
			::= { gponSrvProfilePortVlanCfgTable 1 }

		
		GponSrvProfilePortVlanCfgEntry ::=
			SEQUENCE { 
				gponSrvProfilePortVlanProfileIndex
					INTEGER,
				gponSrvProfilePortVlanPortTypeIndex
					INTEGER,
				gponSrvProfilePortVlanPortIdIndex
					INTEGER,
				gponSrvProfilePortVlanPvid
					INTEGER,
				gponSrvProfilePortVlanPvidPri
					INTEGER,
				gponSrvProfilePortVlanMode
					INTEGER
			 }

		-- 1.3.6.1.4.1.17409.2.8.11.3.5.1.1.1
		gponSrvProfilePortVlanProfileIndex OBJECT-TYPE
			SYNTAX INTEGER
			MAX-ACCESS not-accessible
			STATUS current
			DESCRIPTION
				"Description."
			::= { gponSrvProfilePortVlanCfgEntry 1 }

		
		-- 1.3.6.1.4.1.17409.2.8.11.3.5.1.1.2
		gponSrvProfilePortVlanPortTypeIndex OBJECT-TYPE
			SYNTAX INTEGER
				{
				eth(0),
				wlan(1),
				catv(2)
				}
			MAX-ACCESS not-accessible
			STATUS current
			DESCRIPTION
				"Description."
			::= { gponSrvProfilePortVlanCfgEntry 2 }

		
		-- 1.3.6.1.4.1.17409.2.8.11.3.5.1.1.3
		gponSrvProfilePortVlanPortIdIndex OBJECT-TYPE
			SYNTAX INTEGER
			MAX-ACCESS not-accessible
			STATUS current
			DESCRIPTION
				"Description."
			::= { gponSrvProfilePortVlanCfgEntry 3 }

		
		-- 1.3.6.1.4.1.17409.2.8.11.3.5.1.1.4
		gponSrvProfilePortVlanPvid OBJECT-TYPE
			SYNTAX INTEGER (0..4094)
			MAX-ACCESS read-write
			STATUS current
			DESCRIPTION
				"0:unconcern"
			::= { gponSrvProfilePortVlanCfgEntry 4 }

		
		-- 1.3.6.1.4.1.17409.2.8.11.3.5.1.1.5
		gponSrvProfilePortVlanPvidPri OBJECT-TYPE
			SYNTAX INTEGER (0..7)
			MAX-ACCESS read-write
			STATUS current
			DESCRIPTION
				"Description."
			::= { gponSrvProfilePortVlanCfgEntry 5 }

		
		-- 1.3.6.1.4.1.17409.2.8.11.3.5.1.1.6
		gponSrvProfilePortVlanMode OBJECT-TYPE
			SYNTAX INTEGER
				{
				transparent(0),
				tag(1),
				translate(2),
				aggregation(3),
				trunk(4)
				}
			MAX-ACCESS read-write
			STATUS current
			DESCRIPTION
				"Description."
			::= { gponSrvProfilePortVlanCfgEntry 6 }

		
		-- 1.3.6.1.4.1.17409.2.8.11.3.5.2
		gponSrvProfilePortVlanTranslationTable OBJECT-TYPE
			SYNTAX SEQUENCE OF GponSrvProfilePortVlanTranslationEntry
			MAX-ACCESS not-accessible
			STATUS current
			DESCRIPTION
				"Description."
			::= { gponSrvProfilePortVlanObjects 2 }

		
		-- 1.3.6.1.4.1.17409.2.8.11.3.5.2.1
		gponSrvProfilePortVlanTranslationEntry OBJECT-TYPE
			SYNTAX GponSrvProfilePortVlanTranslationEntry
			MAX-ACCESS not-accessible
			STATUS current
			DESCRIPTION
				"Description."
			INDEX { gponSrvProfilePortVlanTransProfileIndex, gponSrvProfilePortVlanTransPortTypeIndex, gponSrvProfilePortVlanTransPortIdIndex, gponSrvProfilePortVlanTransVlanIndex }
			::= { gponSrvProfilePortVlanTranslationTable 1 }

		
		GponSrvProfilePortVlanTranslationEntry ::=
			SEQUENCE { 
				gponSrvProfilePortVlanTransProfileIndex
					INTEGER,
				gponSrvProfilePortVlanTransPortTypeIndex
					INTEGER,
				gponSrvProfilePortVlanTransPortIdIndex
					INTEGER,
				gponSrvProfilePortVlanTransVlanIndex
					INTEGER,
				gponSrvProfilePortVlanTransNewVlan
					INTEGER,
				gponSrvProfilePortVlanTransRowStatus
					RowStatus
			 }

		-- 1.3.6.1.4.1.17409.2.8.11.3.5.2.1.1
		gponSrvProfilePortVlanTransProfileIndex OBJECT-TYPE
			SYNTAX INTEGER
			MAX-ACCESS not-accessible
			STATUS current
			DESCRIPTION
				"Description."
			::= { gponSrvProfilePortVlanTranslationEntry 1 }

		
		-- 1.3.6.1.4.1.17409.2.8.11.3.5.2.1.2
		gponSrvProfilePortVlanTransPortTypeIndex OBJECT-TYPE
			SYNTAX INTEGER
				{
				eth(0),
				wlan(1),
				catv(2)
				}
			MAX-ACCESS not-accessible
			STATUS current
			DESCRIPTION
				"Description."
			::= { gponSrvProfilePortVlanTranslationEntry 2 }

		
		-- 1.3.6.1.4.1.17409.2.8.11.3.5.2.1.3
		gponSrvProfilePortVlanTransPortIdIndex OBJECT-TYPE
			SYNTAX INTEGER
			MAX-ACCESS not-accessible
			STATUS current
			DESCRIPTION
				"Description."
			::= { gponSrvProfilePortVlanTranslationEntry 3 }

		
		-- 1.3.6.1.4.1.17409.2.8.11.3.5.2.1.4
		gponSrvProfilePortVlanTransVlanIndex OBJECT-TYPE
			SYNTAX INTEGER
			MAX-ACCESS not-accessible
			STATUS current
			DESCRIPTION
				"Description."
			::= { gponSrvProfilePortVlanTranslationEntry 4 }

		
		-- 1.3.6.1.4.1.17409.2.8.11.3.5.2.1.5
		gponSrvProfilePortVlanTransNewVlan OBJECT-TYPE
			SYNTAX INTEGER
			MAX-ACCESS read-create
			STATUS current
			DESCRIPTION
				"Description."
			::= { gponSrvProfilePortVlanTranslationEntry 5 }

		
		-- 1.3.6.1.4.1.17409.2.8.11.3.5.2.1.6
		gponSrvProfilePortVlanTransRowStatus OBJECT-TYPE
			SYNTAX RowStatus
			MAX-ACCESS read-create
			STATUS current
			DESCRIPTION
				"Description."
			::= { gponSrvProfilePortVlanTranslationEntry 6 }

		
		-- 1.3.6.1.4.1.17409.2.8.11.3.5.3
		gponSrvProfilePortVlanAggregationTable OBJECT-TYPE
			SYNTAX SEQUENCE OF GponSrvProfilePortVlanAggregationEntry
			MAX-ACCESS not-accessible
			STATUS current
			DESCRIPTION
				"Description."
			::= { gponSrvProfilePortVlanObjects 3 }

		
		-- 1.3.6.1.4.1.17409.2.8.11.3.5.3.1
		gponSrvProfilePortVlanAggregationEntry OBJECT-TYPE
			SYNTAX GponSrvProfilePortVlanAggregationEntry
			MAX-ACCESS not-accessible
			STATUS current
			DESCRIPTION
				"Description."
			INDEX { gponSrvProfilePortVlanAggrProfileIndex, gponSrvProfilePortVlanAggrPortTypeIndex, gponSrvProfilePortVlanAggrPortIdIndex, gponSrvProfilePortVlanAggrVlanIndex }
			::= { gponSrvProfilePortVlanAggregationTable 1 }

		
		GponSrvProfilePortVlanAggregationEntry ::=
			SEQUENCE { 
				gponSrvProfilePortVlanAggrProfileIndex
					INTEGER,
				gponSrvProfilePortVlanAggrPortTypeIndex
					INTEGER,
				gponSrvProfilePortVlanAggrPortIdIndex
					INTEGER,
				gponSrvProfilePortVlanAggrVlanIndex
					INTEGER,
				gponSrvProfilePortVlanAggrVlanList
					OCTET STRING,
				gponSrvProfilePortVlanAggrRowStatus
					RowStatus
			 }

		-- 1.3.6.1.4.1.17409.2.8.11.3.5.3.1.1
		gponSrvProfilePortVlanAggrProfileIndex OBJECT-TYPE
			SYNTAX INTEGER
			MAX-ACCESS not-accessible
			STATUS current
			DESCRIPTION
				"Description."
			::= { gponSrvProfilePortVlanAggregationEntry 1 }

		
		-- 1.3.6.1.4.1.17409.2.8.11.3.5.3.1.2
		gponSrvProfilePortVlanAggrPortTypeIndex OBJECT-TYPE
			SYNTAX INTEGER
				{
				eth(0),
				wlan(1),
				catv(2)
				}
			MAX-ACCESS not-accessible
			STATUS current
			DESCRIPTION
				"Description."
			::= { gponSrvProfilePortVlanAggregationEntry 2 }

		
		-- 1.3.6.1.4.1.17409.2.8.11.3.5.3.1.3
		gponSrvProfilePortVlanAggrPortIdIndex OBJECT-TYPE
			SYNTAX INTEGER
			MAX-ACCESS not-accessible
			STATUS current
			DESCRIPTION
				"Description."
			::= { gponSrvProfilePortVlanAggregationEntry 3 }

		
		-- 1.3.6.1.4.1.17409.2.8.11.3.5.3.1.4
		gponSrvProfilePortVlanAggrVlanIndex OBJECT-TYPE
			SYNTAX INTEGER
			MAX-ACCESS not-accessible
			STATUS current
			DESCRIPTION
				"Description."
			::= { gponSrvProfilePortVlanAggregationEntry 4 }

		
		-- 1.3.6.1.4.1.17409.2.8.11.3.5.3.1.5
		gponSrvProfilePortVlanAggrVlanList OBJECT-TYPE
			SYNTAX OCTET STRING (SIZE (16))
			MAX-ACCESS read-create
			STATUS current
			DESCRIPTION
				"max num of vlan is 8, two bytes is one vlan."
			::= { gponSrvProfilePortVlanAggregationEntry 5 }

		
		-- 1.3.6.1.4.1.17409.2.8.11.3.5.3.1.6
		gponSrvProfilePortVlanAggrRowStatus OBJECT-TYPE
			SYNTAX RowStatus
			MAX-ACCESS read-create
			STATUS current
			DESCRIPTION
				"Description."
			::= { gponSrvProfilePortVlanAggregationEntry 6 }

		
		-- 1.3.6.1.4.1.17409.2.8.11.3.5.4
		gponSrvProfilePortVlanTrunkTable OBJECT-TYPE
			SYNTAX SEQUENCE OF GponSrvProfilePortVlanTrunkEntry
			MAX-ACCESS not-accessible
			STATUS current
			DESCRIPTION
				"Description."
			::= { gponSrvProfilePortVlanObjects 4 }

		
		-- 1.3.6.1.4.1.17409.2.8.11.3.5.4.1
		gponSrvProfilePortVlanTrunkEntry OBJECT-TYPE
			SYNTAX GponSrvProfilePortVlanTrunkEntry
			MAX-ACCESS not-accessible
			STATUS current
			DESCRIPTION
				"Description."
			INDEX { gponSrvProfilePortVlanTrunkProfileIndex, gponSrvProfilePortVlanTrunkPortTypeIndex, gponSrvProfilePortVlanTrunkPortIdIndex }
			::= { gponSrvProfilePortVlanTrunkTable 1 }

		
		GponSrvProfilePortVlanTrunkEntry ::=
			SEQUENCE { 
				gponSrvProfilePortVlanTrunkProfileIndex
					INTEGER,
				gponSrvProfilePortVlanTrunkPortTypeIndex
					INTEGER,
				gponSrvProfilePortVlanTrunkPortIdIndex
					INTEGER,
				gponSrvProfilePortVlanTrunkVlanList
					OCTET STRING,
				gponSrvProfilePortVlanTrunkRowStatus
					RowStatus
			 }

		-- 1.3.6.1.4.1.17409.2.8.11.3.5.4.1.1
		gponSrvProfilePortVlanTrunkProfileIndex OBJECT-TYPE
			SYNTAX INTEGER
			MAX-ACCESS not-accessible
			STATUS current
			DESCRIPTION
				"Description."
			::= { gponSrvProfilePortVlanTrunkEntry 1 }

		
		-- 1.3.6.1.4.1.17409.2.8.11.3.5.4.1.2
		gponSrvProfilePortVlanTrunkPortTypeIndex OBJECT-TYPE
			SYNTAX INTEGER
				{
				eth(0),
				wlan(1),
				catv(2)
				}
			MAX-ACCESS not-accessible
			STATUS current
			DESCRIPTION
				"Description."
			::= { gponSrvProfilePortVlanTrunkEntry 2 }

		
		-- 1.3.6.1.4.1.17409.2.8.11.3.5.4.1.3
		gponSrvProfilePortVlanTrunkPortIdIndex OBJECT-TYPE
			SYNTAX INTEGER
			MAX-ACCESS not-accessible
			STATUS current
			DESCRIPTION
				"Description."
			::= { gponSrvProfilePortVlanTrunkEntry 3 }

		
		-- 1.3.6.1.4.1.17409.2.8.11.3.5.4.1.4
		gponSrvProfilePortVlanTrunkVlanList OBJECT-TYPE
			SYNTAX OCTET STRING (SIZE (16))
			MAX-ACCESS read-create
			STATUS current
			DESCRIPTION
				"max num of vlan is 8, two bytes is one vlan."
			::= { gponSrvProfilePortVlanTrunkEntry 4 }

		
		-- 1.3.6.1.4.1.17409.2.8.11.3.5.4.1.5
		gponSrvProfilePortVlanTrunkRowStatus OBJECT-TYPE
			SYNTAX RowStatus
			MAX-ACCESS read-create
			STATUS current
			DESCRIPTION
				"Description."
			::= { gponSrvProfilePortVlanTrunkEntry 5 }

		
		-- 1.3.6.1.4.1.17409.2.8.11.4
		gponTrafficProfileObjects OBJECT IDENTIFIER ::= { gponProfileObjects 4 }

		
		-- 1.3.6.1.4.1.17409.2.8.11.4.1
		gponTrafficProfileInfoTable OBJECT-TYPE
			SYNTAX SEQUENCE OF GponTrafficProfileInfoEntry
			MAX-ACCESS not-accessible
			STATUS current
			DESCRIPTION
				"Description."
			::= { gponTrafficProfileObjects 1 }

		
		-- 1.3.6.1.4.1.17409.2.8.11.4.1.1
		gponTrafficProfileInfoEntry OBJECT-TYPE
			SYNTAX GponTrafficProfileInfoEntry
			MAX-ACCESS not-accessible
			STATUS current
			DESCRIPTION
				"cir/pir/cbs/pbs must config at the same time."
			INDEX { gponTrafficProfileId }
			::= { gponTrafficProfileInfoTable 1 }

		
		GponTrafficProfileInfoEntry ::=
			SEQUENCE { 
				gponTrafficProfileId
					INTEGER,
				gponTrafficProfileName
					DisplayString,
				gponTrafficProfileCfgCir
					INTEGER,
				gponTrafficProfileCfgPir
					INTEGER,
				gponTrafficProfileCfgCbs
					INTEGER,
				gponTrafficProfileCfgPbs
					INTEGER,
				gponTrafficProfileCfgPriority
					INTEGER,
				gponTrafficProfileBindNum
					INTEGER,
				gponTrafficProfileRowStatus
					RowStatus
			 }

		-- 1.3.6.1.4.1.17409.2.8.11.4.1.1.1
		gponTrafficProfileId OBJECT-TYPE
			SYNTAX INTEGER
			MAX-ACCESS not-accessible
			STATUS current
			DESCRIPTION
				"Description."
			::= { gponTrafficProfileInfoEntry 1 }

		
		-- 1.3.6.1.4.1.17409.2.8.11.4.1.1.2
		gponTrafficProfileName OBJECT-TYPE
			SYNTAX DisplayString
			MAX-ACCESS read-write
			STATUS current
			DESCRIPTION
				"Description."
			::= { gponTrafficProfileInfoEntry 2 }

		
		-- 1.3.6.1.4.1.17409.2.8.11.4.1.1.3
		gponTrafficProfileCfgCir OBJECT-TYPE
			SYNTAX INTEGER
			UNITS "kbit/s"
			MAX-ACCESS read-write
			STATUS current
			DESCRIPTION
				"Description."
			::= { gponTrafficProfileInfoEntry 3 }

		
		-- 1.3.6.1.4.1.17409.2.8.11.4.1.1.4
		gponTrafficProfileCfgPir OBJECT-TYPE
			SYNTAX INTEGER
			UNITS "kbit/s"
			MAX-ACCESS read-write
			STATUS current
			DESCRIPTION
				"Description."
			::= { gponTrafficProfileInfoEntry 4 }

		
		-- 1.3.6.1.4.1.17409.2.8.11.4.1.1.5
		gponTrafficProfileCfgCbs OBJECT-TYPE
			SYNTAX INTEGER
			UNITS "byte"
			MAX-ACCESS read-write
			STATUS current
			DESCRIPTION
				"Description."
			::= { gponTrafficProfileInfoEntry 5 }

		
		-- 1.3.6.1.4.1.17409.2.8.11.4.1.1.6
		gponTrafficProfileCfgPbs OBJECT-TYPE
			SYNTAX INTEGER
			UNITS "byte"
			MAX-ACCESS read-write
			STATUS current
			DESCRIPTION
				"Description."
			::= { gponTrafficProfileInfoEntry 6 }

		
		-- 1.3.6.1.4.1.17409.2.8.11.4.1.1.7
		gponTrafficProfileCfgPriority OBJECT-TYPE
			SYNTAX INTEGER (0..7)
			MAX-ACCESS read-write
			STATUS current
			DESCRIPTION
				"Description."
			::= { gponTrafficProfileInfoEntry 7 }

		
		-- 1.3.6.1.4.1.17409.2.8.11.4.1.1.8
		gponTrafficProfileBindNum OBJECT-TYPE
			SYNTAX INTEGER
			MAX-ACCESS read-only
			STATUS current
			DESCRIPTION
				"Description."
			::= { gponTrafficProfileInfoEntry 8 }

		
		-- 1.3.6.1.4.1.17409.2.8.11.4.1.1.9
		gponTrafficProfileRowStatus OBJECT-TYPE
			SYNTAX RowStatus
			MAX-ACCESS read-create
			STATUS current
			DESCRIPTION
				"Description."
			::= { gponTrafficProfileInfoEntry 9 }

	END

--
-- NSCRTV-EPONEOC-GPON-PROFILE-MIB.my
--
