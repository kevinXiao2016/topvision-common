--
-- NSCRTV-EPONEOC-GPON-PERF-GEM-MIB.mib
-- MIB generated by MG-SOFT Visual MIB Builder Version 4.0 Build 349
-- Friday, September 30, 2016 at 09:45:40
--

	NSCRTV-EPONEOC-GPON-PERF-GEM-MIB DEFINITIONS ::= BEGIN
 
		IMPORTS
			BridgeId, Timeout			
				FROM BRIDGE-MIB			
			enterprises, TimeTicks, IpAddress, Unsigned32, Gauge32, 
			Counter32, Counter64, OBJECT-TYPE, OBJECT-IDENTITY, 
			NOTIFICATION-TYPE			
				FROM SNMPv2-SMI			
			DateAndTime, TruthValue, RowStatus, MacAddress, DisplayString, 
			TimeStamp, TEXTUAL-CONVENTION			
				FROM SNMPv2-TC;

--
-- Textual conventions
--
		GponCardIndex ::= TEXTUAL-CONVENTION
			STATUS current
			DESCRIPTION 
				"     
				For easy presenting the chassis view by NMS, bCardIndex shall be formatted
				in a following manner:                        
				    Four bytes of INTEGER, from the most significant byte to the least significant
				    bytes
				        -----------------------------------------------------------------------------
				Reserved byte Reserved byte   Reserved byte Sub-slot 2-bit Main-slot 6-bit        
				Notes:
				-----         
				1. Reserved bytes shall be set to 0.        
				2. The main-slot shall be started from 1, and shall be in a consecutive manner,
				   for all slots, including service slots, control slots, switch slots, power
				slots,FAN slots, etc.For example, 1, 2, 3          
				3. The sub-slot shall be started from 1, and shall be in a consecutive manner.
				   For example, 1, 2. If no sub-slot concept of a main-slot, set to 0.        
				4. For fixed device, if no slot concept, NE shall set both main-slot and sub-slot
				to 0, to indicate this is meaningless. For modulized device, they MUST not be
				set to 0.This definition shall applied to both OLT and ONU.        
				5. For trunk, since there is no slot concept, set main-slot to all-1 and sub-slot
				to 0. This definition shall applied to both OLT and ONU.
				
				For example, 
				0x00 00 00 0A, represents main-slot 10, no sub-slot
				0x00 00 00 42, represents main-slot 2, sub-slot 1
				0x00 00 00 3F, represents a trunk
				"
			SYNTAX Unsigned32

		GponPortIndex ::= TEXTUAL-CONVENTION
			STATUS current
			DESCRIPTION 
				"       
				The device port number shall start from 1. Nunber 0 had specific meaning, stands
				for portIndex is meaningless, for the situation defined.
				"
			SYNTAX INTEGER (0..255)

		GponDeviceIndex ::= TEXTUAL-CONVENTION
			STATUS current
			DESCRIPTION 
				"
				Gpon olt/onu
				ONU ID       
				Olt device-8bit OLT Card-8bit Pon port-8bit OnuNUM-8bit        
				Note: 
				----        
				1. OLT device must not be 0.        
				2. Card here shall confirm the last byte definition of GponCardIndex
				   to indicate the main-slot and sub-slot index.         
				3. Pon port must not be 0.
				4. The useful ONU logical ID MUST never be set to 0, where NUM of 0 has
				   another meaning, to indicate that the ONU logical ID is meaningless,
				   or said to not applied.
				        
				Usage guide:
				-----------        
				This TC could be used for OLT SNI, OLT PON port, OLT ONU ID
				ONU UNI, OLT device, trunk.         
				If the refered MIB object does not have clear definition,
				refer to the following:
				Applied Obj  - Descriptions of Index
				------------------------------------------------------------------
				OLT Pon Port - OnuNum shall be set to 0,
				OLT SNI    - Same as OLT Pon Port         
				OLT onu ID   - Set OnuNUM to corresponding ONU logical ID         
				ONU UNI    - Same as OLT ONU ID
				OLT device   - Set card, pon port and OnuNUM to 0
				Trunk    - Card to 0x3F, pon port to trunk ID, OnuNUM to 0
				         Olt device to corresponding ONU device       
				"
			SYNTAX Unsigned32


		GponStats15MinRecordType ::= TEXTUAL-CONVENTION
			STATUS current
			DESCRIPTION 
				" "
			SYNTAX INTEGER (0..96)

		GponStats24HourRecordType ::= TEXTUAL-CONVENTION
			STATUS current
			DESCRIPTION 
				" "
			SYNTAX INTEGER (0..30)


--
-- Node definitions
--
	
		-- 1.3.6.1.4.1.17409
		nscrtvRoot OBJECT IDENTIFIER ::= { enterprises 17409 }

		
		-- 1.3.6.1.4.1.17409.2
		nscrtvFTTxTree OBJECT IDENTIFIER ::= { nscrtvRoot 2 }

		
--      DESCRIPTION
		-- 1.3.6.1.4.1.17409.2.8
		gponTree OBJECT IDENTIFIER ::= { nscrtvFTTxTree 8 }
		

			
-- ------------------------------------------------------------------------------
-- performanceStatisticObjects(1.3.6.1.4.1.17409.2.8.10)
-- ------------------------------------------------------------------------------ 
-- 1.3.6.1.4.1.17409.2.8.10
		performanceStatisticObjects OBJECT IDENTIFIER ::= { gponTree 10 }

		-- 1.3.6.1.4.1.17409.2.8.10.6
		curStatsGemPortTable OBJECT-TYPE
			SYNTAX SEQUENCE OF CurStatsGemPortEntry
			MAX-ACCESS not-accessible
			STATUS current
			DESCRIPTION
				"Description."
			::= { performanceStatisticObjects 6 }


		-- 1.3.6.1.4.1.17409.2.8.10.6.1
		curStatsGemPortEntry OBJECT-TYPE
			SYNTAX CurStatsGemPortEntry
			MAX-ACCESS not-accessible
			STATUS current
			DESCRIPTION
				"Description."
			INDEX { curStatsGemPortDeviceIndex, curStatsGemPortIndex }
			::= { curStatsGemPortTable 1 }

		
		CurStatsGemPortEntry ::=
			SEQUENCE { 
				curStatsGemPortDeviceIndex
					GponDeviceIndex,
				curStatsGemPortIndex
					INTEGER,
				curStatsGemPortOutGemFrames
					Counter64,
				curStatsGemPortInGemFrames
					Counter64,
				curStatsGemPortOutBytes
					Counter64,
				curStatsGemPortInBytes
					Counter64,
				curStatsGemPortStatusAndAction
					INTEGER
			 }

		-- 1.3.6.1.4.1.17409.2.8.10.6.1.1
		curStatsGemPortDeviceIndex OBJECT-TYPE
			SYNTAX GponDeviceIndex
			MAX-ACCESS not-accessible
			STATUS current
			DESCRIPTION
				"Description."
			::= { curStatsGemPortEntry 1 }

		
		-- 1.3.6.1.4.1.17409.2.8.10.6.1.2
		curStatsGemPortIndex OBJECT-TYPE
			SYNTAX INTEGER
			MAX-ACCESS not-accessible
			STATUS current
			DESCRIPTION
				"Description."
			::= { curStatsGemPortEntry 2 }

		
		-- 1.3.6.1.4.1.17409.2.8.10.6.1.3
		curStatsGemPortOutGemFrames OBJECT-TYPE
			SYNTAX Counter64
			MAX-ACCESS read-only
			STATUS current
			DESCRIPTION
				"Description."
			::= { curStatsGemPortEntry 3 }

		
		-- 1.3.6.1.4.1.17409.2.8.10.6.1.4
		curStatsGemPortInGemFrames OBJECT-TYPE
			SYNTAX Counter64
			MAX-ACCESS read-only
			STATUS current
			DESCRIPTION
				"Description."
			::= { curStatsGemPortEntry 4 }

		
		-- 1.3.6.1.4.1.17409.2.8.10.6.1.5
		curStatsGemPortOutBytes OBJECT-TYPE
			SYNTAX Counter64
			MAX-ACCESS read-only
			STATUS current
			DESCRIPTION
				"Description."
			::= { curStatsGemPortEntry 5 }

		
		-- 1.3.6.1.4.1.17409.2.8.10.6.1.6
		curStatsGemPortInBytes OBJECT-TYPE
			SYNTAX Counter64
			MAX-ACCESS read-only
			STATUS current
			DESCRIPTION
				"Description."
			::= { curStatsGemPortEntry 6 }

		
		-- 1.3.6.1.4.1.17409.2.8.10.6.1.7
		curStatsGemPortStatusAndAction OBJECT-TYPE
			SYNTAX INTEGER
				{
				none(1),
				cleandata(2)
				}
			MAX-ACCESS read-write
			STATUS current
			DESCRIPTION
				"Description."
			::= { curStatsGemPortEntry 7 }

		
		-- 1.3.6.1.4.1.17409.2.8.10.7
		stats15GemPortTable OBJECT-TYPE
			SYNTAX SEQUENCE OF Stats15GemPortEntry
			MAX-ACCESS not-accessible
			STATUS current
			DESCRIPTION
				"Description."
			::= { performanceStatisticObjects 7 }

		
		-- 1.3.6.1.4.1.17409.2.8.10.7.1
		stats15GemPortEntry OBJECT-TYPE
			SYNTAX Stats15GemPortEntry
			MAX-ACCESS not-accessible
			STATUS current
			DESCRIPTION
				"Description."
			INDEX { stats15GemPortDeviceIndex, stats15GemPortIndex, stats15GemPortStatIndex }
			::= { stats15GemPortTable 1 }

		
		Stats15GemPortEntry ::=
			SEQUENCE { 
				stats15GemPortDeviceIndex
					GponDeviceIndex,
				stats15GemPortIndex
					INTEGER,
				stats15GemPortStatIndex
					GponStats15MinRecordType,
				stats15GemPortOutGemFrames
					Counter64,
				stats15GemPortInGemFrames
					Counter64,
				stats15GemPortOutBytes
					Counter64,
				stats15GemPortInBytes
					Counter64,
				stats15GemPortStatusAndAction
					INTEGER,
				stats15GemPortValidityTag
					TruthValue,
				stats15GemPortElapsedTime
					Counter32,
				stats15GemPortEndTime
					DateAndTime
			 }

		-- 1.3.6.1.4.1.17409.2.8.10.7.1.1
		stats15GemPortDeviceIndex OBJECT-TYPE
			SYNTAX GponDeviceIndex
			MAX-ACCESS not-accessible
			STATUS current
			DESCRIPTION
				"Description."
			::= { stats15GemPortEntry 1 }

		
		-- 1.3.6.1.4.1.17409.2.8.10.7.1.2
		stats15GemPortIndex OBJECT-TYPE
			SYNTAX INTEGER
			MAX-ACCESS not-accessible
			STATUS current
			DESCRIPTION
				"Description."
			::= { stats15GemPortEntry 2 }

		
		-- 1.3.6.1.4.1.17409.2.8.10.7.1.3
		stats15GemPortStatIndex OBJECT-TYPE
			SYNTAX GponStats15MinRecordType
			MAX-ACCESS not-accessible
			STATUS current
			DESCRIPTION
				"Description."
			::= { stats15GemPortEntry 3 }

		
		-- 1.3.6.1.4.1.17409.2.8.10.7.1.4
		stats15GemPortOutGemFrames OBJECT-TYPE
			SYNTAX Counter64
			MAX-ACCESS read-only
			STATUS current
			DESCRIPTION
				"Description."
			::= { stats15GemPortEntry 4 }

		
		-- 1.3.6.1.4.1.17409.2.8.10.7.1.5
		stats15GemPortInGemFrames OBJECT-TYPE
			SYNTAX Counter64
			MAX-ACCESS read-only
			STATUS current
			DESCRIPTION
				"Description."
			::= { stats15GemPortEntry 5 }

		
		-- 1.3.6.1.4.1.17409.2.8.10.7.1.6
		stats15GemPortOutBytes OBJECT-TYPE
			SYNTAX Counter64
			MAX-ACCESS read-only
			STATUS current
			DESCRIPTION
				"Description."
			::= { stats15GemPortEntry 6 }

		
		-- 1.3.6.1.4.1.17409.2.8.10.7.1.7
		stats15GemPortInBytes OBJECT-TYPE
			SYNTAX Counter64
			MAX-ACCESS read-only
			STATUS current
			DESCRIPTION
				"Description."
			::= { stats15GemPortEntry 7 }

		
		-- 1.3.6.1.4.1.17409.2.8.10.7.1.8
		stats15GemPortStatusAndAction OBJECT-TYPE
			SYNTAX INTEGER
				{
				none(1),
				cleandata(2)
				}
			MAX-ACCESS read-write
			STATUS current
			DESCRIPTION
				"Description."
			::= { stats15GemPortEntry 8 }

		
		-- 1.3.6.1.4.1.17409.2.8.10.7.1.9
		stats15GemPortValidityTag OBJECT-TYPE
			SYNTAX TruthValue
			MAX-ACCESS read-only
			STATUS current
			DESCRIPTION
				"Description."
			::= { stats15GemPortEntry 9 }

		
		-- 1.3.6.1.4.1.17409.2.8.10.7.1.10
		stats15GemPortElapsedTime OBJECT-TYPE
			SYNTAX Counter32
			UNITS "seconds"
			MAX-ACCESS read-only
			STATUS current
			DESCRIPTION
				"Description."
			::= { stats15GemPortEntry 10 }

		
		-- 1.3.6.1.4.1.17409.2.8.10.7.1.11
		stats15GemPortEndTime OBJECT-TYPE
			SYNTAX DateAndTime
			MAX-ACCESS read-only
			STATUS current
			DESCRIPTION
				"Description."
			::= { stats15GemPortEntry 11 }

		
		-- 1.3.6.1.4.1.17409.2.8.10.8
		stats24GemPortTable OBJECT-TYPE
			SYNTAX SEQUENCE OF Stats24GemPortEntry
			MAX-ACCESS not-accessible
			STATUS current
			DESCRIPTION
				"Description."
			::= { performanceStatisticObjects 8 }

		
		-- 1.3.6.1.4.1.17409.2.8.10.8.1
		stats24GemPortEntry OBJECT-TYPE
			SYNTAX Stats24GemPortEntry
			MAX-ACCESS not-accessible
			STATUS current
			DESCRIPTION
				"Description."
			INDEX { stats24GemPortDeviceIndex, stats24GemPortIndex, stats24GemPortStatIndex }
			::= { stats24GemPortTable 1 }

		
		Stats24GemPortEntry ::=
			SEQUENCE { 
				stats24GemPortDeviceIndex
					GponDeviceIndex,
				stats24GemPortIndex
					INTEGER,
				stats24GemPortStatIndex
					GponStats24HourRecordType,
				stats24GemPortOutGemFrames
					Counter64,
				stats24GemPortInGemFrames
					Counter64,
				stats24GemPortOutBytes
					Counter64,
				stats24GemPortInBytes
					Counter64,
				stats24GemPortStatusAndAction
					INTEGER,
				stats24GemPortValidityTag
					TruthValue,
				stats24GemPortElapsedTime
					Counter32,
				stats24GemPortEndTime
					DateAndTime
			 }

		-- 1.3.6.1.4.1.17409.2.8.10.8.1.1
		stats24GemPortDeviceIndex OBJECT-TYPE
			SYNTAX GponDeviceIndex
			MAX-ACCESS not-accessible
			STATUS current
			DESCRIPTION
				"Description."
			::= { stats24GemPortEntry 1 }

		
		-- 1.3.6.1.4.1.17409.2.8.10.8.1.2
		stats24GemPortIndex OBJECT-TYPE
			SYNTAX INTEGER
			MAX-ACCESS not-accessible
			STATUS current
			DESCRIPTION
				"Description."
			::= { stats24GemPortEntry 2 }

		
		-- 1.3.6.1.4.1.17409.2.8.10.8.1.3
		stats24GemPortStatIndex OBJECT-TYPE
			SYNTAX GponStats24HourRecordType
			MAX-ACCESS not-accessible
			STATUS current
			DESCRIPTION
				"Description."
			::= { stats24GemPortEntry 3 }

		
		-- 1.3.6.1.4.1.17409.2.8.10.8.1.4
		stats24GemPortOutGemFrames OBJECT-TYPE
			SYNTAX Counter64
			MAX-ACCESS read-only
			STATUS current
			DESCRIPTION
				"Description."
			::= { stats24GemPortEntry 4 }

		
		-- 1.3.6.1.4.1.17409.2.8.10.8.1.5
		stats24GemPortInGemFrames OBJECT-TYPE
			SYNTAX Counter64
			MAX-ACCESS read-only
			STATUS current
			DESCRIPTION
				"Description."
			::= { stats24GemPortEntry 5 }

		
		-- 1.3.6.1.4.1.17409.2.8.10.8.1.6
		stats24GemPortOutBytes OBJECT-TYPE
			SYNTAX Counter64
			MAX-ACCESS read-only
			STATUS current
			DESCRIPTION
				"Description."
			::= { stats24GemPortEntry 6 }

		
		-- 1.3.6.1.4.1.17409.2.8.10.8.1.7
		stats24GemPortInBytes OBJECT-TYPE
			SYNTAX Counter64
			MAX-ACCESS read-only
			STATUS current
			DESCRIPTION
				"Description."
			::= { stats24GemPortEntry 7 }

		
		-- 1.3.6.1.4.1.17409.2.8.10.8.1.8
		stats24GemPortStatusAndAction OBJECT-TYPE
			SYNTAX INTEGER
				{
				none(1),
				cleandata(2)
				}
			MAX-ACCESS read-write
			STATUS current
			DESCRIPTION
				"Description."
			::= { stats24GemPortEntry 8 }

		
		-- 1.3.6.1.4.1.17409.2.8.10.8.1.9
		stats24GemPortValidityTag OBJECT-TYPE
			SYNTAX TruthValue
			MAX-ACCESS read-only
			STATUS current
			DESCRIPTION
				"Description."
			::= { stats24GemPortEntry 9 }

		
		-- 1.3.6.1.4.1.17409.2.8.10.8.1.10
		stats24GemPortElapsedTime OBJECT-TYPE
			SYNTAX Counter32
			UNITS "seconds"
			MAX-ACCESS read-only
			STATUS current
			DESCRIPTION
				"Description."
			::= { stats24GemPortEntry 10 }

		
		-- 1.3.6.1.4.1.17409.2.8.10.8.1.11
		stats24GemPortEndTime OBJECT-TYPE
			SYNTAX DateAndTime
			MAX-ACCESS read-only
			STATUS current
			DESCRIPTION
				"Description."
			::= { stats24GemPortEntry 11 }

	
	END

--
-- NSCRTV-EPONEOC-GPON-PERF-GEM-MIB.my
--
