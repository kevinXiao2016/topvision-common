---EPON MIB 版本2016-10-28

NSCRTV-FTTX-EPON-MIB DEFINITIONS ::= BEGIN
    IMPORTS
        BridgeId, Timeout     
      FROM BRIDGE-MIB       
        IpAddress, Unsigned32, Integer32, Counter32,OBJECT-TYPE, TimeTicks, Gauge32, Counter64,
    MODULE-IDENTITY, OBJECT-IDENTITY, enterprises     
      FROM SNMPv2-SMI     
    DateAndTime, MacAddress, TimeStamp, RowStatus, TruthValue, DisplayString, TEXTUAL-CONVENTION
      FROM SNMPv2-TC;


nscrtvRoot  OBJECT IDENTIFIER ::= { enterprises 17409 }

-- DESCRIPTION
--     "nscrtvRoot定义全国广电设备管理MIB根节点。"

nscrtvHFCemsTree  OBJECT IDENTIFIER  ::= { nscrtvRoot 1 }
nscrtvFTTxTree  OBJECT IDENTIFIER  ::= { nscrtvRoot 2}
-- DESCRIPTION
--     "nscrtvFTTxTree定义EPON、EOC等设备管理系统的MIB根节点,"
--     "所有FTTx综合网络设备管理系统的MIB均应在该节点下定义"

propertyIdent  OBJECT IDENTIFIER  ::= { nscrtvFTTxTree 1}
--     DESCRIPTION
--     "属性(Property)MIB的分支节点标识。"

alarmsIdent   OBJECT IDENTIFIER ::= { nscrtvFTTxTree 2}

--     DESCRIPTION
--     "告警(Alarms)MIB的分支节点标识。"

eponTree   OBJECT IDENTIFIER ::= { nscrtvFTTxTree 3}

--     DESCRIPTION
--     "EPON MIB的分支节点标识。"

eoCTree   OBJECT IDENTIFIER ::= { nscrtvFTTxTree 4}

--     DESCRIPTION
--     "EoC MIB的分支节点标识。"


    eponAlarmTree OBJECT IDENTIFIER ::= { alarmsIdent 11 }

      eponTrapObjectGroup OBJECT IDENTIFIER ::= { eponAlarmTree 1 }

      eponAlarmObjGroup OBJECT IDENTIFIER ::= { eponAlarmTree 2 }

      eponManagementObjGroup OBJECT IDENTIFIER ::= { eponAlarmTree 3 }


      systemObjects OBJECT IDENTIFIER ::= { eponTree 1 }

      sniObjects OBJECT IDENTIFIER ::= { eponTree 2 }

      ponPortObjects OBJECT IDENTIFIER ::= { eponTree 3 }

      onuObjects OBJECT IDENTIFIER ::= { eponTree 4 }

      uniObjects OBJECT IDENTIFIER ::= { eponTree 5 }

      igmpManagementObjects OBJECT IDENTIFIER ::= { eponTree 6 }

      vlanManagementObjects OBJECT IDENTIFIER ::= { eponTree 7 }

      qosManagementObjects OBJECT IDENTIFIER ::= { eponTree 8 }

      stpManagementObjects OBJECT IDENTIFIER ::= { eponTree 9 }

      performanceStatisticObjects OBJECT IDENTIFIER ::= { eponTree 10 }


    EponDeviceIndex ::= TEXTUAL-CONVENTION
      STATUS current
      DESCRIPTION 
        "
        Epon olt/onu设备索引号。       
        ONU ID的组成(4字节)(高--低)          
        Olt device-8bit OLT Card-8bit Pon port-8bit OnuNUM-8bit        
        Note: 
        ----        
        1. OLT device must not be 0.        
        2. Card here shall confirm the last byte definition of EponCardIndex
           to indicate the main-slot and sub-slot index.         
        3. Pon port must not be 0.
        4. The useful ONU logical ID MUST never be set to 0, where NUM of 0 has
           another meaning, to indicate that the ONU logical ID is meaningless,
           or said to not applied.
                
        Usage guide:
        -----------        
        This TC could be used for OLT SNI, OLT PON port, OLT ONU ID
        OLT device, trunk.         
        If the refered MIB object does not have clear definition,
        refer to the following:
        Applied Obj  - Descriptions of Index
        ------------------------------------------------------------------
        OLT Pon Port - OnuNum shall be set to 0,
        OLT SNI    - Same as OLT Pon Port         
        OLT onu ID   - Set OnuNUM to corresponding ONU logical ID         
        OLT device   - Set card, pon port and OnuNUM to 0
        Trunk    - Card to 0x3F, pon port to trunk ID, OnuNUM to 0
                 Olt device to corresponding ONU device       
        "
      SYNTAX Unsigned32
  
    EponCardIndex ::= TEXTUAL-CONVENTION
      STATUS current
      DESCRIPTION 
        "
        板卡索引号        
        For easy presenting the chassis view by NMS, bCardIndex shall be formatted
        in a following manner:                        
            Four bytes of INTEGER, from the most significant byte to the least significant
            bytes
                -----------------------------------------------------------------------------
        Reserved byte Reserved byte   Reserved byte Sub-slot 2-bit Main-slot 6-bit        
        Notes:
        -----         
        1. Reserved bytes shall be set to 0.        
        2. The main-slot shall be started from 1, and shall be in a consecutive manner,
           for all slots, including service slots, control slots, switch slots, power
 slots,FAN slots, etc.For example, 1, 2, 3          
        3. The sub-slot shall be started from 1, and shall be in a consecutive manner.
           For example, 1, 2. If no sub-slot concept of a main-slot, set to 0.        
4. For fixed device, if no slot concept, NE shall set both main-slot and sub-slot
   to 0, to indicate this is meaningless. For modulized device, they MUST not be
 set to 0.This definition shall applied to both OLT and ONU.        
5. For trunk, since there is no slot concept, set main-slot to all-1 and sub-slot
 to 0. This definition shall applied to both OLT and ONU.
        
        For example, 
        0x00 00 00 0A, represents main-slot 10, no sub-slot
        0x00 00 00 42, represents main-slot 2, sub-slot 1
        0x00 00 00 3F, represents a trunk
        "
      SYNTAX Unsigned32
      
    EponPortIndex ::= TEXTUAL-CONVENTION
      STATUS current
      DESCRIPTION 
        "
        Epon端口索引号        
        The device port number shall start from 1. Nunber 0 had specific meaning, stands
        for portIndex is meaningless, for the situation defined.
        "
      SYNTAX INTEGER (0..255)

    EponAlarmCode ::= TEXTUAL-CONVENTION
      STATUS current
      DESCRIPTION 
        "Alarm codes, uniquely indentifies each kind of alarm.
        Refer to EPON alarm definition table"
      SYNTAX INTEGER (1..65535)

    EponAlarmInstance ::= TEXTUAL-CONVENTION
      STATUS current
      DESCRIPTION 
        "
        Alarm instance, which define the detailed management object
        reported the alarm. For example, OLT device 1, slot 2, port 3
        reports a port down alarm.
        It is represents in OCTET STRING format.
        1. The first four OCTET has same definition as EponDeviceIndex TC.
        2. The fifth OCTET is the slot definition of ONU, which shall 
           have same definition as last byte definition in EponCardIndex
           TC.
        3. The sixth OCTET is the UNI port ID of ONU, which is similar to
           EponPortIndex TC.
        4. The seventh and eighth OCTETS are reserved and shall be set to 
           0 at any time, and shall be ignored by maangement system.        
        For example,        
        0x01 02 03 04 05 06 00 00, represents OLT device 1, slot 2, port 3, 
        ONU logical ID 4, slot 5 UNI port 6 of the connected ONU.        
        "
      SYNTAX OCTET STRING ( SIZE (8) )

    EponSeverityType ::= TEXTUAL-CONVENTION
      STATUS current
      DESCRIPTION 
        "
        告警严重程度"
      SYNTAX INTEGER
        {
        critical(1),
        major(2),
        minor(3),
        warning(4),
        info(5),
        clear(6)
        }

    AutoNegotiationTechAbility ::= TEXTUAL-CONVENTION
      STATUS current
      DESCRIPTION 
        "Technology ability of auto negotiation. Refer to 
        clause 30.6.1.1.5 of IEEE 802.3 2005 edition"
      SYNTAX BITS
        {
        tenBaseTFullDuplex(1),
        tenBaseTHalfDuplex(2),
        hundredBaseTFullDuplex(3),
        hundredBaseTHalfDuplex(4),
        thousandBaseTFullDuplex(5),
        thousandBaseTHalfDuplex(6),
        thousandBaseXFullDuplex(7),
        thousandBaseXHalfDuplex(8),          
        fdxPause(9),
        fdxApause(10),
        fdxSpause(11),
        fdxBpause(12)
        }

    TAddress ::= TEXTUAL-CONVENTION
      STATUS current
      DESCRIPTION 
        "
        First four octets sames definition of IpAddress, stands for NMS IP address
        The last four octets same definition of INTEGER, stands for trap UDP port "
      SYNTAX OCTET STRING (SIZE (8))

    EponStats15MinRecordType ::= TEXTUAL-CONVENTION
      STATUS current
      DESCRIPTION 
        "15分钟性能统计记录的索引号
        索引号为0表示当前15分钟性能数据
        1..96表示历史的15分钟性能,1代表最新的数据,96代表最老的数据"
      SYNTAX INTEGER (0..96)

    EponStats24HourRecordType ::= TEXTUAL-CONVENTION
      STATUS current
      DESCRIPTION 
        "24小时性能统计记录的索引号
        索引号为0表示当前24小时性能数据
        1..30表示历史的24小时性能, 1代表最新的数据,30代表最老的数据"
      SYNTAX INTEGER (0..30)

    EponStatsThresholdType ::= TEXTUAL-CONVENTION
      STATUS current
      DESCRIPTION 
        "门限类型,见 性能量定义表
        1-  InOctets                 
        2 InPkts                   
        3 InBroadcastPkts          
        4 InMulticastPkts          
        5 InPkts64Octets           
        6 InPkts65to127Octets      
        7 InPkts128to255Octets     
        8 InPkts256to511Octets     
        9 InPkts512to1023Octets    
        10  InPkts1024to1518Octets 
        11  InPkts1519to1522Octets 
        12  InUndersizePkts        
        13  InOversizePkts         
        14  InFragments            
        15  InMpcpFrames           
        16  InMpcpOctets           
        17  InOAMFrames            
        18  InOAMOctets            
        19  InCRCErrorPkts         
        20  InDropEvents           
        21  InJabbers              
        22  InCollision            
        23  OutOctets              
        24  OutPkts                
        25  OutBroadcastPkts       
        26  OutMulticastPkts       
        27  OutPkts64Octets        
        28  OutPkts65to127Octets   
        29  OutPkts128to255Octets  
        30  OutPkts256to511Octets  
        31  OutPkts512to1023Octets 
        32  OutPkts1024to1518Octets
        33  OutPkts1519o1522Octets 
        34  OutUndersizePkts       
        35  OutOversizePkts        
        36  OutFragments           
        37  OutMpcpFrames          
        38  OutMpcpOctets          
        39  OutOAMFrames           
        40  OutOAMOctets           
        41  OutCRCErrorPkts        
        42  OutDropEvents          
        43  OutJabbers             
        44  OutCollision

        50  Temperature
        51  Voltage
52  TXPower
53  RXPower

        
        Note:
        ----------------------------------------------------------------
        1. For 50 Temperature, this parameter shall only applied to
           a. Slot level, for each service/switch/management card, for
              chassis-based system.
           b. Node-level, for fixed box.
        2. For 50 Temperature, shall be applied to both OLT and ONU
        3. For 50 Temperature, since no 15-min performance data collection
           are required, system shall ensure the temperature polling interval
           no less than 5 seconds. The alarm shall be only generated when the
           threshold is acrossed for three continuous intervals, and shall be 
           cleared, when the threshold is not accrossed any more, for three 
           continous intervals.
        "
      SYNTAX INTEGER (1..1024)


--------------------------------------------------------------------------------
--  systemObjects [系统属性参数管理项](1.3.6.1.4.1.17409.2.3.1)
--------------------------------------------------------------------------------       
    systemGlobalObjects OBJECT-IDENTITY
      STATUS current
      DESCRIPTION 
        "全局参数表"
      ::= { systemObjects 1 }
                            
    systemTime OBJECT-TYPE
      SYNTAX DateAndTime
      MAX-ACCESS read-write
      STATUS current
      DESCRIPTION
        "
        节点系统时间, 8字节的十六进制或11字节的十六进制
        建议采用8字节定义,不包括时区"
      ::= { systemGlobalObjects 1 }
    
    inbandIpAddress OBJECT-TYPE
      SYNTAX IpAddress
      MAX-ACCESS read-only
      STATUS current
      DESCRIPTION
        "
        带内管理接口IP地址"
      ::= { systemGlobalObjects 2 }
    
    inbandIpSubnetMask OBJECT-TYPE
      SYNTAX IpAddress
      MAX-ACCESS read-only
      STATUS current
      DESCRIPTION
        "
        带内管理接口IP掩码"
      ::= { systemGlobalObjects 3 }
    
    inbandIpGateway OBJECT-TYPE
      SYNTAX IpAddress
      MAX-ACCESS read-only
      STATUS current
      DESCRIPTION
        "
        带内管理接口网关IP地址"
      ::= { systemGlobalObjects 4 }
    
    inbandVlanId OBJECT-TYPE
      SYNTAX INTEGER
      MAX-ACCESS read-write
      STATUS current
      DESCRIPTION
        "
        带内管理接口VLAN ID.
        
        带内管理VLAN的成员关系由VLAN表定义"
      ::= { systemGlobalObjects 5 }
    
    inbandMacAddress OBJECT-TYPE
      SYNTAX MacAddress
      MAX-ACCESS read-only
      STATUS current
      DESCRIPTION
        "
        带内管理接口MAC地址."
      ::= { systemGlobalObjects 6 }
    
    outbandIpAddress OBJECT-TYPE
      SYNTAX IpAddress
      MAX-ACCESS read-only
      STATUS current
      DESCRIPTION
        "
        带外管理接口IP地址"
      ::= { systemGlobalObjects 7 }
    
    outbandIpSubnetMask OBJECT-TYPE
      SYNTAX IpAddress
      MAX-ACCESS read-only
      STATUS current
      DESCRIPTION
        "
        带外管理接口IP掩码"
      ::= { systemGlobalObjects 8 }
    
    outbandIpGateway OBJECT-TYPE
      SYNTAX IpAddress
      MAX-ACCESS read-only
      STATUS current
      DESCRIPTION
        "
        带外管理接口网关IP地址"
      ::= { systemGlobalObjects 9 }
    
    outbandMacAddress OBJECT-TYPE
      SYNTAX MacAddress
      MAX-ACCESS read-only
      STATUS current
      DESCRIPTION
        "
        带外管理接口MAC地址"
      ::= { systemGlobalObjects 10 }
    
    systemOUI OBJECT-TYPE
      SYNTAX OCTET STRING (SIZE (3))
      MAX-ACCESS read-only
      STATUS current
      DESCRIPTION
        "
        系统OUI"
      ::= { systemGlobalObjects 11 }

    vendorName OBJECT-TYPE
      SYNTAX DisplayString
      MAX-ACCESS read-only
      STATUS current
      DESCRIPTION
        "
        Vender name of the OLT equipment"
      ::= { systemGlobalObjects 12 }
    
devSn OBJECT-TYPE
SYNTAX DisplayString
MAX-ACCESS read-only
STATUS current
DESCRIPTION
"
Serial number of the OLT equipment"
::= { systemGlobalObjects 13 }


saveConfig OBJECT-TYPE
SYNTAX INTEGER
MAX-ACCESS read-write
STATUS current
DESCRIPTION
"
Save device configuration when set value to 1."
::= { systemGlobalObjects 14 }

saveConfigStatus OBJECT-TYPE
SYNTAX INTEGER{
fail(0),
success(1),
inProcess(2)
}
MAX-ACCESS read-only
STATUS current
DESCRIPTION
"
Save device configuration status "
::= { systemGlobalObjects 15 }



    oltObjects OBJECT-IDENTITY
      STATUS current
      DESCRIPTION 
        "
        OLT管理项节点"
      ::= { systemObjects 2 }
    
    oltPropertyTable OBJECT-TYPE
      SYNTAX SEQUENCE OF OltPropertyEntry
      MAX-ACCESS not-accessible
      STATUS current
      DESCRIPTION
        "
        OLT属性表"
      ::= { oltObjects 1 }
    
    oltPropertyEntry OBJECT-TYPE
      SYNTAX OltPropertyEntry
      MAX-ACCESS not-accessible
      STATUS current
      DESCRIPTION
        " "
      INDEX { oltDeviceIndex }
      ::= { oltPropertyTable 1 }
    
    OltPropertyEntry ::=
      SEQUENCE { 
        oltDeviceIndex
          INTEGER,
        oltName
          DisplayString,
        oltType
          DisplayString,
        oltAdminStatus
          INTEGER,
        oltDeviceUpTime
          TimeStamp,
        oltDeviceNumOfTotalServiceSlot
          INTEGER,
        oltDeviceNumOfTotalPowerSlot
          INTEGER,
        oltDeviceNumOfTotalFanSlot
          INTEGER,
        oltDeviceStyle
          INTEGER
                    
       }

    oltDeviceIndex  OBJECT-TYPE
      SYNTAX INTEGER
      MAX-ACCESS not-accessible
      STATUS current
      DESCRIPTION
        "
        OLT设备索引号。
        
        一个OLT节点可以由多台OLT设备组成。节点内的每台OLT设备由OLT设备索引号唯一标识"
      ::= { oltPropertyEntry 1 }
    
    oltName OBJECT-TYPE
      SYNTAX DisplayString
      MAX-ACCESS read-write
      STATUS current
      DESCRIPTION
        "
        该OLT设备的名称"
      ::= { oltPropertyEntry 2 }
    
    oltType OBJECT-TYPE
      SYNTAX DisplayString
      MAX-ACCESS read-only
      STATUS current
      DESCRIPTION
        "
        OLT设备类型"
      ::= { oltPropertyEntry 3 }
    
    oltAdminStatus OBJECT-TYPE
      SYNTAX INTEGER
        {
        up(1),
        down(2),
        testing(3)
        }
      MAX-ACCESS read-only
      STATUS current
      DESCRIPTION
        "
        OLT设备管理状态        
        up(1)      - 设备允许提供业务
        down(2)    - 设备禁止提供业务
        testing(3) - 设备处于测试状态,该状态下可能无法正常提供业务"
      ::= { oltPropertyEntry 4 }
    
    oltDeviceUpTime OBJECT-TYPE
      SYNTAX TimeStamp
      MAX-ACCESS read-only
      STATUS current
      DESCRIPTION
        "
        该OLT设备启动时长"
      ::= { oltPropertyEntry 5 }

    oltDeviceNumOfTotalServiceSlot OBJECT-TYPE
      SYNTAX INTEGER
      MAX-ACCESS read-only
      STATUS current
      DESCRIPTION
        "
        Total number of service slots in the OLT device, including
        service card, switch card, control card, uplink card, etc. 
        but except power, FAN, regardless whether the slot is installed
        module"
      ::= { oltPropertyEntry 6 }

    oltDeviceNumOfTotalPowerSlot OBJECT-TYPE
      SYNTAX INTEGER
      MAX-ACCESS read-only
      STATUS current
      DESCRIPTION
        "
        Total number of power slots in the OLT device, regardless whether 
        the slot is installed module"
      ::= { oltPropertyEntry 7 }
       
    oltDeviceNumOfTotalFanSlot OBJECT-TYPE
      SYNTAX INTEGER
      MAX-ACCESS read-only
      STATUS current
      DESCRIPTION
        "
        Total number of FAN slots in the OLT device, regardless whether 
        the slot is installed module"
      ::= { oltPropertyEntry 8 }

    oltDeviceStyle OBJECT-TYPE
      SYNTAX INTEGER
        {
          fixed(1),
          chassisBased(2),
          other(3)
        }
      MAX-ACCESS read-only
      STATUS current
      DESCRIPTION
        "
        The device stype of either fixed or chassis based：        
        fixed(1) - such as pizza box
        chassisBased(2) - Have number of slots for installing service card, power card, etc.        
        "
      ::= { oltPropertyEntry 9 }
    
    boardObjects OBJECT-IDENTITY
      STATUS current
      DESCRIPTION 
        "
        板卡管理项"
      ::= { systemObjects 3 }
    
    boardTable OBJECT-TYPE
      SYNTAX SEQUENCE OF BoardEntry
      MAX-ACCESS not-accessible
      STATUS current
      DESCRIPTION
        "
        OLT板卡表        
        This table shall include rows for all slots, including the slots has
        a presence state of 'NotInstalled'.
        "
      ::= { boardObjects 1 }
    
    boardEntry OBJECT-TYPE
      SYNTAX BoardEntry
      MAX-ACCESS not-accessible
      STATUS current
      DESCRIPTION
        " "
      INDEX { bDeviceIndex, bCardIndex}
      ::= { boardTable 1 }
    
    BoardEntry ::=
      SEQUENCE { 
        bDeviceIndex
          INTEGER,
        bCardIndex
          EponCardIndex,
        bType
          INTEGER,
        bAttribute
          INTEGER,
        bOperationStatus
          INTEGER,
        bAdminStatus
          INTEGER,
        bHardwareVersion
          DisplayString,
        bFirmwareVersion
          DisplayString,
        bSoftwareVersion
          DisplayString,
        bUpTime
          TimeStamp,
        bAlarmStatus
          BITS,
        bSerialNumber
          DisplayString,
        bAction
          INTEGER,
        bName
          OCTET STRING,
        bPresenceStatus 
          INTEGER
       }

    bDeviceIndex  OBJECT-TYPE
      SYNTAX INTEGER
      MAX-ACCESS not-accessible
      STATUS current
      DESCRIPTION
        "
        OLT设备索引号。        
        一个OLT节点可以由多台OLT设备组成。节点内的每台OLT设备由OLT设备索引号唯一标识"
      ::= { boardEntry 1 }

    bCardIndex  OBJECT-TYPE
      SYNTAX EponCardIndex
      MAX-ACCESS not-accessible
      STATUS current
      DESCRIPTION
        "
        板卡索引号"
      ::= { boardEntry 2 }
    
    bType OBJECT-TYPE
      SYNTAX INTEGER
        {
        controlBoard(1),
        geponBoard(2),
        uplinkBoard(3),
        switchBoard(4),
        other(5),
        vacant(6)
        }
      MAX-ACCESS read-only
      STATUS current
      DESCRIPTION
        "
        板卡类型        
        controlBoard(1) - 主控板
        geponBoard(2)    - GE EPON板
        uplinkBoard(3)  - 上联板
        switchBoard(4)  - 交换板(考虑存在交换板和主控板分开的情况)
        other(5)        - 未知类型板卡 
        vacant(6)   - 板卡未插入
        "
      ::= { boardEntry 3 }
    
    bAttribute OBJECT-TYPE
      SYNTAX INTEGER
        {
        active(1),
        standby(2),
        standalone(3),
        notApplicable(4)
        }
      MAX-ACCESS read-only
      STATUS current
      DESCRIPTION
        "
        板卡属性 - 用于描述主控卡和交换卡在主备冗余方式下的状态
        
        active(1)        - 该板卡为主用板卡 
        standby(2)       - 该板卡为备用板卡
        standalone(3)    - 独立工作,用于描述OLT设备不支持主控卡和交换卡主备冗余方式
                           时的工作状态
        notApplicable(4) - 该板卡不是主控卡和交换卡,此对象不适用于该板卡"
      ::= { boardEntry 4 }
    
    bOperationStatus OBJECT-TYPE
      SYNTAX INTEGER
        {
        up(1),
        down(2),
        testing(3)
        }
      MAX-ACCESS read-only
      STATUS current
      DESCRIPTION
        "
        板卡操作状态
        
        up(1)      - 该板卡可以提供业务
        down(2)    - 该板卡无法提供业务
        testing(3) - 该板卡处于测试状态,该状态下可能无法正常提供业务"
      ::= { boardEntry 5 }
    
    bAdminStatus OBJECT-TYPE
      SYNTAX INTEGER
        {
        up(1),
        down(2),
        testing(3)
        }
      MAX-ACCESS read-write
      STATUS current
      DESCRIPTION
        "
        板卡管理状态        
        up(1)      - 该板卡允许提供业务
        down(2)    - 该板卡禁止提供业务
        testing(3) - 该板卡处于测试状态,该状态下可能无法正常提供业务"
      ::= { boardEntry 6 }
    
    bHardwareVersion OBJECT-TYPE
      SYNTAX DisplayString
      MAX-ACCESS read-only
      STATUS current
      DESCRIPTION
        "
        板卡硬件版本"
      ::= { boardEntry 7 }
    
    bFirmwareVersion OBJECT-TYPE
      SYNTAX DisplayString
      MAX-ACCESS read-only
      STATUS current
      DESCRIPTION
        "
        板卡固件版本"
      ::= { boardEntry 8 }
    
    bSoftwareVersion OBJECT-TYPE
      SYNTAX DisplayString
      MAX-ACCESS read-only
      STATUS current
      DESCRIPTION
        "
        板卡软件版本"
      ::= { boardEntry 9 }
    
    bUpTime OBJECT-TYPE
      SYNTAX TimeStamp
      MAX-ACCESS read-only
      STATUS current
      DESCRIPTION
        "
        板卡在线时间"
      ::= { boardEntry 10 }
    
    bAlarmStatus OBJECT-TYPE
      SYNTAX BITS
        {
        critical(0),
        major(1),
        minor(2),
        warning(3)
        }
      MAX-ACCESS read-only
      STATUS current
      DESCRIPTION
        "
        板卡告警状态"
      ::= { boardEntry 11 }
    
    bSerialNumber OBJECT-TYPE
      SYNTAX DisplayString
      MAX-ACCESS read-only
      STATUS current
      DESCRIPTION
        "
        板卡SN"
      ::= { boardEntry 12 }
    
    bAction OBJECT-TYPE
      SYNTAX INTEGER
        {
        noAction(1),
        switchover(2),
        upgrade(3)
        }
      MAX-ACCESS read-write
      STATUS current
      DESCRIPTION
        "
        对板卡施加的操作        
        noAction(1)    - 表示没有任何操作,用于默认设置和其他操作完成后恢复值
        switchover(2)  - 主备切换,只针对主控卡和交换卡
        upgrade(3)     - 板卡软件升级"
      ::= { boardEntry 13 }
    bName OBJECT-TYPE
      SYNTAX OCTET STRING (SIZE (1..32))
      MAX-ACCESS read-only
      STATUS current
      DESCRIPTION
        "
        The board name defined by vendor individual"
      ::= { boardEntry 14 }
    
    bPresenceStatus OBJECT-TYPE
      SYNTAX INTEGER
        {
        installed(1),
        notInstalled(2),
        others(3)
        }
      MAX-ACCESS read-only
      STATUS current
      DESCRIPTION
        "The physical presence status of the slot"
      ::= { boardEntry 15 }
    
    powerObjects OBJECT-IDENTITY
      STATUS current
      DESCRIPTION 
        "
        电源表模块列表"
      ::= { systemObjects 4 }
    
    powerPropertyTable OBJECT-TYPE
      SYNTAX SEQUENCE OF PowerPropertyEntry
      MAX-ACCESS not-accessible
      STATUS current
      DESCRIPTION
        "
        电源板属性表"
      ::= { powerObjects 1 }
    
    powerPropertyEntry OBJECT-TYPE
      SYNTAX PowerPropertyEntry
      MAX-ACCESS not-accessible
      STATUS current
      DESCRIPTION
        " "
      INDEX { powerDeviceIndex, powerCardIndex}
      ::= { powerPropertyTable 1 }
    
    PowerPropertyEntry ::=
      SEQUENCE { 
        powerDeviceIndex
          INTEGER,
        powerCardIndex
          EponCardIndex,
        powerCardOperationStatus
          INTEGER,
        powerCardAlarmStatus
          BITS,
        powerCardAction
          INTEGER,
        powerCardName
          OCTET STRING,
        powerCardPresenceStatus
          INTEGER,
        powerCardRedundancyStatus
          INTEGER
       }

    powerDeviceIndex  OBJECT-TYPE
      SYNTAX INTEGER
      MAX-ACCESS not-accessible
      STATUS current
      DESCRIPTION
        "
        OLT设备索引号。        
        一个OLT节点可以由多台OLT设备组成。节点内的每台OLT设备由OLT设备索引号唯一标识"
      ::= { powerPropertyEntry 1 }

    powerCardIndex  OBJECT-TYPE
      SYNTAX EponCardIndex
      MAX-ACCESS not-accessible
      STATUS current
      DESCRIPTION
        "
        板卡索引号"
      ::= { powerPropertyEntry 2 }

    powerCardOperationStatus OBJECT-TYPE
      SYNTAX INTEGER
        {
        up(1),
        down(2),
        testing(3)
        }
      MAX-ACCESS read-only
      STATUS current
      DESCRIPTION
        "
        电源板操作状态        
        up(1)      - 该板卡可以提供业务
        down(2)    - 该板卡无法提供业务
        testing(3) - 该板卡处于测试状态,该状态下可能无法正常提供业务"
      ::= { powerPropertyEntry 3 }
    
    powerCardAlarmStatus OBJECT-TYPE
      SYNTAX BITS
        {
        critical(0),
        major(1),
        minor(2),
        warning(3)
        }
      MAX-ACCESS read-only
      STATUS current
      DESCRIPTION
        "
        电源板告警状态"
      ::= { powerPropertyEntry 4 }
    
    powerCardAction OBJECT-TYPE
      SYNTAX INTEGER
        {
        noAction(1),
        switchover(2)
        }
      MAX-ACCESS read-write
      STATUS current
      DESCRIPTION
        "
        对电源板施加的操作        
        noAction(1)    - 表示没有任何操作,用于默认设置和其他操作完成后恢复值
        switchover(2)  - 主备切换,如果电源工作在主备模式
        
        Note:
        
        Switchover(2) shall be only set to the power board with powerCardRedundancyStatus
        of active(1)"
      ::= { powerPropertyEntry 5 }

    powerCardName OBJECT-TYPE
      SYNTAX OCTET STRING (SIZE (1..32))
      MAX-ACCESS read-only
      STATUS current
      DESCRIPTION
        "
        The power card name defined by vendor individual"
      ::= { powerPropertyEntry 6 }
   
    powerCardPresenceStatus OBJECT-TYPE
      SYNTAX INTEGER
        {
        installed(1),
        notInstalled(2),
        others(3)
        }
      MAX-ACCESS read-only
      STATUS current
      DESCRIPTION
        "The physical presence status of the power slot"
      ::= { powerPropertyEntry 7 }

    powerCardRedundancyStatus OBJECT-TYPE
      SYNTAX INTEGER
        {
        active(1),
        stanby(2),
        standalone(3),
        loadShareing(4)
        }
      MAX-ACCESS read-only
      STATUS current
      DESCRIPTION
        "The redundancy status of the power card：        
        active(1)   -   The power card is working on redundanct active/
                    Standby mode and the current role is active.
        stanby(2)   - The power card is working on redundanct active/
                    Standby mode and the current role is standby.
        standalone(3) -   The power card is not working on redundanct mode 
                  and the current role is standalone.
        loadShareing(4) -   The power card is working on redundanct loadsharing
                  mode.
        "
      ::= { powerPropertyEntry 8 }
    
    fanObjects OBJECT-IDENTITY
      STATUS current
      DESCRIPTION 
        "
        风扇表"
      ::= { systemObjects 5 }
    
    fanPropertyTable OBJECT-TYPE
      SYNTAX SEQUENCE OF FanPropertyEntry
      MAX-ACCESS not-accessible
      STATUS current
      DESCRIPTION
        "
        风扇属性表"
      ::= { fanObjects 1 }
    
    fanPropertyEntry OBJECT-TYPE
      SYNTAX FanPropertyEntry
      MAX-ACCESS not-accessible
      STATUS current
      DESCRIPTION
        " "
      INDEX { fanDeviceIndex, fanCardIndex}
      ::= { fanPropertyTable 1 }
    
    FanPropertyEntry ::=
      SEQUENCE { 
        fanDeviceIndex
          INTEGER,
        fanCardIndex
          EponCardIndex,
        fanCardOperationStatus
          INTEGER,
        fanCardAlarmStatus
          BITS,
        fanCardName
          OCTET STRING,
        fanCardPresenceStatus
          INTEGER
       }

    fanDeviceIndex  OBJECT-TYPE
      SYNTAX INTEGER
      MAX-ACCESS not-accessible
      STATUS current
      DESCRIPTION
        "
        OLT设备索引号。        
        一个OLT节点可以由多台OLT设备组成。节点内的每台OLT设备由OLT设备索引号唯一标识"
      ::= { fanPropertyEntry 1 }

    fanCardIndex  OBJECT-TYPE
      SYNTAX EponCardIndex
      MAX-ACCESS not-accessible
      STATUS current
      DESCRIPTION
        "
        板卡索引号"
      ::= { fanPropertyEntry 2 }

    fanCardOperationStatus OBJECT-TYPE
      SYNTAX INTEGER
        {
        up(1),
        down(2),
        testing(3)
        }
      MAX-ACCESS read-only
      STATUS current
      DESCRIPTION
        "
        风扇板操作状态        
        up(1)      - 该板卡可以提供业务
        down(2)    - 该板卡无法提供业务
        testing(3) - 该板卡处于测试状态,该状态下可能无法正常提供业务"
      ::= { fanPropertyEntry 3 }
    
    fanCardAlarmStatus OBJECT-TYPE
      SYNTAX BITS
        {
        critical(0),
        major(1),
        minor(2),
        warning(3)
        }
      MAX-ACCESS read-only
      STATUS current
      DESCRIPTION
        "
        风扇板告警状态"
      ::= { fanPropertyEntry 4 }

    fanCardName OBJECT-TYPE
      SYNTAX OCTET STRING (SIZE (1..32))
      MAX-ACCESS read-only
      STATUS current
      DESCRIPTION
        "
        The FAN card name defined by vendor individual"
      ::= { fanPropertyEntry 5 }
    
    fanCardPresenceStatus OBJECT-TYPE
      SYNTAX INTEGER
        {
        installed(1),
        notInstalled(2),
        others(3)
        }
      MAX-ACCESS read-only
      STATUS current
      DESCRIPTION
        "The physical presence status of the FAN card slot"
      ::= { fanPropertyEntry 6 }
  
    fileTransferManagement OBJECT-IDENTITY
      STATUS current
      DESCRIPTION 
        "
        文件传输节点"
      ::= { systemObjects 6 }
    
    fileTransferTable OBJECT-TYPE
      SYNTAX SEQUENCE OF FileTransferEntry
      MAX-ACCESS not-accessible
      STATUS current
      DESCRIPTION
        "
        文件传输进程表"
      ::= { fileTransferManagement 1 }
    
    fileTransferEntry OBJECT-TYPE
      SYNTAX FileTransferEntry
      MAX-ACCESS not-accessible
      STATUS current
      DESCRIPTION
        " "
      INDEX { fileTransferIndex }
      ::= { fileTransferTable 1 }
    
    FileTransferEntry ::=
      SEQUENCE { 
        fileTransferIndex
          INTEGER,
        fileTransferProtocolType
          INTEGER,
        serverIpAddress
          IpAddress,
        ftpUserName
          DisplayString,
        ftpUserPassword
          DisplayString,
        transferFileSrcNamePath
          DisplayString,
        transferFileDstNamePath
          DisplayString,
        transferAction
          INTEGER,
        transferStatus
          INTEGER
       }

    fileTransferIndex OBJECT-TYPE
      SYNTAX INTEGER (1..10)
      MAX-ACCESS not-accessible
      STATUS current
      DESCRIPTION
        "
        文件传送进程流水号"
      ::= { fileTransferEntry 1 }
    
    fileTransferProtocolType OBJECT-TYPE
      SYNTAX INTEGER
        {
        ftp(1),
        tftp(2)
        }
      MAX-ACCESS read-write
      STATUS current
      DESCRIPTION
        "
        该进程使用的文件传输协议类型"
      ::= { fileTransferEntry 2 }
    
    serverIpAddress OBJECT-TYPE
      SYNTAX IpAddress
      MAX-ACCESS read-write
      STATUS current
      DESCRIPTION
        "
        该进程使用的服务器IP地址"
      ::= { fileTransferEntry 3 }
    
    ftpUserName OBJECT-TYPE
      SYNTAX DisplayString
      MAX-ACCESS read-write
      STATUS current
      DESCRIPTION
        "
        该进程使用的用户名,仅适用于FTP协议"
      ::= { fileTransferEntry 4 }
    
    ftpUserPassword OBJECT-TYPE
      SYNTAX DisplayString
      MAX-ACCESS read-write
      STATUS current
      DESCRIPTION
        "
        该进程使用的密码,仅适用于FTP协议"
      ::= { fileTransferEntry 5 }
    
    transferFileSrcNamePath OBJECT-TYPE
      SYNTAX DisplayString
      MAX-ACCESS read-write
      STATUS current
      DESCRIPTION
        "
        该进程对应的文件源名称路径,比如‘/tftproot/file/image.bin"
      ::= { fileTransferEntry 6 }
    
    transferFileDstNamePath OBJECT-TYPE
      SYNTAX DisplayString
      MAX-ACCESS read-write
      STATUS current
      DESCRIPTION
        "
        该进程对应的文件目的名称路径,比如‘/tftproot/file/image.bin"
      ::= { fileTransferEntry 7 }
    
    transferAction OBJECT-TYPE
      SYNTAX INTEGER
        {
        noOperation(1),
        put(2), 
        get(3),
        halt(4)
        }
      MAX-ACCESS read-write
      STATUS current
      DESCRIPTION
        "
        该进程对应的文件传输动作        
        noOperation(1) - 表示没有任何传输操作,用于默认设置和其他操作完成后恢复值
        put(2)       - 上传文件
        get(3)         - 下载文件
        halt(4)        - 停止文件传送"
      ::= { fileTransferEntry 8 }
    
    transferStatus OBJECT-TYPE
      SYNTAX INTEGER
        {
        idle(1),
        inProgress(2),
        success(3),
        failure(4)
        }
      MAX-ACCESS read-only
      STATUS current
      DESCRIPTION
        "
        该进程对应的文件传输状态        
        idle(1)       - 空闲
        inProgress(2) - 正在传送中
        success(3)    - 传送成功
        failure(4)    - 传送失败"
      ::= { fileTransferEntry 9 }

    
    fileInfoManagementTable OBJECT-TYPE
      SYNTAX SEQUENCE OF FileInfoManagementEntry
      MAX-ACCESS not-accessible
      STATUS current
      DESCRIPTION
        "       
        It is done by file list per directionary.        
        Please walk filePath for the file lists in the specified
        path. If leave it NULL or walk fileInfoManagementEntry,
        the file list of the root directionary shall be returned        
        "
      ::= { fileTransferManagement 2 }
    
    fileInfoManagementEntry OBJECT-TYPE
      SYNTAX FileInfoManagementEntry
      MAX-ACCESS not-accessible
      STATUS current
      DESCRIPTION
        " "
      INDEX { filePath, fileName }
      ::= { fileInfoManagementTable 1 }
    
    FileInfoManagementEntry ::=
      SEQUENCE { 
        filePath
          DisplayString,
        fileName
          DisplayString,
        fileSize
          Counter32,
        fileModifyTime
          DateAndTime,
        fileManagementAction
          INTEGER,
        fileAttribute
          INTEGER
       }
              
    filePath OBJECT-TYPE
      SYNTAX DisplayString
      MAX-ACCESS not-accessible
      STATUS current
      DESCRIPTION
        "
        File path        
        It shall be started with a length octet, followed with path string. The length octet
        shall indicate the number of character octets, excluding length itself.        
        For example, 0x05 41 42 43 44 45, respresents ABCDE        
        It shall be ended with '/', which is used to distinguish the two DisplayString
        indexes. For example, if the path is flash/root, filePath shall be set to flash/root/. 
        "
      ::= { fileInfoManagementEntry 1 }
    fileName OBJECT-TYPE
      SYNTAX DisplayString
      MAX-ACCESS not-accessible
      STATUS current
      DESCRIPTION
        "
        File name. MUST not include '/' character and MUST not be NULL.        
        It shall be started with a length octet, followed with name string. The length octet
        shall indicate the number of character octets, excluding length itself.        
        For example, 0x05 41 42 43 44 45, respresents ABCDE
        "
      ::= { fileInfoManagementEntry 2 }
         
    fileSize OBJECT-TYPE
      SYNTAX Counter32
      UNITS "bytes"
      MAX-ACCESS read-only
      STATUS current
      DESCRIPTION
        "
        文件大小,以字节为单位"
      ::= { fileInfoManagementEntry 3 }
    
    fileModifyTime OBJECT-TYPE
      SYNTAX DateAndTime
      MAX-ACCESS read-only
      STATUS current
      DESCRIPTION
        "
        文件修改时间"
      ::= { fileInfoManagementEntry 4 }
    
    fileManagementAction OBJECT-TYPE
      SYNTAX INTEGER
        {
        noOperation(1),
        erase(2)
        }
      MAX-ACCESS read-write
      STATUS current
      DESCRIPTION
        "
        对文件施加的动作        
        noOperation(1) - 表示没有任何传输操作,用于默认设置和其他操作完成后恢复值
        erase(2)       - 文件删除"
      ::= { fileInfoManagementEntry 5 }

    fileAttribute OBJECT-TYPE
      SYNTAX INTEGER
        {
        file(1),        -- It is a file
        dir(2)          -- It is a directionary
        }
      MAX-ACCESS read-only
      STATUS current
      DESCRIPTION
        "
        The attribute of the file"
      ::= { fileInfoManagementEntry 6 }


--ONU批处理升级表

onuBatchUpgradeTable OBJECT-TYPE
SYNTAX SEQUENCE OF OnuBatchUpgradeEntry
MAX-ACCESS not-accessible
STATUS current
DESCRIPTION
"
ONU批处理升级表,具体实现流程见附录A.1 "
::= { systemObjects 7 }

	
	onuBatchUpgradeEntry OBJECT-TYPE
	  SYNTAX OnuBatchUpgradeEntry
	  MAX-ACCESS not-accessible
	  STATUS current
	  DESCRIPTION
	    " "
	    INDEX { onuBatchUpgradeIndex }
	  ::= { onuBatchUpgradeTable 1 }	

	OnuBatchUpgradeEntry ::=
	  SEQUENCE {
	    onuBatchUpgradeIndex
	      INTEGER,
	    onuBatchUpgradeOnuList
	      OCTET STRING,
	    onuBatchUpgradeAction
	      INTEGER,
	    onuBatchUpgradeStatus
	      OCTET STRING,
	    onuBatchUpgradeImageName
	      DisplayString
	  }
	
    onuBatchUpgradeIndex OBJECT-TYPE
      SYNTAX INTEGER (1..16)
      MAX-ACCESS not-accessible
      STATUS current
      DESCRIPTION
        "
        onu升级操作索引,OLT厂商根据OLT对ONU升级的并行能力,建立一定数量的升级操作项,至少为1,不强制要求并行升级多类型ONU,允许串行方式执行"
      ::= { onuBatchUpgradeEntry 1 }

	onuBatchUpgradeOnuList OBJECT-TYPE
	  SYNTAX OCTET STRING
	  MAX-ACCESS read-write
	  STATUS current
	  DESCRIPTION
	    "Onu列表,每4byte表示一个onu(参照EponDeviceIndex),长度为4 * (onu个数),最大长度是4*256"
	  ::= { onuBatchUpgradeEntry 2 }
	
	
	onuBatchUpgradeAction OBJECT-TYPE
	  SYNTAX INTEGER
	  MAX-ACCESS read-write
	  STATUS current
	  DESCRIPTION
	    "写入任意值触发升级"
	  ::= { onuBatchUpgradeEntry 3 }
	
	
	onuBatchUpgradeStatus OBJECT-TYPE
	  SYNTAX OCTET STRING
	  MAX-ACCESS read-only
	  STATUS current
	  DESCRIPTION
	    "
	    Onu列表,每2byte表示一个onu的升级状态,长度为2 * (onu个数),同当前升级任务的onulist一一对应
	    状态码说明：
	    1：Idle
	    2：Waiting
	    3：InProgress
	    4：Success
	    5：Failure(不确定原因的错误)
	    6：OnuTypeNotConsistent(Onu类型不一致)
	    7：FileDownloadFail(下载镜像失败,包括OLT内部板卡间传输失败或者文件前置校验失败)
	    8：OnuNotExist(Onu掉线或者别的导致Onuid失效的情况)
	    9：NotConsistent(Onu同升级文件不匹配)
	    10：OnuCommunicationFail(Onu通信失败)
	    "
	  ::= { onuBatchUpgradeEntry 4 }
	
	onuBatchUpgradeImageName OBJECT-TYPE
	  SYNTAX DisplayString
	  MAX-ACCESS read-write
	  STATUS current
	  DESCRIPTION
	    "写入用于升级的ONU镜像文件名"
	  ::= { onuBatchUpgradeEntry 5 }	
	




--------------------------------------------------------------------------------
--  sniObjects [OLT上联端口属性管理项](1.3.6.1.4.1.17409.2.3.2)
--------------------------------------------------------------------------------  
       
    sniAttributeTable  OBJECT-TYPE
        SYNTAX      SEQUENCE OF SniAttributeEntry
        MAX-ACCESS  not-accessible
        STATUS      current
        DESCRIPTION
            "A list of sniAttributeTable entries. "
        ::= {sniObjects 1 }
        
    sniAttributeEntry  OBJECT-TYPE
        SYNTAX      SniAttributeEntry
        MAX-ACCESS  not-accessible
        STATUS      current
        DESCRIPTION  
            "The sniAttributeEntry Information"
        INDEX       { sniAttributeDeviceIndex, sniAttributeCardIndex,sniAttributePortIndex }   
        ::={sniAttributeTable 1 }   
        
    SniAttributeEntry ::= SEQUENCE {
        sniAttributeDeviceIndex              INTEGER,  
        sniAttributeCardIndex                EponCardIndex,
        sniAttributePortIndex                EponPortIndex,         
        sniPortName                 DisplayString,
        sniAdminStatus              INTEGER,
        sniOperationStatus          INTEGER,
        sniMediaType                INTEGER,
        sniAutoNegotiationStatus    INTEGER,
        sniAutoNegotiationMode      INTEGER,
        sniPerfStats15minuteEnable  TruthValue,
        sniPerfStats24hourEnable    TruthValue,
        sniLastStatusChangeTime     TimeTicks,
        sniMacAddrLearnMaxNum       INTEGER,
        sniIsolationEnable          TruthValue,
        sniPortType                 INTEGER
      } 

    sniAttributeDeviceIndex  OBJECT-TYPE
        SYNTAX      INTEGER
        MAX-ACCESS  not-accessible
        STATUS      current
        DESCRIPTION
            "Device Index"
        ::= {sniAttributeEntry 1 }      
        
    sniAttributeCardIndex  OBJECT-TYPE
        SYNTAX      EponCardIndex
        MAX-ACCESS  not-accessible
        STATUS      current
        DESCRIPTION
            "Card Index"
        ::= {sniAttributeEntry 2 }  
        
    sniAttributePortIndex  OBJECT-TYPE
        SYNTAX      EponPortIndex
        MAX-ACCESS  not-accessible
        STATUS      current
        DESCRIPTION
            "Port Index"
        ::= {sniAttributeEntry 3 }     

    sniPortName  OBJECT-TYPE
        SYNTAX      DisplayString
        MAX-ACCESS  read-write
        STATUS      current
        DESCRIPTION
            "Port Name"
        ::= {sniAttributeEntry 4 }
        
    sniAdminStatus  OBJECT-TYPE
        SYNTAX      INTEGER {
            up(1),    
            down(2),
            testing(3)
            }      
        MAX-ACCESS  read-write
        STATUS      current
        DESCRIPTION
            "Admin Status"
        ::= {sniAttributeEntry 5 }     

    sniOperationStatus  OBJECT-TYPE
        SYNTAX  INTEGER {
            up(1), 
            down(2),
            testing(3)
            }     
        MAX-ACCESS  read-only
        STATUS      current
        DESCRIPTION
            "Operation Status"
        ::= {sniAttributeEntry 6 }    

    sniMediaType  OBJECT-TYPE
        SYNTAX      INTEGER {
            twistedPair(1),
            fiber(2),
            other(3)
            }             

        MAX-ACCESS  read-only
        STATUS      current
        DESCRIPTION
            "Media Type"
        ::= {sniAttributeEntry 7 }     

    sniAutoNegotiationStatus  OBJECT-TYPE
        SYNTAX      INTEGER {
            auto-negotiate(1),
            half-10(2),
            full-10(3), 
            half-100(4),
            full-100(5),
            full-1000(6),            
            full-10000(7),
            unknown(8)
            }             
        MAX-ACCESS  read-only
        STATUS      current
        DESCRIPTION
            "Auto Negotiation Status"
        ::= {sniAttributeEntry 8 }
        
    sniAutoNegotiationMode  OBJECT-TYPE
        SYNTAX      INTEGER {
            auto-negotiate(1),
            half-10(2),
            full-10(3), 
            half-100(4),
            full-100(5),
            full-1000(6),            
            full-10000(7)
            }   
        MAX-ACCESS  read-write
        STATUS      current
        DESCRIPTION
            "Auto Negotiation Mode"
        ::= {sniAttributeEntry 9 }     

    sniPerfStats15minuteEnable  OBJECT-TYPE
        SYNTAX      TruthValue
        MAX-ACCESS  read-write
        STATUS      current
        DESCRIPTION
            "true(1) false(2)"
        ::= {sniAttributeEntry 10 } 
        
    sniPerfStats24hourEnable  OBJECT-TYPE
        SYNTAX      TruthValue      
        MAX-ACCESS  read-write
        STATUS      current
        DESCRIPTION
            "true(1) false(2)"
        ::= {sniAttributeEntry 11 }     

    sniLastStatusChangeTime  OBJECT-TYPE
        SYNTAX      TimeTicks
        MAX-ACCESS  read-only
        STATUS      current
        DESCRIPTION
            "Last Change Time"
        ::= {sniAttributeEntry 12 }
        
    sniMacAddrLearnMaxNum  OBJECT-TYPE
        SYNTAX      INTEGER
        MAX-ACCESS  read-write
        STATUS      current
        DESCRIPTION
            "Number of MAC address limited on the SNI port.            
            value 0 means no limit.
入口方向"
        ::= {sniAttributeEntry 13 }     

    sniIsolationEnable  OBJECT-TYPE
        SYNTAX      TruthValue
        MAX-ACCESS  read-write
        STATUS      current
        DESCRIPTION
            "Whether or not isolate the SNI port to other ports"
        ::= {sniAttributeEntry 14 } 
  
sniPortType OBJECT-TYPE
SYNTAX INTEGER{
ge-Port(1),
ten-Ge-Port(2)
}
MAX-ACCESS read-only
STATUS current
DESCRIPTION
" SNI port type, Ge-Port, 10Ge-Port"
::= {sniAttributeEntry 15 }


  sniTrunkManagement  OBJECT-IDENTITY
    STATUS current
    DESCRIPTION 
      ""
    ::= { sniObjects 2 }
       
    sniTrunkGroupConfigTable  OBJECT-TYPE
        SYNTAX      SEQUENCE OF SniTrunkGroupConfigEntry
        MAX-ACCESS  not-accessible
        STATUS      current
        DESCRIPTION
            "A list of sniTrunkGroupConfigTable entries."
        ::= {sniTrunkManagement 1 }
        
    sniTrunkGroupConfigEntry  OBJECT-TYPE
        SYNTAX      SniTrunkGroupConfigEntry
        MAX-ACCESS  not-accessible
        STATUS      current
        DESCRIPTION  
            "The sniTrunk Group Config Entry Information"
        INDEX       { sniTrunkGroupConfigIndex }    
        ::={sniTrunkGroupConfigTable 1 }   
        
    SniTrunkGroupConfigEntry ::= SEQUENCE {
        sniTrunkGroupConfigIndex      INTEGER,  
        sniTrunkGroupConfigName       DisplayString,
        sniTrunkGroupConfigMember     OCTET STRING,     
        sniTrunkGroupConfigPolicy     INTEGER,
        sniTrunkGroupConfigRowstatus  RowStatus
      } 

    sniTrunkGroupConfigIndex  OBJECT-TYPE
        SYNTAX      INTEGER
        MAX-ACCESS  not-accessible
        STATUS      current
        DESCRIPTION
            "Trunk Group Config Index"
        ::= {sniTrunkGroupConfigEntry 1 } 
            
    sniTrunkGroupConfigName  OBJECT-TYPE
        SYNTAX      DisplayString
        MAX-ACCESS  read-create
        STATUS      current
        DESCRIPTION
            "Trunk Group Config Name"
        ::= {sniTrunkGroupConfigEntry 2 }     
        
    sniTrunkGroupConfigMember  OBJECT-TYPE
        SYNTAX      OCTET STRING
        MAX-ACCESS  read-create
        STATUS      current
        DESCRIPTION
            "Trunk Group Config Member.            
            It is presented by member port list. Each member port is identified
            by 4-byte format, same as TC of EponDeviceIndex. The actual length of
            this string depends of the number of member ports in the trunk group.
            The relationship is:            
            Length of the string = 4 * (NUM of member ports)              
            For example, if device 1, port 1/2 and 2/3 is the member ports of the
            trunk, then sniTrunkGroupConfigMember is presented as:
            01 01 02 00 01 02 03 00
            "
        ::= {sniTrunkGroupConfigEntry 3 }
    sniTrunkGroupConfigPolicy  OBJECT-TYPE
        SYNTAX      INTEGER
            {
      srcMac(1),        
      destMac(2),       
      srcMacNDestMac(3),
      srcIp(4),         
      destIp(5),        
      srcIpNDestIp(6)  
             }
        MAX-ACCESS  read-create
        STATUS      current
        DESCRIPTION
            "Trunk Group Config Policy"
        ::= {sniTrunkGroupConfigEntry 4 }   

    sniTrunkGroupConfigRowstatus  OBJECT-TYPE
        SYNTAX      RowStatus
        MAX-ACCESS  read-create
        STATUS      current
        DESCRIPTION
            "Trunk Group Config Rowstatus"
        ::= {sniTrunkGroupConfigEntry 5 } 
  
    sniTrunkGroupTable  OBJECT-TYPE
        SYNTAX      SEQUENCE OF SniTrunkGroupEntry
        MAX-ACCESS  not-accessible
        STATUS      current
        DESCRIPTION
            "a list of sniTrunkGroupConfigTable entries. "
        ::= {sniTrunkManagement 2 }
        
    sniTrunkGroupEntry  OBJECT-TYPE
        SYNTAX      SniTrunkGroupEntry
        MAX-ACCESS  not-accessible
        STATUS      current
        DESCRIPTION  
            "Trunk Group Entry"
        INDEX       { sniTrunkGroupIndex }    
        ::={sniTrunkGroupTable 1 }   
        
    SniTrunkGroupEntry ::= SEQUENCE {
        sniTrunkGroupIndex            INTEGER,  
        sniTrunkGroupOperationStatus  INTEGER,
        sniTrunkGroupActualSpeed      INTEGER,     
        sniTrunkGroupAdminStatus      INTEGER
      }

    sniTrunkGroupIndex  OBJECT-TYPE
        SYNTAX      INTEGER
        MAX-ACCESS  not-accessible
        STATUS      current
        DESCRIPTION
            "Trunk Group Index "
        ::= {sniTrunkGroupEntry 1 } 
        
    sniTrunkGroupOperationStatus  OBJECT-TYPE
        SYNTAX  INTEGER {
            up(1), 
            down(2),
            testing(3)
            } 
        MAX-ACCESS  read-only
        STATUS      current
        DESCRIPTION
            "Trunk Group Operation Status"
        ::= {sniTrunkGroupEntry 2 }   

    sniTrunkGroupActualSpeed  OBJECT-TYPE
        SYNTAX      INTEGER
        UNITS   "Mbps"
        MAX-ACCESS  read-only
        STATUS      current 
        DESCRIPTION
            "Trunk Group Actual Speed.            
            The speed is the aggregated rates of all operational UP member
            ports of the trunk.            
            For example, 4 member ports of the trunk, two are UP, each is 1000M
            then the SUN is 2000M. As a result, the return of the MIB shall be
            2000Mbps"
        ::= {sniTrunkGroupEntry 3 } 
        
    sniTrunkGroupAdminStatus  OBJECT-TYPE
        SYNTAX      INTEGER {
            up(1),       
            down(2),
            testing(3)  
            }
        MAX-ACCESS  read-write
        STATUS      current
        DESCRIPTION
            "Trunk Group AdminStatus"
        ::= {sniTrunkGroupEntry 4 }

    sniMirrorTable  OBJECT-TYPE
        SYNTAX      SEQUENCE OF SniMirrorEntry
        MAX-ACCESS  not-accessible
        STATUS      current
        DESCRIPTION
            "a list of sniMirrorTable entries."
        ::= {sniObjects 3 }
        
    sniMirrorEntry  OBJECT-TYPE
        SYNTAX      SniMirrorEntry
        MAX-ACCESS  not-accessible
        STATUS      current
        DESCRIPTION  
            "The Mirror Information."
        INDEX       { sniMirrorGroupIndex }
        ::={sniMirrorTable 1 }   
        
    SniMirrorEntry ::= SEQUENCE {
        sniMirrorGroupIndex           INTEGER,  
        sniMirrorGroupName            DisplayString,
        sniMirrorGroupDstPortList     OCTET STRING,         
        sniMirrorGroupSrcInPortList   OCTET STRING,
        sniMirrorGroupSrcOutPortList  OCTET STRING,
        sniMirrorGroupRowstatus       RowStatus
      } 

    sniMirrorGroupIndex  OBJECT-TYPE
        SYNTAX      INTEGER
        MAX-ACCESS  not-accessible
        STATUS      current
        DESCRIPTION
            "Mirror Group Index"
        ::= {sniMirrorEntry 1 } 

    sniMirrorGroupName  OBJECT-TYPE
        SYNTAX      DisplayString
        MAX-ACCESS  read-create
        STATUS      current
        DESCRIPTION
            "Mirror Group Name"
        ::= {sniMirrorEntry 2 } 

    sniMirrorGroupDstPortList  OBJECT-TYPE
        SYNTAX      OCTET STRING
        MAX-ACCESS  read-create
        STATUS      current
        DESCRIPTION
            "Mirror Group Dst Port List.            
            It is presented by destination port list. Each  port is identified
            by 4-byte format, same as TC of EponDeviceIndex. The actual length of
            this string depends of the number of destination ports in this mirror 
            instance.            
            The relationship is:            
            Length of the string = 4 * (NUM of ports)              
            For example, if device 1, port 2/3 is the destination port of the
            mirror instance, then object will be presented as:
            01 02 03 00
            "
        ::= {sniMirrorEntry 3 }

    sniMirrorGroupSrcInPortList  OBJECT-TYPE
        SYNTAX      OCTET STRING
        MAX-ACCESS  read-create
        STATUS      current
        DESCRIPTION
            "Mirror Group Src In Port List.            
            It will includes the PON ports.            
            It is presented by source ingress port list. Each  port is identified
            by 4-byte format, same as TC of EponDeviceIndex. The actual length of
            this string depends of the number of source ingress ports in this mirror 
            instance.            
            The relationship is:            
            Length of the string = 4 * (NUM of ports)              
            For example, if device 1, port 2/3, device 6, port 7/8 is the source
            ingress port of the mirror instance, then object will be presented as:
            01 02 03 00 06 07 08 00            
            "
        ::= {sniMirrorEntry 4 }
        
    sniMirrorGroupSrcOutPortList  OBJECT-TYPE
        SYNTAX      OCTET STRING
        MAX-ACCESS  read-create
        STATUS      current
        DESCRIPTION
            "Mirror Group Src Out Port List.            
            It will includes the PON ports.            
            It is presented by source egress port list. Each  port is identified
            by 4-byte format, same as TC of EponDeviceIndex. The actual length of
            this string depends of the number of source egress ports in this mirror 
            instance.            
            The relationship is:            
            Length of the string = 4 * (NUM of ports)              
            For example, if device 1, port 2/3, device 6, port 7/8 is the source
            egress port of the mirror instance, then object will be presented as:
            01 02 03 00 06 07 08 00
            "  
        ::= {sniMirrorEntry 5 }
        
    sniMirrorGroupRowstatus  OBJECT-TYPE
        SYNTAX      RowStatus
        MAX-ACCESS  read-create
        STATUS      current
        DESCRIPTION
            "Mirror Group Rowstatus"
        ::= {sniMirrorEntry 6 } 

  sniMacAddressManagement OBJECT-IDENTITY
    STATUS current
    DESCRIPTION 
      ""
    ::= { sniObjects 4 }

    sniMacAddressManagementTable  OBJECT-TYPE
        SYNTAX      SEQUENCE OF SniMacAddressManagementEntry
        MAX-ACCESS  not-accessible
        STATUS      current
        DESCRIPTION  
            " A list of MacAddressManagement entries. "
        ::= { sniMacAddressManagement 1 }

    sniMacAddressManagementEntry  OBJECT-TYPE
        SYNTAX      SniMacAddressManagementEntry
        MAX-ACCESS  not-accessible
        STATUS      current
        DESCRIPTION  
            "The Mac Address Management Information"
        INDEX   { sniMacAddressManagementDeviceIndex }
        ::= { sniMacAddressManagementTable 1 }

    SniMacAddressManagementEntry ::=  SEQUENCE {
        sniMacAddressManagementDeviceIndex            INTEGER,
        sniMacAddrTableAgingTime  INTEGER,
        sniMacAddrTableClear      INTEGER           
        }
     
    sniMacAddressManagementDeviceIndex  OBJECT-TYPE
        SYNTAX      INTEGER
        MAX-ACCESS  not-accessible
        STATUS      current
        DESCRIPTION  
            "device Index"
        ::= { sniMacAddressManagementEntry 1 }
          
    sniMacAddrTableAgingTime   OBJECT-TYPE
        SYNTAX      INTEGER 
        UNITS   "Seconds"
        MAX-ACCESS  read-write
        STATUS      current
        DESCRIPTION
            "Mac Address Table Aging Time"
        ::= { sniMacAddressManagementEntry 2 }

    sniMacAddrTableClear OBJECT-TYPE
        SYNTAX      INTEGER { allDynamic(1) }
        MAX-ACCESS  read-write
        STATUS      current
        DESCRIPTION
            "Mac Address Table Clear"
        ::= { sniMacAddressManagementEntry 3 }

    sniMacAddressTable OBJECT-TYPE
        SYNTAX      SEQUENCE OF SniMacAddressEntry
        MAX-ACCESS  not-accessible
        STATUS      current
        DESCRIPTION
            "A list of MacAddress entries."
        ::= { sniMacAddressManagement 2 }

    sniMacAddressEntry OBJECT-TYPE
        SYNTAX      SniMacAddressEntry
        MAX-ACCESS  not-accessible
        STATUS      current
        DESCRIPTION
            "SNI端口学习到的MAC地址列表
"
        INDEX   { sniMacAddrIndex,  sniMacAddrVlanIdIndex }
        ::= { sniMacAddressTable 1 }

    SniMacAddressEntry ::= SEQUENCE {
        sniMacAddrIndex        MacAddress,
        sniMacAddrVlanIdIndex  INTEGER,
        sniMacAddrType         INTEGER,      
        sniMacAddrPortId       EponDeviceIndex,
        sniMacAddrRowStatus    RowStatus
        }

    sniMacAddrIndex OBJECT-TYPE
        SYNTAX      MacAddress
        MAX-ACCESS  not-accessible
        STATUS      current
        DESCRIPTION
            "Mac Address Index"
        ::= { sniMacAddressEntry 1 } 

    sniMacAddrVlanIdIndex   OBJECT-TYPE
        SYNTAX      INTEGER
        MAX-ACCESS  not-accessible
        STATUS      current
        DESCRIPTION
            "Mac Address Vlan Id Index"
        ::= { sniMacAddressEntry 2 } 

    sniMacAddrType  OBJECT-TYPE
        SYNTAX  INTEGER { 
            static(1),
            dynamic(2),
            other(3)}
        MAX-ACCESS  read-create
        STATUS    current
        DESCRIPTION
            "Mac Address Type"
        ::= { sniMacAddressEntry 3}

    sniMacAddrPortId OBJECT-TYPE 
        SYNTAX       EponDeviceIndex
        MAX-ACCESS   read-create
        STATUS       current
        DESCRIPTION     
            "Mac Address Port Id"
        ::=  {  sniMacAddressEntry 4 }

    sniMacAddrRowStatus  OBJECT-TYPE
        SYNTAX      RowStatus
        MAX-ACCESS  read-create
        STATUS      current
        DESCRIPTION
            "delete,create,Update"
        ::= { sniMacAddressEntry 5 }

    sniBroadcastStormSuppressionTable OBJECT-TYPE
        SYNTAX      SEQUENCE OF SniBroadcastStormSuppressionEntry
        MAX-ACCESS  not-accessible
        STATUS      current
        DESCRIPTION
            "A list of BroadcastStormSuppression entries."
        ::= { sniObjects 5 }

    sniBroadcastStormSuppressionEntry OBJECT-TYPE
        SYNTAX      SniBroadcastStormSuppressionEntry
        MAX-ACCESS  not-accessible
        STATUS      current
        DESCRIPTION
            "The Broadcast Storm Suppression Information"
        INDEX   { sniBroadcastStormSuppressionDeviceIndex,  sniBroadcastStormSuppressionCardIndex,  sniBroadcastStormSuppressionPortIndex  }
        ::= { sniBroadcastStormSuppressionTable 1 }

    SniBroadcastStormSuppressionEntry ::=
        SEQUENCE {
            sniBroadcastStormSuppressionDeviceIndex                  INTEGER,
            sniBroadcastStormSuppressionCardIndex                    EponCardIndex,
            sniBroadcastStormSuppressionPortIndex                    EponPortIndex,
            sniUnicastStormEnable               TruthValue,
            sniUnicastStormInPacketRate        INTEGER,
            sniUnicastStormOutPacketRate       INTEGER,      
            sniMulticastStormEnable         TruthValue,
            sniMulticastStormInPacketRate   INTEGER,
            sniMulticastStormOutPacketRate  INTEGER,
            sniBroadcastStormEnable         TruthValue,
            sniBroadcastStormInPacketRate   INTEGER,
            sniBroadcastStormOutPacketRate  INTEGER
        }

    sniBroadcastStormSuppressionDeviceIndex OBJECT-TYPE
        SYNTAX      INTEGER
        MAX-ACCESS  not-accessible
        STATUS      current
        DESCRIPTION
            "device Index"
        ::= { sniBroadcastStormSuppressionEntry 1 }

    sniBroadcastStormSuppressionCardIndex OBJECT-TYPE
        SYNTAX      EponCardIndex
        MAX-ACCESS  not-accessible
        STATUS      current
        DESCRIPTION
            "card Index"
        ::= { sniBroadcastStormSuppressionEntry 2 }   

    sniBroadcastStormSuppressionPortIndex  OBJECT-TYPE
        SYNTAX      EponPortIndex
        MAX-ACCESS  not-accessible
        STATUS      current
        DESCRIPTION
            "port Index"
        ::= { sniBroadcastStormSuppressionEntry 3 }

    sniUnicastStormEnable  OBJECT-TYPE
        SYNTAX      TruthValue
        MAX-ACCESS  read-write
        STATUS      current
        DESCRIPTION
            "Cast Storm Enable"
        ::= { sniBroadcastStormSuppressionEntry 4 }
    sniUnicastStormInPacketRate  OBJECT-TYPE
        SYNTAX      INTEGER
        UNITS   "pps"
        MAX-ACCESS  read-write
        STATUS      current
        DESCRIPTION
            "Cast Storm In Packet Rate"
        ::= { sniBroadcastStormSuppressionEntry 5 }

    sniUnicastStormOutPacketRate  OBJECT-TYPE
        SYNTAX      INTEGER
        UNITS   "pps"
        MAX-ACCESS  read-write
        STATUS      current
        DESCRIPTION
            "Cast Storm Out Packet Rate"
        ::= { sniBroadcastStormSuppressionEntry 6 }

    sniMulticastStormEnable  OBJECT-TYPE
        SYNTAX      TruthValue
        MAX-ACCESS  read-write
        STATUS      current
        DESCRIPTION
            "true(1) false(2)"
        ::= { sniBroadcastStormSuppressionEntry 7 }

    sniMulticastStormInPacketRate  OBJECT-TYPE
        SYNTAX      INTEGER
        UNITS   "pps"
        MAX-ACCESS  read-write
        STATUS      current
        DESCRIPTION
            "Multicast Storm In Packet Rate"
        ::= { sniBroadcastStormSuppressionEntry 8 }

    sniMulticastStormOutPacketRate  OBJECT-TYPE
        SYNTAX      INTEGER
        UNITS   "pps"
        MAX-ACCESS  read-write
        STATUS      current
        DESCRIPTION
            "Multicast Storm Out Packet Rate"
        ::= { sniBroadcastStormSuppressionEntry 9 }

    sniBroadcastStormEnable  OBJECT-TYPE
        SYNTAX      TruthValue
        MAX-ACCESS  read-write
        STATUS      current
        DESCRIPTION
            "true(1) false(2)"
        ::= { sniBroadcastStormSuppressionEntry 10 }

    sniBroadcastStormInPacketRate  OBJECT-TYPE
        SYNTAX      INTEGER
        UNITS   "pps"
        MAX-ACCESS  read-write
        STATUS      current
        DESCRIPTION
            "Broadcast Storm In Packet Rate"
        ::= { sniBroadcastStormSuppressionEntry 11 }

    sniBroadcastStormOutPacketRate  OBJECT-TYPE
        SYNTAX      INTEGER
        UNITS   "pps"
        MAX-ACCESS  read-write
        STATUS      current
        DESCRIPTION
            "Broadcast Storm Out Packet Rate"
        ::= { sniBroadcastStormSuppressionEntry 12 } 
  
--------------------------------------------------------------------------------
--  ponPortObjects[PON端口属性管理项](1.3.6.1.4.1.17409.2.3.3)
-------------------------------------------------------------------------------- 
    ponPortInfoTable OBJECT-TYPE
      SYNTAX SEQUENCE OF PonPortInfoEntry
      MAX-ACCESS not-accessible
      STATUS current
      DESCRIPTION
        "PON端口配置信息表"
      ::= { ponPortObjects 1 }
    
    ponPortInfoEntry OBJECT-TYPE
      SYNTAX PonPortInfoEntry
      MAX-ACCESS not-accessible
      STATUS current
      DESCRIPTION     " "
      INDEX { ponDeviceIndex, ponCardIndex, ponPortIndex}
      ::= { ponPortInfoTable 1 }
    
    PonPortInfoEntry ::=
      SEQUENCE { 
        ponDeviceIndex
          INTEGER,
        ponCardIndex
          EponCardIndex,
        ponPortIndex
          EponPortIndex,
        ponPortType
          INTEGER,
        ponOperationStatus
          INTEGER,
        ponPortAdminStatus
          INTEGER,
        ponPortMaxOnuNumSupport
          INTEGER,
        ponPortUpOnuNum
          INTEGER,
        ponPortEncryptMode
          INTEGER,
        ponPortEncryptKeyExchangeTime
          INTEGER,
        ponPortIsolationEnable
          TruthValue,
        maxDsBandwidth
          INTEGER,
        actualDsBandwidthInUse
          INTEGER,
        remainDsBandwidth
          INTEGER,
        perfStats15minuteEnable
          TruthValue,
        perfStats24hourEnable
          TruthValue,
        ponPortMacAddrLearnMaxNum
          INTEGER,
        maxUsBandwidth
          INTEGER,
        actualUsBandwidthInUse
          INTEGER,
        remainUsBandwidth
          INTEGER,
ponPortName
          DisplayString,
onuLongEmitDetectEnable
INTEGER
       }

    ponDeviceIndex  OBJECT-TYPE
      SYNTAX INTEGER
      MAX-ACCESS not-accessible
      STATUS current
      DESCRIPTION
        "
        OLT设备索引号。        
        一个OLT节点可以由多台OLT设备组成。节点内的每台OLT设备由OLT设备索引号唯一标识"
      ::= { ponPortInfoEntry 1 }
    ponCardIndex  OBJECT-TYPE
      SYNTAX EponCardIndex
      MAX-ACCESS not-accessible
      STATUS current
      DESCRIPTION
        "
        板卡索引号"
      ::= { ponPortInfoEntry 2 }

    ponPortIndex  OBJECT-TYPE
      SYNTAX EponPortIndex
      MAX-ACCESS not-accessible
      STATUS current
      DESCRIPTION
        "
        pon端口索引号"
      ::= { ponPortInfoEntry 3 }

    ponPortType OBJECT-TYPE
      SYNTAX INTEGER
        {
        ge-epon(1),
        tenge-epon(2),
        gpon(3),
        other(4)
        }
      MAX-ACCESS read-only
      STATUS current
      DESCRIPTION
        "
        PON端口类型"
      ::= { ponPortInfoEntry 4 }

    ponOperationStatus OBJECT-TYPE
      SYNTAX INTEGER
        {
        up(1),
        down(2),
        testing(3)
        }
      MAX-ACCESS read-only
      STATUS current
      DESCRIPTION
        "
        端口操作状态        
        up(1)      - 该端口可以提供业务
        down(2)    - 该端口无法提供业务
        testing(3) - 该端口处于测试状态,该状态下可能无法正常提供业务"
      ::= { ponPortInfoEntry 5 }

    ponPortAdminStatus OBJECT-TYPE
      SYNTAX INTEGER
        {
        enable (1), 
        disable (2)
        }
      MAX-ACCESS read-write
      STATUS current
      DESCRIPTION
        "
        板卡管理状态        
        enable (1)      - 该端口允许提供业务
        disable (2)    - 该端口禁止提供业务"
      ::= { ponPortInfoEntry 6 }

    ponPortMaxOnuNumSupport OBJECT-TYPE
      SYNTAX INTEGER
      MAX-ACCESS read-only
      STATUS current
      DESCRIPTION
        "
        支持最多ONU数量"
      ::= { ponPortInfoEntry 7 }

    ponPortUpOnuNum OBJECT-TYPE
      SYNTAX INTEGER
      MAX-ACCESS read-only
      STATUS current
      DESCRIPTION
        "
        在线ONU数量"
      ::= { ponPortInfoEntry 8 }

    ponPortEncryptMode OBJECT-TYPE
      SYNTAX INTEGER 
        {
           aes128(1), 
           ctcTripleChurning(2), 
           other(3)
        }
      MAX-ACCESS read-write
      STATUS current
      DESCRIPTION
        "
        加密模式"
      ::= { ponPortInfoEntry 9 }

    ponPortEncryptKeyExchangeTime OBJECT-TYPE
      SYNTAX INTEGER
      UNITS "seconds"
      MAX-ACCESS read-write
      STATUS current
      DESCRIPTION
        "
        密钥交换时间"
      ::= { ponPortInfoEntry 10 }

    ponPortIsolationEnable OBJECT-TYPE
      SYNTAX TruthValue
      MAX-ACCESS read-write
      STATUS current
      DESCRIPTION
        "
        PON端口隔离使能"
      ::= { ponPortInfoEntry 11 }

    maxDsBandwidth OBJECT-TYPE
      SYNTAX INTEGER
      UNITS "kbps"
      MAX-ACCESS read-only
      STATUS current
      DESCRIPTION
        "
        最大下行带宽"
      ::= { ponPortInfoEntry 12 }
    actualDsBandwidthInUse OBJECT-TYPE
      SYNTAX INTEGER
      UNITS "kbps"
      MAX-ACCESS read-only
      STATUS current
      DESCRIPTION
        "
        实际下行使用带宽"
      ::= { ponPortInfoEntry 13 }

    remainDsBandwidth OBJECT-TYPE
      SYNTAX INTEGER
      UNITS "kbps"
      MAX-ACCESS read-only
      STATUS current
      DESCRIPTION
        "
        剩余下行使用带宽"
      ::= { ponPortInfoEntry 14 }

    perfStats15minuteEnable OBJECT-TYPE
      SYNTAX TruthValue
      MAX-ACCESS read-write
      STATUS current
      DESCRIPTION
        "
        15分钟性能统计使能"
      ::= { ponPortInfoEntry 15 }

    perfStats24hourEnable OBJECT-TYPE
      SYNTAX TruthValue
      MAX-ACCESS read-write
      STATUS current
      DESCRIPTION
        "
        24小时性能统计使能"
      ::= { ponPortInfoEntry 16 }

    ponPortMacAddrLearnMaxNum OBJECT-TYPE
      SYNTAX INTEGER
      MAX-ACCESS read-write
      STATUS current
      DESCRIPTION
        "
        PON口mac地址学习最大数目        
        value 0 means no limit
入口方向(可选)"
      ::= { ponPortInfoEntry 17 }

    maxUsBandwidth OBJECT-TYPE
      SYNTAX INTEGER
      UNITS "kbps"
      MAX-ACCESS read-only
      STATUS current
      DESCRIPTION
        "
        最大上行带宽"
      ::= { ponPortInfoEntry 18 }

    actualUsBandwidthInUse OBJECT-TYPE
      SYNTAX INTEGER
      UNITS "kbps"
      MAX-ACCESS read-only
      STATUS current
      DESCRIPTION
        "
        实际上行使用带宽"
      ::= { ponPortInfoEntry 19 }

    remainUsBandwidth OBJECT-TYPE
      SYNTAX INTEGER
      UNITS "kbps"
      MAX-ACCESS read-only
      STATUS current
      DESCRIPTION
        "
        剩余上行使用带宽"
      ::= { ponPortInfoEntry 20 }

    ponPortName OBJECT-TYPE
      SYNTAX DisplayString
      MAX-ACCESS read-write
      STATUS current
      DESCRIPTION
" 
PON port name."
      ::= { ponPortInfoEntry 21 }

onuLongEmitDetectEnable  OBJECT-TYPE
SYNTAX INTEGER
MAX-ACCESS read-write
STATUS current
DESCRIPTION
     "基于PON口的ONU长发光告警使能
检测开关,0：关闭；1：打开"
::= { ponPortInfoEntry 22 }


    aclManagementGroup OBJECT-IDENTITY
      STATUS current
      DESCRIPTION 
        "
        ACL管理"
      ::= { ponPortObjects 2 }

-- ACL管理三张表的实现顺序(1\2\3)


    aclListTable OBJECT-TYPE
      SYNTAX SEQUENCE OF AclListEntry
      MAX-ACCESS not-accessible
      STATUS current
      DESCRIPTION
        "
        ACL列表"
      ::= { aclManagementGroup 1 }

    aclListEntry OBJECT-TYPE
      SYNTAX AclListEntry
      MAX-ACCESS not-accessible
      STATUS current
      DESCRIPTION     " "
      INDEX { aclListIndex }
      ::= { aclListTable 1 }

    AclListEntry ::=
      SEQUENCE { 
        aclListIndex
          INTEGER,
        aclDescription
          DisplayString,
        ruleRowStatus
          RowStatus
       }

    aclListIndex OBJECT-TYPE
      SYNTAX INTEGER
      MAX-ACCESS not-accessible
      STATUS current
      DESCRIPTION
        "
        ACL表索引"
      ::= { aclListEntry 1 }

    aclDescription OBJECT-TYPE
      SYNTAX DisplayString
      MAX-ACCESS read-create
      STATUS current
      DESCRIPTION
        "
        ACL描述信息"
      ::= { aclListEntry 2 }


    ruleRowStatus OBJECT-TYPE
      SYNTAX RowStatus
      MAX-ACCESS read-create
      STATUS current
      DESCRIPTION
        "
        规则行状态"
      ::= { aclListEntry 3 }

    aclRuleTable OBJECT-TYPE
      SYNTAX SEQUENCE OF AclRuleEntry
      MAX-ACCESS not-accessible
      STATUS current
      DESCRIPTION
        "
        ACL规则表"
      ::= { aclManagementGroup 2 }

    aclRuleEntry OBJECT-TYPE
      SYNTAX AclRuleEntry
      MAX-ACCESS not-accessible
      STATUS current
      DESCRIPTION     " "
      INDEX { aclRuleListIndex,aclRuleIndex }
      ::= { aclRuleTable 1 }

    AclRuleEntry ::=
      SEQUENCE { 
aclRuleListIndex
          INTEGER,        aclRuleIndex
          INTEGER,
        matchedSourceMac
          MacAddress,
        matchedDestinationMac
          MacAddress,
        matchedVlanId
          INTEGER,
        matchedEthernetType
          INTEGER,
        matchedSourceIP
          IpAddress,
        matchedDestinationIP
          IpAddress,
        matchedIpMessageType
          INTEGER,
        matchedDscp
          INTEGER,
        matchedSourcePort
          INTEGER,
        matchedDestinationPort
          INTEGER,
        aclRuleRowStatus
          RowStatus,
        matchedFieldSelection
          BITS,
        aclAction
          INTEGER,
        aclActionParameter
          OCTET STRING,
        matchedSourceMacMask 
MacAddress,
matchedDestinationMacMask
MacAddress,
matchedSourceIPMask
IpAddress,
matchedDestinationIPMask
          IpAddress

       }


    aclRuleListIndex OBJECT-TYPE
      SYNTAX INTEGER
      MAX-ACCESS not-accessible
      STATUS current
      DESCRIPTION
        "
        Rule表acl list索引(基于acl列表已创建的list index)"
      ::= { aclRuleEntry 1 }


    aclRuleIndex OBJECT-TYPE
      SYNTAX INTEGER
      MAX-ACCESS not-accessible
      STATUS current
      DESCRIPTION
        "
        ACL规则索引"
      ::= { aclRuleEntry 2 }

    matchedSourceMac OBJECT-TYPE
      SYNTAX MacAddress
      MAX-ACCESS read-create
      STATUS current
      DESCRIPTION
        "
        匹配的源Mac"
      ::= { aclRuleEntry 3 }

    matchedDestinationMac OBJECT-TYPE
      SYNTAX MacAddress
      MAX-ACCESS read-create
      STATUS current
      DESCRIPTION
        "
        匹配的目的Mac"
      ::= { aclRuleEntry 4 }

    matchedVlanId OBJECT-TYPE
      SYNTAX INTEGER
      MAX-ACCESS read-create
      STATUS current
      DESCRIPTION
        "
        匹配的vlan id"
      ::= { aclRuleEntry 5 }

    matchedEthernetType OBJECT-TYPE
      SYNTAX INTEGER
      MAX-ACCESS read-create
      STATUS current
      DESCRIPTION
        "
        匹配的以太网类型
        It is presented in decimal value for heximal EtherType
        比如ARP(0x0806),十进制值为2054
"
      ::= { aclRuleEntry 6 }

    matchedSourceIP OBJECT-TYPE
      SYNTAX IpAddress
      MAX-ACCESS read-create
      STATUS current
      DESCRIPTION
        "
        匹配的源IP"
      ::= { aclRuleEntry 7 }

    matchedDestinationIP OBJECT-TYPE
      SYNTAX IpAddress
      MAX-ACCESS read-create
      STATUS current
      DESCRIPTION
        "
        匹配的目的IP"
      ::= { aclRuleEntry 8 }
    
    matchedIpMessageType OBJECT-TYPE
      SYNTAX INTEGER (0..255)
      MAX-ACCESS read-create
      STATUS current
      DESCRIPTION
        "
        匹配的IP报文类型"
      ::= { aclRuleEntry 9 }

    matchedDscp OBJECT-TYPE
      SYNTAX INTEGER (0..63)
      MAX-ACCESS read-create
      STATUS current
      DESCRIPTION
        "
        匹配的dscp"
      ::= { aclRuleEntry 10 }    
    matchedSourcePort OBJECT-TYPE
      SYNTAX INTEGER
      MAX-ACCESS read-create
      STATUS current
      DESCRIPTION
        "
        匹配的源端口"
      ::= { aclRuleEntry 11 }
    
    matchedDestinationPort OBJECT-TYPE
      SYNTAX INTEGER
      MAX-ACCESS read-create
      STATUS current
      DESCRIPTION
        "
        匹配的目的端口"
      ::= { aclRuleEntry 12 }

    aclRuleRowStatus OBJECT-TYPE
      SYNTAX RowStatus
      MAX-ACCESS read-create
      STATUS current
      DESCRIPTION
        "
        规则状态"
      ::= { aclRuleEntry 13 }

    matchedFieldSelection OBJECT-TYPE
      SYNTAX BITS
        {
        sourceMac(0),
        destinationMac(1),
        vlanId(2),
        etherType(3),
        sourceIp(4),
        destinationIp(5),
        ipProtocolType(6),
        dscp(7),
        sourceProtocolPort(8),
        destinationProtocolPort(9),
        sourceMacMask(10),
        destinationMacMask(11),
        sourceIpMask(12),
        destinationIpMask(13)

        }
      MAX-ACCESS read-create
      STATUS current
      DESCRIPTION
        "
        选择的匹配域,可以多选"
      ::= { aclRuleEntry 14 }

    aclAction OBJECT-TYPE
      SYNTAX INTEGER
        {
        permit(1),
        deny(2),
        mark(3)
        }
      MAX-ACCESS read-create
      STATUS current
      DESCRIPTION
        "
        ACL规则动作(permit、deny、标记等)"
      ::= { aclRuleEntry 15 }

    aclActionParameter OBJECT-TYPE
      SYNTAX OCTET STRING
      MAX-ACCESS read-create
      STATUS current
      DESCRIPTION
        "
        ACL规则动作参数。只对aclAction为mark(3)有效,对于aclAction其他值,
        此对象禁止配置,get时返回NULL。        
        按照INTERNET顺序从左往右的方向排列,第一个为OCTET0,第n个为OCTET
        [n-1]。        
        OCTET 0 表示 MARK 类型。后面的OCTET 表示这种类型的MARK的目标值,这
        是否这些OCTET的长度取决于MARK类型,比如对应于改MARK类型的参数的SYNTAX
        为INTEGER,则需要4个字节,表示对应的数值。        
        MARK类型    目标值的SYNTAX        描述
        -------------------------------------------------------------------
        0                             Reserved
        1       INTEGER (0..7)      MARK 801.1p的值(外层VLAN)
        2       INTEGER (1..4094)   MARK VLAN ID(外层VLAN)
        3       INTEGER (0..7)      MARK TOS PRECEDENCE
        4       INTEGER (0..63)     MARK DSCP
        5..255                            Reserved        
        比如修改VLAN ID为100,对应的值为：02 00 00 00 64"  
      ::= { aclRuleEntry 16 }



matchedSourceMacMask OBJECT-TYPE
      SYNTAX MacAddress
      MAX-ACCESS read-create
      STATUS current
      DESCRIPTION
        "
        匹配的源Mac 反掩码.
        "
      ::= { aclRuleEntry 17 }
      	

    matchedDestinationMacMask OBJECT-TYPE
      SYNTAX MacAddress
      MAX-ACCESS read-create
      STATUS current
      DESCRIPTION
        "
        匹配的源Mac反掩码.
        "
      ::= { aclRuleEntry 18 }
      
    matchedSourceIPMask OBJECT-TYPE
      SYNTAX IpAddress
      MAX-ACCESS read-create
      STATUS current
      DESCRIPTION
        "
        匹配的源IP反掩码.
        "
      ::= { aclRuleEntry 19 }
      
    matchedDestinationIPMask OBJECT-TYPE
      SYNTAX IpAddress
      MAX-ACCESS read-create
      STATUS current
      DESCRIPTION
        "
        匹配的源IP反掩码.
        "
      ::= { aclRuleEntry 20 }

    portACLListTable OBJECT-TYPE
      SYNTAX SEQUENCE OF PortACLListEntry
      MAX-ACCESS not-accessible
      STATUS current
      DESCRIPTION
        "
        端口ACL列表
        This table applies on OLT pon port, OLT SNI, OLT onu ID, ONU UNI.
        1. If the table is maintained in OLT device(OLT作为SNMP Agent):
        Applied Obj  - Descriptions of Index
        ------------------------------------------------------------------
        OLT Pon Port - OnuNum of aclDeviceIndex shall be set to 0,
        /OLT SNI     aclCardIndex, and aclPortIndex set to 0 indicates
                 meaningless 
        OLT onu ID   - Set aclDeviceIndex to corresponding ONU ID,
                 aclCardIndex, and aclPortIndex set to 0 indicates
                 meaningless        
        ONU UNI    - Set aclDeviceIndex to corresponding ONU ID,
                 aclCardIndex, and aclPortIndex set to the corresponding 
                 value        
        2. If the table is maintained in ONU device(ONU作为SNMP Agent):
        aclDeviceIndex shall be set to 0 to indicate meaningless.
        aclCardIndex shall be set to corresponding slot.
        aclPortIndex shall be set to corresponding port.        
        "
        
      ::= { aclManagementGroup 3 }
    
    portACLListEntry OBJECT-TYPE
      SYNTAX PortACLListEntry
      MAX-ACCESS not-accessible
      STATUS current
      DESCRIPTION     " "
      INDEX { aclDeviceIndex, aclCardIndex, aclPortIndex, portAclListIndex }
      ::= { portACLListTable 1 }
    
    PortACLListEntry ::=
      SEQUENCE { 
        aclDeviceIndex
          EponDeviceIndex,
        aclCardIndex
          EponCardIndex,
        aclPortIndex
          EponPortIndex,
        portAclListIndex 
          INTEGER,
        aclPortDirection
          BITS,
        aclRowStatus
          RowStatus
       }

    aclDeviceIndex OBJECT-TYPE
      SYNTAX EponDeviceIndex
      MAX-ACCESS not-accessible
      STATUS current
      DESCRIPTION
        "
        设备索引号。        
        For OLT Agent, set to corresponding PON port, SNI, or ONU
        For ONU Agent, set to 0
        "
      ::= { portACLListEntry 1 }

    aclCardIndex OBJECT-TYPE
      SYNTAX EponCardIndex
      MAX-ACCESS not-accessible
      STATUS current
      DESCRIPTION
        "
        板卡索引号        
        For OLT Agent, set to 0,
        For ONU Agent, set to corresponding slot
        "
      ::= { portACLListEntry 2 }

    aclPortIndex  OBJECT-TYPE
      SYNTAX EponPortIndex
      MAX-ACCESS not-accessible
      STATUS current
      DESCRIPTION
        "
        端口索引号        
        For OLT Agent, set to 0,
        For ONU Agent, set to corresponding slot
        "
      ::= { portACLListEntry 3 }

    portAclListIndex OBJECT-TYPE
      SYNTAX INTEGER
      MAX-ACCESS not-accessible
      STATUS current
      DESCRIPTION
        "
        端口ACL表索引"
      ::= { portACLListEntry 4 }

    aclPortDirection OBJECT-TYPE
      SYNTAX BITS
        {
        ingress(0),
        egress(1)
        }
      MAX-ACCESS read-create
      STATUS current
      DESCRIPTION
        "
        ACL应用到出口或入口,入口必须实现,出口可选"
      ::= { portACLListEntry 5 }

    aclRowStatus OBJECT-TYPE
      SYNTAX RowStatus
      MAX-ACCESS read-create
      STATUS current
      DESCRIPTION
        "
        ACL应用状态"
      ::= { portACLListEntry 6 }

    ponBroadcastStormSuppressionTable OBJECT-TYPE
      SYNTAX SEQUENCE OF PonBroadcastStormSuppressionEntry
      MAX-ACCESS not-accessible
      STATUS current
      DESCRIPTION
        "
        广播风暴抑制表        
        注：若不支持端口级别的配置,则配置一个端口,同一板卡的所有端口的配置均生效"
      ::= { ponPortObjects 3 }

    ponBroadcastStormSuppressionEntry OBJECT-TYPE
      SYNTAX PonBroadcastStormSuppressionEntry
      MAX-ACCESS not-accessible
      STATUS current
      DESCRIPTION     " "
      INDEX { bsDeviceIndex, bsCardIndex, bsPortIndex }
      ::= { ponBroadcastStormSuppressionTable 1 }

    PonBroadcastStormSuppressionEntry ::=
      SEQUENCE { 
        bsDeviceIndex
          INTEGER,
        bsCardIndex
          EponCardIndex,
        bsPortIndex 
          EponPortIndex,
        unicastStormEnable
          TruthValue,
        unicastStormInPacketRate
          INTEGER,
        unicastStormOutPacketRate
          INTEGER,
        multicastStormEnable
          TruthValue,
        multicastStormInPacketRate
          INTEGER,
        multicastStormOutPacketRate
          INTEGER,
        broadcastStormEnable
          TruthValue,
        broadcastStormInPacketRate
          INTEGER,
        broadcastStormOutPacketRate
          INTEGER
       }

    bsDeviceIndex OBJECT-TYPE
      SYNTAX INTEGER
      MAX-ACCESS not-accessible
      STATUS current
      DESCRIPTION
        "
        OLT设备索引号。        
        一个OLT节点可以由多台OLT设备组成。节点内的每台OLT设备由OLT设备索引号唯一标识"
      ::= { ponBroadcastStormSuppressionEntry 1 }

    bsCardIndex OBJECT-TYPE
      SYNTAX EponCardIndex
      MAX-ACCESS not-accessible
      STATUS current
      DESCRIPTION
        "
        板卡索引号"
      ::= { ponBroadcastStormSuppressionEntry 2 }

    bsPortIndex   OBJECT-TYPE
      SYNTAX EponPortIndex
      MAX-ACCESS not-accessible
      STATUS current
      DESCRIPTION
        "
        pon端口索引号"
      ::= { ponBroadcastStormSuppressionEntry 3 }

    unicastStormEnable OBJECT-TYPE
      SYNTAX TruthValue
      MAX-ACCESS read-write
      STATUS current
      DESCRIPTION
        "
        未知单播风暴抑制使能"
      ::= { ponBroadcastStormSuppressionEntry 4 }

    unicastStormInPacketRate OBJECT-TYPE
      SYNTAX INTEGER
      UNITS "pps"
      MAX-ACCESS read-write
      STATUS current
      DESCRIPTION
        "
        未知单播风暴抑制入口速率"
      ::= { ponBroadcastStormSuppressionEntry 5 }

    unicastStormOutPacketRate OBJECT-TYPE
      SYNTAX INTEGER
      UNITS "pps"
      MAX-ACCESS read-write
      STATUS current
      DESCRIPTION
        "
        未知单播风暴抑制出口速率"
      ::= { ponBroadcastStormSuppressionEntry 6 }

    multicastStormEnable OBJECT-TYPE
      SYNTAX TruthValue
      MAX-ACCESS read-write
      STATUS current
      DESCRIPTION
        "
        组播风暴抑制使能"
      ::= { ponBroadcastStormSuppressionEntry 7 }

    multicastStormInPacketRate OBJECT-TYPE
      SYNTAX INTEGER
      UNITS "pps"
      MAX-ACCESS read-write
      STATUS current
      DESCRIPTION
        "
        组播风暴抑制入口速率"
      ::= { ponBroadcastStormSuppressionEntry 8 }

    multicastStormOutPacketRate OBJECT-TYPE
      SYNTAX INTEGER
      UNITS "pps"
      MAX-ACCESS read-write
      STATUS current
      DESCRIPTION
        "
        组播风暴抑制出口速率"
      ::= { ponBroadcastStormSuppressionEntry 9 }

    broadcastStormEnable OBJECT-TYPE
      SYNTAX TruthValue
      MAX-ACCESS read-write
      STATUS current
      DESCRIPTION
        "
        广播风暴抑制使能"
      ::= { ponBroadcastStormSuppressionEntry 10 }

    broadcastStormInPacketRate OBJECT-TYPE
      SYNTAX INTEGER
      UNITS "pps"
      MAX-ACCESS read-write
      STATUS current
      DESCRIPTION
        "
        广播风暴抑制入口速率"
      ::= { ponBroadcastStormSuppressionEntry 11 }

    broadcastStormOutPacketRate OBJECT-TYPE
      SYNTAX INTEGER
      UNITS "pps"
      MAX-ACCESS read-write
      STATUS current
      DESCRIPTION
        "
        广播风暴抑制出口速率"
      ::= { ponBroadcastStormSuppressionEntry 12 }


ponOnuAuthenticationModeTable OBJECT-TYPE
SYNTAX SEQUENCE OF PonOnuAuthenticationModeEntry
MAX-ACCESS  not-accessible
STATUS  optional
DESCRIPTION
"基于PON口的ONU认证模式表"
::= { ponPortObjects 4 }

ponOnuAuthenticationModeEntry OBJECT-TYPE
SYNTAX PonOnuAuthenticationModeEntry
MAX-ACCESS  not-accessible
STATUS  current
DESCRIPTION 
"The ponOnuAuthenticationModeEntry Information"
INDEX{ ponAuthenDeviceIndex,ponAuthenCardIndex,ponAuthenPortIndex}   
::={ ponOnuAuthenticationModeTable 1 }   

PonOnuAuthenticationModeEntry
::= SEQUENCE {
ponAuthenDeviceIndex 
INTEGER,
ponAuthenCardIndex 
EponCardIndex,
ponAuthenPortIndex 
EponPortIndex,
ponOnuAuthenMode 
INTEGER
} 

ponAuthenDeviceIndex OBJECT-TYPE
SYNTAX  INTEGER
MAX-ACCESS  not-accessible
STATUS  current
DESCRIPTION
    " OLT设备索引号。一个OLT节点可以由多台OLT设备组成。
节点内的每台OLT设备由OLT设备索引号唯一标识"
::= { ponOnuAuthenticationModeEntry 1 } 

ponAuthenCardIndex OBJECT-TYPE
SYNTAX  EponCardIndex
MAX-ACCESS  not-accessible 
STATUS  current
DESCRIPTION
    "板卡索引号"
::= { ponOnuAuthenticationModeEntry 2 }

ponAuthenPortIndex OBJECT-TYPE
SYNTAX  EponPortIndex
MAX-ACCESS  not-accessible 
STATUS  current
DESCRIPTION
    "pon端口索引号"
::= { ponOnuAuthenticationModeEntry 3 }


ponOnuAuthenMode OBJECT-TYPE
SYNTAX  INTEGER {
			logical-ID-and-logical-password(1),
			physics-ID-or-logical-ID-password(2),
			logical-ID(3),
			physics-ID-or-logical-ID-notPassword(4),
			mac(5),
			auto(6)
			}

MAX-ACCESS  read-create 
STATUS  current
DESCRIPTION
    "Authen mode；This is mode in authen ,
注：同一个PON口下的所有ONU只能使用一同认证模式"
::= { ponOnuAuthenticationModeEntry 4 }




ponPortOpticalTransmissionPropertyTable OBJECT-TYPE
SYNTAX SEQUENCE OF PonPortOpticalTransmissionPropertyEntry
MAX-ACCESS not-accessible
STATUS current
DESCRIPTION
"
光端口传输特性表
注：若不支持端口级别的配置,则配置一个端口,同一板卡的所有端口的配置均生效"
::= { ponPortObjects 5 }

ponPortOpticalTransmissionPropertyEntry OBJECT-TYPE
SYNTAX PonPortOpticalTransmissionPropertyEntry
MAX-ACCESS not-accessible
STATUS current
DESCRIPTION " "
INDEX { ponOpDeviceIndex, ponOpCardIndex, ponOpPortIndex }
::= { ponPortOpticalTransmissionPropertyTable 1 }

PonPortOpticalTransmissionPropertyEntry ::=
SEQUENCE {
ponOpDeviceIndex
INTEGER,
ponOpCardIndex
EponCardIndex,
ponOpPortIndex
EponPortIndex,
ponOpVcc
INTEGER,
ponOpBias
INTEGER,
ponOpTxPower
INTEGER
}

ponOpDeviceIndex OBJECT-TYPE
SYNTAX INTEGER
MAX-ACCESS read-only
STATUS current
DESCRIPTION
"
OLT设备索引号。
一个OLT节点可以由多台OLT设备组成。节点内的每台OLT设备由OLT设备索引号唯一标识"
::= { ponPortOpticalTransmissionPropertyEntry 1 }

ponOpCardIndex OBJECT-TYPE
SYNTAX EponCardIndex
MAX-ACCESS read-only
STATUS current
DESCRIPTION
"
板卡索引号。"
::= { ponPortOpticalTransmissionPropertyEntry 2 }

ponOpPortIndex OBJECT-TYPE
SYNTAX EponPortIndex
MAX-ACCESS read-only
STATUS current
DESCRIPTION
"
端口索引号。"
::= { ponPortOpticalTransmissionPropertyEntry 3 }

ponOpVcc OBJECT-TYPE
SYNTAX INTEGER
UNITS "centi-mV"
MAX-ACCESS read-only
STATUS current
DESCRIPTION
"
电压。"
::= { ponPortOpticalTransmissionPropertyEntry 4 }

ponOpBias OBJECT-TYPE
SYNTAX INTEGER
UNITS "centi-mA"
MAX-ACCESS read-only
STATUS current
DESCRIPTION
"
电流。"
::= { ponPortOpticalTransmissionPropertyEntry 5 }

ponOpTxPower OBJECT-TYPE
SYNTAX INTEGER
UNITS "centi-dBm"
MAX-ACCESS read-only
STATUS current
DESCRIPTION
"
发送功率。"
::= { ponPortOpticalTransmissionPropertyEntry 6 }





-- 基于OLT PON口的ONU接收光功率

    ponPortOpticalRxPowerTable OBJECT-TYPE
        SYNTAX   SEQUENCE OF PonPortOpticalRxPowerEntry
        MAX-ACCESS  not-accessible
        STATUS  optional
        DESCRIPTION
        "基于OLT PON口的ONU接收光功率"
                ::= { ponPortObjects 6 }

    ponPortOpticalRxPowerEntry OBJECT-TYPE
        SYNTAX  PonPortOpticalRxPowerEntry
        MAX-ACCESS  not-accessible
        STATUS  current
        DESCRIPTION
        "The ponPortOpticalRxPowerEntry Information"
        INDEX{ ponOpRxOfOnuDeviceIndex}  
                ::={ ponPortOpticalRxPowerTable 1 }  

        PonPortOpticalRxPowerEntry
                ::= SEQUENCE
                {  ponOpRxOfOnuDeviceIndex  EponDeviceIndex,
                   ponOpRxPowerOfOnu INTEGER
                }

    ponOpRxOfOnuDeviceIndex OBJECT-TYPE
SYNTAX      EponDeviceIndex
        MAX-ACCESS  not-accessible
        STATUS      current
        DESCRIPTION
            "onuDevice Index"
        ::= { ponPortOpticalRxPowerEntry 1 }

        ponOpRxPowerOfOnu OBJECT-TYPE
        SYNTAX      INTEGER
        UNITS   "centi-dBm"
        MAX-ACCESS  read-only 
        STATUS      current
        DESCRIPTION
            "OLT pon port received onu optical power"
        ::= { ponPortOpticalRxPowerEntry  2}


--------------------------------------------------------------------------------
--  onuObjects[ONU属性管理项](1.3.6.1.4.1.17409.2.3.4)
--------------------------------------------------------------------------------  
    onuInfoTable  OBJECT-TYPE
        SYNTAX      SEQUENCE OF OnuInfoEntry
        MAX-ACCESS  not-accessible
        STATUS      current
        DESCRIPTION
            "A list of onuInfoTable entries. "
        ::= {onuObjects 1 }
        
    onuInfoEntry  OBJECT-TYPE
        SYNTAX      OnuInfoEntry
        MAX-ACCESS  not-accessible
        STATUS      current
        DESCRIPTION  
            "The onuInfoEntry Information"
        INDEX       { onuDeviceIndex }   
        ::={onuInfoTable 1 }   
        
    OnuInfoEntry ::= SEQUENCE {
        onuDeviceIndex              EponDeviceIndex, 
        onuName                     DisplayString,
        onuType                     INTEGER,
        onuIpAddress                IpAddress,
        onuIpSubnetMask             IpAddress,
        onuIpGateway                IpAddress,
        onuMacAddress               MacAddress,
        onuOperationStatus          INTEGER,
        onuAdminStatus              INTEGER,
        onuChipVendor               DisplayString,
        onuChipType                 DisplayString,
        onuChipVersion              DisplayString,
        onuSoftwareVersion          DisplayString,
        onuFirmwareVersion          DisplayString,
        onuTestDistance             INTEGER,
        onuLlidId                   INTEGER,
        resetONU                    INTEGER,
        onuTimeSinceLastRegister  Counter32,
        onuVendorId DisplayString,
        onuModelId DisplayString,
        onuHardwareVersion DisplayString,
        onuSn DisplayString,
        onuTimeLastRegister DateAndTime

      } 

    onuDeviceIndex  OBJECT-TYPE
        SYNTAX      EponDeviceIndex
        MAX-ACCESS  not-accessible
        STATUS      current
        DESCRIPTION
            "onuDevice Index"
        ::= {onuInfoEntry 1 }        
        
    onuName  OBJECT-TYPE
        SYNTAX      DisplayString
        MAX-ACCESS  read-write 
        STATUS      current
        DESCRIPTION
            "onu Name"
        ::= {onuInfoEntry 2 }   
        
    onuType  OBJECT-TYPE
        SYNTAX      INTEGER
          {
            fixed(1),
            chassisBased(2)
          }
        MAX-ACCESS  read-only 
        STATUS      current
        DESCRIPTION
            "onu Type            
            fixed(1)        - not slot concept
            chassisBased(2) - port is indexed by coupling slot ID"
        ::= {onuInfoEntry 3 }             
   
    onuIpAddress  OBJECT-TYPE
        SYNTAX      IpAddress
        MAX-ACCESS  read-write 
        STATUS      current
        DESCRIPTION
            "onu Ip Address"
        ::= {onuInfoEntry 4 }    
        
    onuIpSubnetMask  OBJECT-TYPE
        SYNTAX      IpAddress
        MAX-ACCESS  read-write 
        STATUS      current
        DESCRIPTION
            "onu Ip Subnet Mask"
        ::= {onuInfoEntry 5 }  
        
    onuIpGateway  OBJECT-TYPE
        SYNTAX      IpAddress
        MAX-ACCESS  read-write 
        STATUS      current
        DESCRIPTION
            "onu Ip Gateway"
        ::= {onuInfoEntry 6 }   
        
    onuMacAddress  OBJECT-TYPE
        SYNTAX      MacAddress
        MAX-ACCESS  read-only 
        STATUS      current
        DESCRIPTION
            "onuMac Address"
        ::= {onuInfoEntry 7 }  
        
    onuOperationStatus  OBJECT-TYPE
        SYNTAX      INTEGER {
        up(1),
        down(2),
        testing(3)
        }
        MAX-ACCESS  read-only 
        STATUS      current
        DESCRIPTION
            "onu Operation Status"
        ::= {onuInfoEntry 8 }   
        
    onuAdminStatus  OBJECT-TYPE
        SYNTAX      INTEGER {
        up(1),
        down(2),
        testing(3)
        }
        MAX-ACCESS  read-write 
        STATUS      current
        DESCRIPTION
            "onu Admin Status,
down(2),不给授权,关闭数据通道"
        ::= {onuInfoEntry 9 }      
        
    onuChipVendor  OBJECT-TYPE
        SYNTAX      DisplayString
        MAX-ACCESS  read-only 
        STATUS      current
        DESCRIPTION
            "onu Chip Vendor"
        ::= {onuInfoEntry 10 }     
        
    onuChipType  OBJECT-TYPE
        SYNTAX      DisplayString
        MAX-ACCESS  read-only 
        STATUS      current
        DESCRIPTION
            "onu Chip Type"
        ::= {onuInfoEntry 11 } 
        
    onuChipVersion  OBJECT-TYPE
        SYNTAX      DisplayString
        MAX-ACCESS  read-only 
        STATUS      current
        DESCRIPTION
            "onu Chip Version"
        ::= {onuInfoEntry 12 }   
        
    onuSoftwareVersion  OBJECT-TYPE
        SYNTAX      DisplayString
        MAX-ACCESS  read-only 
        STATUS      current
        DESCRIPTION
            "onu Software Version"
        ::= {onuInfoEntry 13 }    
        
    onuFirmwareVersion  OBJECT-TYPE
        SYNTAX      DisplayString
        MAX-ACCESS  read-only 
        STATUS      current
        DESCRIPTION
            "onu Firmware Version"
        ::= {onuInfoEntry 14 }     
     
    onuTestDistance  OBJECT-TYPE
        SYNTAX      INTEGER
        UNITS   "Meter"
        MAX-ACCESS  read-only 
        STATUS      current
        DESCRIPTION
            "onu Test Distance"
        ::= {onuInfoEntry 15 }  
        
    onuLlidId  OBJECT-TYPE
        SYNTAX      INTEGER
        MAX-ACCESS  read-only 
        STATUS      current
        DESCRIPTION
            "onu Llid Id"
        ::= {onuInfoEntry 16 }     
        
    resetONU  OBJECT-TYPE
        SYNTAX      INTEGER { reset(1) }
        MAX-ACCESS  read-write 
        STATUS      current
        DESCRIPTION
            "reset ONU"
        ::= {onuInfoEntry 17 }   
    
    onuTimeSinceLastRegister  OBJECT-TYPE
        SYNTAX      Counter32
        UNITS   "seconds"
        MAX-ACCESS  read-only 
        STATUS      current
        DESCRIPTION
            "The number of seconds, since the time when the ONU is registered"
        ::= {onuInfoEntry 18 }        

           

onuVendorId OBJECT-TYPE
SYNTAX DisplayString
MAX-ACCESS read-only
STATUS current
DESCRIPTION
"ONU vendor id."
::= {onuInfoEntry 25 }


onuModelId OBJECT-TYPE
SYNTAX DisplayString
MAX-ACCESS read-only
STATUS current
DESCRIPTION
"ONU model id."
::= {onuInfoEntry 26 }

onuHardwareVersion OBJECT-TYPE
SYNTAX DisplayString
MAX-ACCESS read-only
STATUS current
DESCRIPTION
"ONU hardware version."
::= {onuInfoEntry 27 }

onuSn OBJECT-TYPE
SYNTAX DisplayString
MAX-ACCESS read-only
STATUS current
DESCRIPTION
"ONU serial number."
::= {onuInfoEntry 28 }

    onuTimeLastRegister OBJECT-TYPE
        SYNTAX      DateAndTime
        MAX-ACCESS  read-only
        STATUS      current
        DESCRIPTION
            " ONU最后注册时间 "
        ::= {onuInfoEntry 29 }




    onuPonPortOpticalTransmissionPropertyTable  OBJECT-TYPE
        SYNTAX      SEQUENCE OF OnuPonPortOpticalTransmissionPropertyEntry
        MAX-ACCESS  not-accessible
        STATUS      current
        DESCRIPTION
            "
            This table is designed for both OLT and ONU 
        Applied Obj  - Descriptions of Index
      ------------------------------------------------------------------
        OLT      - OnuNum of EponDeviceIndex TC shall be set to 0,
                 onuPonPortOpticalTransmissionPropertyCardIndex, and 
                 onuPonPortOpticalTransmissionPropertyPortIndex set to 
                 65535 indicates meaningless
        ONU      - Set EponDeviceIndex TC to corresponding ONU ID,
                   onuPonPortOpticalTransmissionPropertyCardIndex, and 
                   onuPonPortOpticalTransmissionPropertyPortIndex set to the 
                   corresponding value
      "
        ::= {onuObjects 2 }
        
    onuPonPortOpticalTransmissionPropertyEntry  OBJECT-TYPE
        SYNTAX      OnuPonPortOpticalTransmissionPropertyEntry
        MAX-ACCESS  not-accessible
        STATUS      current
        DESCRIPTION  
            "The onuPonPortOpticalTransmissionPropertyEntry Information"
        INDEX       { onuPonPortOpticalTransmissionPropertyDeviceIndex, onuPonPortOpticalTransmissionPropertyCardIndex,onuPonPortOpticalTransmissionPropertyPortIndex }   
        ::={onuPonPortOpticalTransmissionPropertyTable 1 }   
        
    OnuPonPortOpticalTransmissionPropertyEntry ::= SEQUENCE {
        onuPonPortOpticalTransmissionPropertyDeviceIndex     EponDeviceIndex,  
        onuPonPortOpticalTransmissionPropertyCardIndex       INTEGER,
        onuPonPortOpticalTransmissionPropertyPortIndex       INTEGER,        
        onuReceivedOpticalPower                              INTEGER,
        onuTramsmittedOpticalPower                           INTEGER,
        onuBiasCurrent                                       INTEGER,
        onuWorkingVoltage                                    INTEGER,
        onuWorkingTemperature                                INTEGER     
      } 

    onuPonPortOpticalTransmissionPropertyDeviceIndex  OBJECT-TYPE
        SYNTAX      EponDeviceIndex
        MAX-ACCESS  not-accessible
        STATUS      current
        DESCRIPTION
            "Device Index of the ONU."
        ::= {onuPonPortOpticalTransmissionPropertyEntry 1 }      
 
     onuPonPortOpticalTransmissionPropertyCardIndex  OBJECT-TYPE
        SYNTAX      INTEGER
        MAX-ACCESS  not-accessible
        STATUS      current
        DESCRIPTION
            "Card Index in the ONU. Shall set to 0, if ONU is not a modulized 
            device"
        ::= {onuPonPortOpticalTransmissionPropertyEntry 2 }  
        
    onuPonPortOpticalTransmissionPropertyPortIndex  OBJECT-TYPE
        SYNTAX      INTEGER
        MAX-ACCESS  not-accessible
        STATUS      current
        DESCRIPTION
            "Port Index in the Pon card of ONU"
        ::= {onuPonPortOpticalTransmissionPropertyEntry 3 }          
    onuReceivedOpticalPower  OBJECT-TYPE
        SYNTAX      INTEGER
        UNITS   "centi-dBm"
        MAX-ACCESS  read-only 
        STATUS      current
        DESCRIPTION
            "received Optical Power"
        ::= {onuPonPortOpticalTransmissionPropertyEntry 4 }    
        
    onuTramsmittedOpticalPower  OBJECT-TYPE
        SYNTAX      INTEGER
        UNITS   "centi-dBm"
        MAX-ACCESS  read-only 
        STATUS      current
        DESCRIPTION
            "tramsmitted Optical Power"
        ::= {onuPonPortOpticalTransmissionPropertyEntry 5 }               
        
    onuBiasCurrent  OBJECT-TYPE
        SYNTAX      INTEGER
        UNITS   "centi-mA"
        MAX-ACCESS  read-only 
        STATUS      current
        DESCRIPTION
            "biasCurrent"
        ::= {onuPonPortOpticalTransmissionPropertyEntry 6 }  

    onuWorkingVoltage  OBJECT-TYPE
        SYNTAX      INTEGER
        UNITS   "centi-mV"
        MAX-ACCESS  read-only 
        STATUS      current
        DESCRIPTION
            "onuworking Voltage"
        ::= {onuPonPortOpticalTransmissionPropertyEntry 7 }  
        
    onuWorkingTemperature  OBJECT-TYPE
        SYNTAX      INTEGER
        UNITS   "Centi-degree centigrade"
       MAX-ACCESS  read-only 
        STATUS      current
        DESCRIPTION
            "working Temperature"
        ::= {onuPonPortOpticalTransmissionPropertyEntry 8 } 
          
    onuCapabilityTable  OBJECT-TYPE
        SYNTAX      SEQUENCE OF OnuCapabilityEntry
        MAX-ACCESS  not-accessible
        STATUS      current
        DESCRIPTION
            "A list of onuInfoTable entries. "
        ::= {onuObjects 3 }
        
    onuCapabilityEntry  OBJECT-TYPE
        SYNTAX      OnuCapabilityEntry
        MAX-ACCESS  not-accessible
        STATUS      current
        DESCRIPTION  
            "The onuCapabilityEntry Information"
        INDEX       { onuCapabilityDeviceIndex }   
        ::={onuCapabilityTable 1 }   
        
    OnuCapabilityEntry ::= SEQUENCE {   
        onuCapabilityDeviceIndex     EponDeviceIndex,   
        onuGePortNum                 INTEGER,
        onuGePortBitmap              OCTET STRING,
        onuFePortNum                 INTEGER,
        onuFePortBitmap              OCTET STRING,
        onuQueueNumUplink            INTEGER,    
        onuMaxQueueNumUplink         INTEGER,    
        onuQueueNumDownlink          INTEGER,    
        onuMaxQueueNumDownlink       INTEGER,    
        onuFecEnable                 TruthValue,    
        onuEncryptMode               INTEGER,    
        onuEncryptKeyExchangeTime    TimeTicks,
        onuIsolationEnable           TruthValue    
      } 
       
    onuCapabilityDeviceIndex  OBJECT-TYPE
        SYNTAX      EponDeviceIndex
        MAX-ACCESS  not-accessible
        STATUS      current
        DESCRIPTION
            "onu Device Index"
        ::= {onuCapabilityEntry 1 }   
        
    onuGePortNum  OBJECT-TYPE
        SYNTAX      INTEGER
        MAX-ACCESS  read-only 
        STATUS      current
        DESCRIPTION
            "gePort Num"
        ::= {onuCapabilityEntry 2 }    

    onuGePortBitmap  OBJECT-TYPE
        SYNTAX      OCTET STRING
        MAX-ACCESS  read-only 
        STATUS      current
        DESCRIPTION
            "gePort Bitmap
            
            In slot+port pair list manner. Suppose each slot support up to 64 ports.
            One octet to indentify slot and 8 octets to identify portbitmap for
            the slot. The bitmap definition is internet sequence. The most left bit 
            is for port 1 of the slot, the most right bit is for port 64 of the slot.            
            If the slot cannot support 64 ports, set the bits of not supported ports
            to 0.            
            If the port is GE port, set the corresponding bit to 1.                 
            Since the slot num depends on each individual device, the object is variable
            length. If the device is fixed box (not modulized), set the slot number to 
            255. Then the network management system could ignore the slot info.            
            It is not necessary to list the slot doesn't support GE port.                        
            For example, if have 4 GE ports, of: 1/4, 1/6, 2/3, 4/17,
            the object will be presented in:
            01 14 00 00 00 00 00 00 00
            02 20 00 00 00 00 00 00 00
            04 00 00 80 00 00 00 00 00            
            Another example, for fixed box, if have 4 ge ports of 4,6,10,17, the object
            will be presented as:
            FF 14 40 10 00 00 00 00
            "
        ::= {onuCapabilityEntry 3 }  
        
    onuFePortNum  OBJECT-TYPE
        SYNTAX      INTEGER
        MAX-ACCESS  read-only 
        STATUS      current
        DESCRIPTION
            "fePort Num"
        ::= {onuCapabilityEntry 4 }    
        
    onuFePortBitmap  OBJECT-TYPE
        SYNTAX      OCTET STRING
        MAX-ACCESS  read-only 
        STATUS      current
        DESCRIPTION
            "fePort Bitmap
            
            In slot+port pair list manner. Suppose each slot support up to 64 ports.
            One octet to indentify slot and 8 octets to identify portbitmap for
            the slot. The bitmap definition is internet sequence. The most left bit 
            is for port 1 of the slot, the most right bit is for port 64 of the slot.            
            If the slot cannot support 64 ports, set the bits of not supported ports
            to 0.            
            If the port is FE port, set the corresponding bit to 1.                 
            Since the slot num depends on each individual device, the object is variable
            length. If the device is fixed box (not modulized), set the slot number to 
            255. Then the network management system could ignore the slot info.            
            It is not necessary to list the slot doesn't support FE port.                        
            For example, if have 4 FE ports, of: 1/4, 1/6, 2/3, 4/17,
            the object will be presented in:
            01 14 00 00 00 00 00 00 00
            02 20 00 00 00 00 00 00 00
            04 00 00 80 00 00 00 00 00            
            Another example, for fixed box, if have 4 FE ports of 4,6,10,17, the object
            will be presented as:
            FF 14 40 10 00 00 00 00
            "
        ::= {onuCapabilityEntry 5 }     
        
    onuQueueNumUplink  OBJECT-TYPE
        SYNTAX      INTEGER
        MAX-ACCESS  read-only 
        STATUS      current
        DESCRIPTION
            "queue Num Uplink"
        ::= {onuCapabilityEntry 6 }     
        
    onuMaxQueueNumUplink  OBJECT-TYPE
        SYNTAX      INTEGER
        MAX-ACCESS  read-only 
        STATUS      current
        DESCRIPTION
            "max Queue Num Uplink"
        ::= {onuCapabilityEntry 7 }  
        
    onuQueueNumDownlink  OBJECT-TYPE
        SYNTAX      INTEGER
        MAX-ACCESS  read-only 
        STATUS      current
        DESCRIPTION
            "queue Num Downlink"
        ::= {onuCapabilityEntry 8 }  
        
    onuMaxQueueNumDownlink  OBJECT-TYPE
        SYNTAX      INTEGER
        MAX-ACCESS  read-only 
        STATUS      current
        DESCRIPTION
            "max Queue Num Downlink"
        ::= {onuCapabilityEntry 9 }    
        
     onuFecEnable  OBJECT-TYPE
        SYNTAX      TruthValue
        MAX-ACCESS  read-write 
        STATUS      current
        DESCRIPTION
            "fec Enable"
        ::= {onuCapabilityEntry 10 }  
        
    onuEncryptMode  OBJECT-TYPE
        SYNTAX      INTEGER {
                aes128(1),
                ctcTripleChurning(2),
                other(3)
                       }
        MAX-ACCESS  read-only 
        STATUS      current
        DESCRIPTION
            "encrypt Mode"
        ::= {onuCapabilityEntry 11 }    
        
    onuEncryptKeyExchangeTime  OBJECT-TYPE
        SYNTAX      TimeTicks
        MAX-ACCESS  read-only 
        STATUS      current
        DESCRIPTION
            "encryptKeyExchange Time"
        ::= {onuCapabilityEntry 12 }                                                                                                    

    onuIsolationEnable  OBJECT-TYPE
        SYNTAX      TruthValue    
        MAX-ACCESS  read-write
        STATUS      current
        DESCRIPTION
            "
ONU端口隔离使能
true(1) false(2)"
        ::= { onuCapabilityEntry  13 }


    slaTable  OBJECT-TYPE
        SYNTAX      SEQUENCE OF SlaEntry
        MAX-ACCESS  not-accessible
        STATUS      current
        DESCRIPTION
            "A list of slaTable entries. "
        ::= {onuObjects 4 }
        
    slaEntry  OBJECT-TYPE
        SYNTAX      SlaEntry
        MAX-ACCESS  not-accessible
        STATUS      current
        DESCRIPTION  
            "The slaEntry Information"
        INDEX       { slaIndex }   
        ::={slaTable 1 }   
        
    SlaEntry ::= SEQUENCE {
        slaIndex               EponDeviceIndex,  
        slaDsFixedBW             INTEGER,
        slaDsPeakBW              INTEGER,
        slaDsCommittedBW         INTEGER,  
        slaUsFixedBW             INTEGER,
        slaUsPeakBW              INTEGER,
        slaUsCommittedBW         INTEGER              
      } 
     
    slaIndex  OBJECT-TYPE
        SYNTAX      EponDeviceIndex
        MAX-ACCESS  not-accessible
        STATUS      current
        DESCRIPTION
            "sla Index"
        ::= {slaEntry 1 }  
         
    slaDsFixedBW  OBJECT-TYPE
        SYNTAX      INTEGER
        UNITS   "kbps"
        MAX-ACCESS  read-write 
        STATUS      current
        DESCRIPTION
            "Downstream sla FixedBW"
        ::= {slaEntry 2 }  
        
    slaDsPeakBW  OBJECT-TYPE
        SYNTAX      INTEGER
        UNITS   "kbps"
        MAX-ACCESS  read-write 
        STATUS      current
        DESCRIPTION
            "Downstream sla PeakBW"
        ::= {slaEntry 3 }    
        
    slaDsCommittedBW  OBJECT-TYPE
        SYNTAX      INTEGER
        UNITS   "kbps"
        MAX-ACCESS  read-write 
        STATUS      current
        DESCRIPTION
            "Downstream sla CommittedBW"
        ::= {slaEntry 4 }                               
 
    slaUsFixedBW  OBJECT-TYPE
        SYNTAX      INTEGER
        UNITS   "kbps"
        MAX-ACCESS  read-write 
        STATUS      current
        DESCRIPTION
            "Upstream sla FixedBW"
        ::= {slaEntry 5 }  
        
    slaUsPeakBW  OBJECT-TYPE
        SYNTAX      INTEGER
        UNITS   "kbps"
        MAX-ACCESS  read-write 
        STATUS      current
        DESCRIPTION
            "Upstream sla PeakBW"
        ::= {slaEntry 6 }    
        
    slaUsCommittedBW  OBJECT-TYPE
        SYNTAX      INTEGER
        UNITS   "kbps"
        MAX-ACCESS  read-write 
        STATUS      current
        DESCRIPTION
            "Upstream sla CommittedBW"
        ::= {slaEntry 7 }
        

  onuAuthenticationManagement OBJECT-IDENTITY
    STATUS current
    DESCRIPTION 
      "ONU认证管理"
    ::= { onuObjects 5 }

          
        
    onuAuthenticationConfigTable  OBJECT-TYPE
        SYNTAX      SEQUENCE OF OnuAuthenticationConfigEntry
        MAX-ACCESS  not-accessible
        STATUS      current
        DESCRIPTION
            "A list of onuAuthenticationConfigTable entries. "
        ::= {onuAuthenticationManagement 2 }
        
    onuAuthenticationConfigEntry  OBJECT-TYPE
        SYNTAX      OnuAuthenticationConfigEntry
        MAX-ACCESS  not-accessible
        STATUS      current
        DESCRIPTION  
            "The onuAuthenticationConfigEntry Information"
        INDEX       { onuAuthenOnuId }   
        ::={onuAuthenticationConfigTable 1 }   
        
    OnuAuthenticationConfigEntry ::= SEQUENCE {
        onuAuthenOnuId                            EponDeviceIndex,  
        onuAuthenMacAddress                       MacAddress,
        onuAuthenRowStatus                        INTEGER
      } 
         

    onuAuthenOnuId  OBJECT-TYPE
        SYNTAX      EponDeviceIndex
        MAX-ACCESS  not-accessible
        STATUS      current
        DESCRIPTION
            "onu logical ID"
        ::= {onuAuthenticationConfigEntry 1 } 

    onuAuthenMacAddress  OBJECT-TYPE
        SYNTAX      MacAddress
        MAX-ACCESS  read-create 
        STATUS      current
        DESCRIPTION
            "onu Mac Address"
        ::= {onuAuthenticationConfigEntry 2 }   

    onuAuthenRowStatus  OBJECT-TYPE
        SYNTAX      RowStatus
        MAX-ACCESS  read-create 
        STATUS      current
        DESCRIPTION
            "authen Row Status"
        ::= {onuAuthenticationConfigEntry 4 }
    
    -- 黑名单表
    onuAuthenticationBlockTable  OBJECT-TYPE
        SYNTAX      SEQUENCE OF OnuAuthenticationBlockEntry
        MAX-ACCESS  not-accessible
        STATUS      current
        DESCRIPTION
            "A list of onuAuthenticationBlockTable entries. "
        ::= {onuAuthenticationManagement 3 }
        
    onuAuthenticationBlockEntry  OBJECT-TYPE
        SYNTAX      OnuAuthenticationBlockEntry
        MAX-ACCESS  not-accessible
        STATUS      current
        DESCRIPTION  
            "The onuAuthenticationBlockEntry Information"
        INDEX       { onuAuthenBlockOnuId }   
        ::={onuAuthenticationBlockTable 1 }   
        
    OnuAuthenticationBlockEntry ::= SEQUENCE {
        onuAuthenBlockOnuId                   EponDeviceIndex,
        onuAuthenBlockMacAddress              MacAddress,
        authenBlockTime                       TimeTicks,
        onuAuthenBlockRowStatus               RowStatus
      }    
        
       
    onuAuthenBlockOnuId  OBJECT-TYPE
        SYNTAX      EponDeviceIndex
        MAX-ACCESS  not-accessible
        STATUS      current
        DESCRIPTION
            "ONU Id"
        ::= {onuAuthenticationBlockEntry 1 }   
        
    onuAuthenBlockMacAddress  OBJECT-TYPE
        SYNTAX      MacAddress
        MAX-ACCESS  read-create
        STATUS      current
        DESCRIPTION
            "Mac Address"
        ::= {onuAuthenticationBlockEntry 2 }  
        
    authenBlockTime  OBJECT-TYPE
        SYNTAX      TimeTicks
        MAX-ACCESS  read-create
        STATUS      current
        DESCRIPTION
            "加入黑名单时间"
        ::= {onuAuthenticationBlockEntry 3 }   

    onuAuthenBlockRowStatus  OBJECT-TYPE
        SYNTAX      RowStatus
        MAX-ACCESS  read-create 
        STATUS      current
        DESCRIPTION
            " Row Status"
        ::= { onuAuthenticationBlockEntry 4 }
   

    -- onu loid认证表
    onuLoidAuthenticationConfigTable  OBJECT-TYPE
        SYNTAX      SEQUENCE OF OnuLoidAuthenticationConfigEntry
        MAX-ACCESS  not-accessible
        STATUS      current
        DESCRIPTION
            "A list of onu LOID AuthenticationConfigTable entries. "
        ::= {onuAuthenticationManagement 4 }
        
    onuLoidAuthenticationConfigEntry  OBJECT-TYPE
        SYNTAX      OnuLoidAuthenticationConfigEntry
        MAX-ACCESS  not-accessible
        STATUS      current
        DESCRIPTION  
            "The onuLoidAuthenticationConfigEntryInformation"
        INDEX       { onuLoidAuthenOnuId}   
        ::={ onuLoidAuthenticationConfigTable   1 }   
        
    OnuLoidAuthenticationConfigEntry  ::= SEQUENCE {
        onuLoidAuthenOnuId                        EponDeviceIndex,  
        onuLoidAuthenLOID                             OCTET STRING,
        onuLoidAuthenPassword                         OCTET STRING,
        onuLoidAuthenRowStatus                        RowStatus
      } 
         

    onuLoidAuthenOnuId  OBJECT-TYPE
        SYNTAX      EponDeviceIndex
        MAX-ACCESS  not-accessible
        STATUS      current
        DESCRIPTION
            "onu logical ID"
        ::= { onuLoidAuthenticationConfigEntry  1 } 


    onuLoidAuthenLOID OBJECT-TYPE
         SYNTAX  OCTET STRING(SIZE(1..24))
         MAX-ACCESS  read-create
         STATUS  current
         DESCRIPTION
                    " ONU认证逻辑标识 "
         ::= { onuLoidAuthenticationConfigEntry  2 }

    onuLoidAuthenPassword OBJECT-TYPE
         SYNTAX  OCTET STRING(SIZE(0..12))
         MAX-ACCESS  read-create
         STATUS  current
         DESCRIPTION
         "密码为0～12位的字符串,如356abc,当位数为0的时候,表示没有密码"
         ::= { onuLoidAuthenticationConfigEntry  3 }


     onuLoidAuthenRowStatus OBJECT-TYPE
          SYNTAX  RowStatus
          MAX-ACCESS  read-create
          STATUS  current
          DESCRIPTION
          " Row Status"
          ::= { onuLoidAuthenticationConfigEntry  4 }

 
    -- ONU 自动上线表(上线未进行认证的ONU列表)

    onuAutoFindTable  OBJECT-TYPE
        SYNTAX      SEQUENCE OF OnuAutoFindEntry
        MAX-ACCESS  not-accessible
        STATUS      current
        DESCRIPTION
            "A list of autofind list entries. "
        ::= { onuObjects 6 }
        
    onuAutoFindEntry   OBJECT-TYPE
        SYNTAX      OnuAutoFindEntry  
        MAX-ACCESS  not-accessible
        STATUS      current
        DESCRIPTION  
            "The onuAutoFindEntry  Information
自动上电上线的未授权的ONU,全部只读,不做配置"
        INDEX       { onuAutoFindOnuIndex  }   
        ::={ onuAutoFindTable  1 }   
        
    OnuAutoFindEntry  ::= SEQUENCE {
        onuAutoFindOnuIndex	               EponDeviceIndex,
        onuAutoFindMacAddress	             MacAddress,
        onuAutoFindTime	                   TimeTicks,     
        onuAutoFindAuthenLOID             OCTET STRING,
		onuAutoFindAuthenPassword         OCTET STRING
              }    
        
       
    onuAutoFindOnuIndex  OBJECT-TYPE
        SYNTAX      EponDeviceIndex
        MAX-ACCESS  not-accessible
        STATUS      current
        DESCRIPTION
            "index "
        ::= { onuAutoFindEntry   1 }   
        
    onuAutoFindMacAddress  OBJECT-TYPE
        SYNTAX      MacAddress
        MAX-ACCESS  read-only
        STATUS      current
        DESCRIPTION
            "Mac Address"
        ::= { onuAutoFindEntry   2 }  
        
    onuAutoFindTime  OBJECT-TYPE
        SYNTAX      TimeTicks
        MAX-ACCESS  read-only
        STATUS      current
        DESCRIPTION
            "上线时间"
        ::= { onuAutoFindEntry   3 }   


    onuAutoFindAuthenLOID  OBJECT-TYPE
         SYNTAX  OCTET STRING(SIZE(1..24))
         MAX-ACCESS  read-only
         STATUS  current
         DESCRIPTION
            " ONU认证逻辑标识；
              当位数为0的时候,表示没有 "
         ::= { onuAutoFindEntry   4  }

    onuAutoFindAuthenPassword   OBJECT-TYPE
         SYNTAX  OCTET STRING(SIZE(0..12))
         MAX-ACCESS  read-only
         STATUS  current
         DESCRIPTION
         " 密码为0～12位的字符串,如356abc,当位数为0的时候,表示没有密码"
        ::= { onuAutoFindEntry  5 }

--------------------------------------------------------------------------------
--  uniObjects[UNI用户端口属性管理项](1.3.6.1.4.1.17409.2.3.5)
-------------------------------------------------------------------------------- 

 uniAttributeTable  OBJECT-TYPE
        SYNTAX      SEQUENCE OF UniAttributeEntry
        MAX-ACCESS  not-accessible
        STATUS      current
        DESCRIPTION
            "A list of uniAttributeTable entries."
        ::= {uniObjects 1 }
        
    uniAttributeEntry  OBJECT-TYPE
        SYNTAX      UniAttributeEntry
        MAX-ACCESS  not-accessible
        STATUS      current
        DESCRIPTION  
            "The uniAttributeEntry Information"
        INDEX       { uniAttributeDeviceIndex, uniAttributeCardIndex,uniAttributePortIndex }   
        ::={uniAttributeTable 1 }   
        
    UniAttributeEntry ::= SEQUENCE {
        uniAttributeDeviceIndex              EponDeviceIndex,  
        uniAttributeCardIndex                EponCardIndex,
        uniAttributePortIndex                EponPortIndex,         
        uniAdminStatus              INTEGER,
        uniOperationStatus          INTEGER,
        uniAutoNegotiationEnable    TruthValue,
        uniAutoNegotiationLocalTechAbility      AutoNegotiationTechAbility,
        uniAutoNegotiationRestart   INTEGER,
        uniMacAddrLearnMaxNum       INTEGER,
uniCurrentPerfStatsEnable   TruthValue

      } 

    uniAttributeDeviceIndex  OBJECT-TYPE
        SYNTAX      EponDeviceIndex
        MAX-ACCESS  not-accessible
        STATUS      current
        DESCRIPTION
            "Device Index
            
            For OLT Agent, set to corresponding ONU ID
            For ONU Agent, set to 0
            "
        ::= {uniAttributeEntry 1 }      
        
    uniAttributeCardIndex  OBJECT-TYPE
        SYNTAX      EponCardIndex
        MAX-ACCESS  not-accessible
        STATUS      current
        DESCRIPTION
            "Card Index            
            The value of this cardIndex depends on onuType.            
      fixed(1)        - set to 0, to indicate slot num is meaningless.
      chassisBased(2) - MUST NOT be zero            
            "
        ::= {uniAttributeEntry 2 }  
        
    uniAttributePortIndex  OBJECT-TYPE
        SYNTAX      EponPortIndex
        MAX-ACCESS  not-accessible
        STATUS      current
        DESCRIPTION
            "Port Index"
        ::= {uniAttributeEntry 3 }     
        
    uniAdminStatus  OBJECT-TYPE
        SYNTAX      INTEGER {
            up(1),    
            down(2),
            testing(3)
            }      
        MAX-ACCESS  read-write
        STATUS      current
        DESCRIPTION
            "Admin Status"
        ::= {uniAttributeEntry 4 }     

    uniOperationStatus  OBJECT-TYPE
        SYNTAX  INTEGER {
            up(1), 
            down(2),
            testing(3)
            }     
        MAX-ACCESS  read-only
        STATUS      current
        DESCRIPTION
            "Operation Status"
        ::= {uniAttributeEntry 5 }    

    uniAutoNegotiationEnable  OBJECT-TYPE
        SYNTAX      TruthValue
        MAX-ACCESS  read-write
        STATUS      current
        DESCRIPTION
            "Whether or not to enable auto negotiation on the uni port"
        ::= {uniAttributeEntry 6 }

    uniAutoNegotiationLocalTechAbility  OBJECT-TYPE
        SYNTAX      AutoNegotiationTechAbility
        MAX-ACCESS  read-only
        STATUS      current
        DESCRIPTION
            "This indicates the technology ability of the local device"
        ::= {uniAttributeEntry 7 }

    uniAutoNegotiationRestart OBJECT-TYPE 
        SYNTAX      INTEGER {
            restart(1)
            }        
        MAX-ACCESS  read-write
        STATUS      current
        DESCRIPTION
            "Restart the autonegotiation"
        ::= {uniAttributeEntry 8 }
 
        
                
    uniMacAddrLearnMaxNum  OBJECT-TYPE
        SYNTAX      INTEGER
        MAX-ACCESS  read-write
        STATUS      current
        DESCRIPTION
            "Mac Address Learn Max Num"
        ::= { uniAttributeEntry  9 }       

    uniCurrentPerfStatsEnable   OBJECT-TYPE
        SYNTAX      TruthValue  
        MAX-ACCESS  read-write
        STATUS      current
        DESCRIPTION
            "true(1) false(2)"
        ::= { uniAttributeEntry  10 }



   uniMacAddressManagement OBJECT-IDENTITY
    STATUS current
    DESCRIPTION 
      ""
    ::= { uniObjects 2 } 

    -- uniMacAddressManagementTable  OBJECT-IDENTITY
    --    STATUS      current
    --    DESCRIPTION  
    --        " MacAddressManagement global parameters in a onu. "
    --    ::= { uniMacAddressManagement 1 }



    uniMacAddressManagementTable  OBJECT-TYPE
        SYNTAX  SEQUENCE OF UniMacAddressManagementEntry
        MAX-ACCESS  not-accessible
        STATUS      current
        DESCRIPTION
            "A list of MacAddress global parameter in a onu."
        ::= { uniMacAddressManagement 1 }

    uniMacAddressManagementEntry  OBJECT-TYPE
        SYNTAX      UniMacAddressManagementEntry
        MAX-ACCESS  not-accessible
        STATUS      current
        DESCRIPTION
            " "
        INDEX   { uniMacAddrONUIndex }
        ::= { uniMacAddressManagementTable 1 }


    UniMacAddressManagementEntry::=
        SEQUENCE {
        uniMacAddrONUIndex   EponDeviceIndex,
        uniMacAddrAgingTime   INTEGER,
        uniMacAddrClear      INTEGER   
        }


    uniMacAddrONUIndex   OBJECT-TYPE
  SYNTAX      EponDeviceIndex
        MAX-ACCESS  not-accessible
        STATUS      current
        DESCRIPTION
            "onuDevice Index"
        ::= { uniMacAddressManagementEntry 1 }



    uniMacAddrAgingTime   OBJECT-TYPE
        SYNTAX      INTEGER
        UNITS   "Seconds" 
        MAX-ACCESS  read-write
        STATUS      current
        DESCRIPTION
            "Mac Address Table Aging Time"
        ::= { uniMacAddressManagementEntry 2 }

    uniMacAddrClear OBJECT-TYPE
        SYNTAX      INTEGER { allDynamic(1) }
        MAX-ACCESS  read-write
        STATUS      current
        DESCRIPTION
            "Mac Address Table Clear"
        ::= { uniMacAddressManagementEntry 3 }

                   
       
                     
    uniPortRateLimitTable OBJECT-TYPE
        SYNTAX      SEQUENCE OF UniPortRateLimitEntry
        MAX-ACCESS  not-accessible
        STATUS      current
        DESCRIPTION
            "A list of PortRateLimit entries."
        ::= { uniObjects 4 }

    uniPortRateLimitEntry OBJECT-TYPE
        SYNTAX      UniPortRateLimitEntry
        MAX-ACCESS  not-accessible
        STATUS      current
        DESCRIPTION
            "The Port Rate Limit Information"
        INDEX       { uniPortRateLimitDeviceIndex, uniPortRateLimitCardIndex, uniPortRateLimitPortIndex }
        ::= { uniPortRateLimitTable 1 }

    UniPortRateLimitEntry ::=
        SEQUENCE {
            uniPortRateLimitDeviceIndex  EponDeviceIndex,
            uniPortRateLimitCardIndex    EponCardIndex,
            uniPortRateLimitPortIndex    EponPortIndex,
            uniPortInCIR    INTEGER,
            uniPortInCBS    INTEGER,
            uniPortInEBS    INTEGER,      
            uniPortOutCIR   INTEGER,
            uniPortOutPIR   INTEGER,
            uniPortInRateLimitEnable  TruthValue,
            uniPortOutRateLimitEnable TruthValue
            }
    uniPortRateLimitDeviceIndex OBJECT-TYPE
        SYNTAX      EponDeviceIndex
        MAX-ACCESS  not-accessible
        STATUS      current
        DESCRIPTION
            "device Index
            
            For OLT Agent, set to corresponding ONU ID
            For ONU Agent, set to 0
            "
        ::= { uniPortRateLimitEntry 1 }

    uniPortRateLimitCardIndex OBJECT-TYPE
        SYNTAX      EponCardIndex
        MAX-ACCESS  not-accessible
        STATUS      current
        DESCRIPTION
            "card Index            
            The value of this cardIndex depends on onuType.            
      fixed(1)        - set to 0, to indicate slot num is meaningless.
      chassisBased(2) - MUST NOT be zero 
            "
        ::= { uniPortRateLimitEntry 2 }   

    uniPortRateLimitPortIndex OBJECT-TYPE
        SYNTAX      EponPortIndex
        MAX-ACCESS  not-accessible
        STATUS      current
        DESCRIPTION
            "port Index"
        ::= { uniPortRateLimitEntry 3 }
           
    uniPortInCIR OBJECT-TYPE
        SYNTAX      INTEGER
        UNITS       "kbps"
        MAX-ACCESS  read-write
        STATUS      current
        DESCRIPTION
            "Committed Information Rate(CIR) in kbps."
        ::= { uniPortRateLimitEntry 4 }

    uniPortInCBS OBJECT-TYPE
        SYNTAX      INTEGER
        UNITS   "Kbytes"
        MAX-ACCESS  read-write
        STATUS      current
        DESCRIPTION
            "Committed Burst Rate(CBS) in kbyte."    
        ::= { uniPortRateLimitEntry 5 }

    uniPortInEBS OBJECT-TYPE
        SYNTAX      INTEGER
        UNITS   "Kbytes"
        MAX-ACCESS  read-write
        STATUS      current
        DESCRIPTION
            "ebs in kbytes."  
        ::= { uniPortRateLimitEntry 6 }

    uniPortOutCIR OBJECT-TYPE
        SYNTAX      INTEGER
        UNITS       "kbps"
        MAX-ACCESS  read-write
        STATUS      current
        DESCRIPTION
            "Committed Information Rate(CIR) in kbps."
        ::= { uniPortRateLimitEntry 7 }

    uniPortOutPIR OBJECT-TYPE
        SYNTAX      INTEGER
        UNITS   "kbps"
        MAX-ACCESS  read-write
        STATUS      current
        DESCRIPTION
            "PIR in kbps."  
        ::= { uniPortRateLimitEntry 8 }

    uniPortInRateLimitEnable OBJECT-TYPE
        SYNTAX      TruthValue
        MAX-ACCESS  read-write
        STATUS      current
        DESCRIPTION
            "Whether or not to enable or disable ingress rate limit for the UNI."  
        ::= { uniPortRateLimitEntry 9 }

    uniPortOutRateLimitEnable OBJECT-TYPE
        SYNTAX      TruthValue
        MAX-ACCESS  read-write
        STATUS      current
        DESCRIPTION
            "Whether or not to enable or disable egress rate limit for the UNI."  
        ::= { uniPortRateLimitEntry 10 }
            
    
  
--------------------------------------------------------------------------------
--  igmpManagementObjects[IGMP管理项](1.3.6.1.4.1.17409.2.3.6)
-------------------------------------------------------------------------------- 
    igmpEntityTable OBJECT-TYPE
      SYNTAX SEQUENCE OF IgmpEntityEntry
      MAX-ACCESS not-accessible
      STATUS current
      DESCRIPTION
        "
IGMP实体表"
      ::= { igmpManagementObjects 1 }
    
    igmpEntityEntry OBJECT-TYPE
      SYNTAX IgmpEntityEntry
      MAX-ACCESS not-accessible
      STATUS current
      DESCRIPTION
        " "
      INDEX { igmpDeviceIndex }
      ::= { igmpEntityTable 1 }
    
    IgmpEntityEntry ::=
      SEQUENCE { 
        igmpDeviceIndex
          INTEGER,
        igmpMode
          INTEGER,
        maxQueryResponseTime
          INTEGER,
        robustVariable
          INTEGER,
        queryInterval
          INTEGER,
        lastMemberQueryInterval
          INTEGER,
        lastMemberQueryCount
          INTEGER,
        igmpVersion
          INTEGER
       }
    
    igmpDeviceIndex OBJECT-TYPE
      SYNTAX INTEGER
      MAX-ACCESS not-accessible
      STATUS current
      DESCRIPTION
        "
        设备索引号。        
        For OLT Agent, set to corresponding device        
        For ONU Agent, set to 0"
      ::= { igmpEntityEntry 1 }

    igmpMode OBJECT-TYPE
      SYNTAX INTEGER
        {
        centralized(1),
        distributedwithcm(2),
        disabled(3),
        distributedwocm(4)
        }
      MAX-ACCESS read-write
      STATUS current
      DESCRIPTION
        "
        IGMP工作模式
        1代表proxy,2代表可控组播,3代表disabled,4代表snooping模式        
        "
      DEFVAL { disabled }
      ::= { igmpEntityEntry 2 }
    
    maxQueryResponseTime OBJECT-TYPE
      SYNTAX INTEGER
      UNITS "tenth second"
      MAX-ACCESS read-write
      STATUS current
      DESCRIPTION
        "
        最大响应查询时间
        单位：1/10秒
        This is used for sending general query"
      ::= { igmpEntityEntry 3 }

    robustVariable OBJECT-TYPE
      SYNTAX INTEGER
      MAX-ACCESS read-write
      STATUS current
      DESCRIPTION
        "
        健壮性变量
        This is used for sending general query
        No less than 1"
      ::= { igmpEntityEntry 4 }

    
    queryInterval OBJECT-TYPE
      SYNTAX INTEGER
      UNITS "seconds"
      MAX-ACCESS read-write
      STATUS current
      DESCRIPTION
        "
        发送查询报文的时间间隔
        单位：秒
        This is used for sending general query
        "
      ::= { igmpEntityEntry 5 }
    
    lastMemberQueryInterval OBJECT-TYPE
      SYNTAX INTEGER
      UNITS "tenth second"
      MAX-ACCESS read-write
      STATUS current
      DESCRIPTION
        "
        Max Response Time inserted into Group-Specific Queries sent in response 
        to Leave Group messages, and is also the amount of time between 
        Group-Specific Query messages
        "
      ::= { igmpEntityEntry 6 }
      
    lastMemberQueryCount OBJECT-TYPE
      SYNTAX INTEGER
      MAX-ACCESS read-write
      STATUS current
      DESCRIPTION
        "
        Number of Group-Specific Queries sent before the router assumes there 
        are no local members
        "               
      ::= { igmpEntityEntry 7 }
    
    igmpVersion OBJECT-TYPE
      SYNTAX INTEGER
        {
        v1(1),
        v2(2),
        v3(3)
        }
      MAX-ACCESS read-write
      STATUS current
      DESCRIPTION
        "
        IGMP版本
"
      DEFVAL { v2 }
      ::= { igmpEntityEntry 8 }

    
    igmpProxyParaTable OBJECT-TYPE
      SYNTAX SEQUENCE OF IgmpProxyParaEntry
      MAX-ACCESS not-accessible
      STATUS current
      DESCRIPTION
        "
        IGMP proxy参数表 - 频道列表"
      ::= { igmpManagementObjects 2 }
    
    igmpProxyParaEntry OBJECT-TYPE
      SYNTAX IgmpProxyParaEntry
      MAX-ACCESS not-accessible
      STATUS current
      DESCRIPTION
        " "
      INDEX { proxyIndex }
      ::= { igmpProxyParaTable 1 }
    
    IgmpProxyParaEntry ::=
      SEQUENCE { 
        proxyIndex
          INTEGER,
        proxyName
          OCTET STRING,
        proxySrcIPAddress
          IpAddress,
        proxyMulticastVID
          INTEGER,
        proxyMulticastIPAddress
          IpAddress,
        multicastMaxBW
          Unsigned32,
        proxyRowStatus
          RowStatus
       }

    proxyIndex OBJECT-TYPE
      SYNTAX INTEGER (1..2000)
      MAX-ACCESS not-accessible
      STATUS current
      DESCRIPTION
        "
        IGMP Proxy索引号 - 频道号"
      ::= { igmpProxyParaEntry 1 }
    
    proxyName OBJECT-TYPE
      SYNTAX OCTET STRING (SIZE (0..256))
      MAX-ACCESS read-create
      STATUS current
      DESCRIPTION
        "
        IGMP Proxy别名(如央视、文广传媒等)"
      ::= { igmpProxyParaEntry 2 }
    
    proxySrcIPAddress OBJECT-TYPE
      SYNTAX IpAddress
      MAX-ACCESS read-create
      STATUS current
      DESCRIPTION
        "
        igmp v3中的源ip地址,具体见igmp v3协议。"
      ::= { igmpProxyParaEntry 3 }
    
    proxyMulticastVID OBJECT-TYPE
      SYNTAX INTEGER
      MAX-ACCESS read-create
      STATUS current
      DESCRIPTION
        "
        IGMP Proxy对应组播VID
        注：只有在可控组播模式下组播VID才有意义"
      ::= { igmpProxyParaEntry 4 }
    
    proxyMulticastIPAddress OBJECT-TYPE
      SYNTAX IpAddress
      MAX-ACCESS read-create
      STATUS current
      DESCRIPTION
        "
        组播IP地址"
      ::= { igmpProxyParaEntry 5 }
    
    
    multicastMaxBW OBJECT-TYPE
      SYNTAX Unsigned32
      UNITS "kbps"
      MAX-ACCESS read-create
      STATUS current
      DESCRIPTION
        "
        组播最大带宽        
        单位：kbps"
      ::= { igmpProxyParaEntry 7 }
    
    proxyRowStatus OBJECT-TYPE
      SYNTAX RowStatus
      MAX-ACCESS read-create
      STATUS current
      DESCRIPTION
        "
        行状态"
      ::= { igmpProxyParaEntry 8 }
    
    igmpForwardingTable OBJECT-TYPE
      SYNTAX SEQUENCE OF IgmpForwardingEntry
      MAX-ACCESS not-accessible
      STATUS current
      DESCRIPTION
        "
        Multicast forwarding table        
        "
      ::= { igmpManagementObjects 3 }
    
    igmpForwardingEntry OBJECT-TYPE
      SYNTAX IgmpForwardingEntry
      MAX-ACCESS not-accessible
      STATUS current
      DESCRIPTION
        " "
      INDEX { groupDeviceIndex, groupVlanIndex, groupIPAddress }
      ::= { igmpForwardingTable 1 }    
    IgmpForwardingEntry ::=
      SEQUENCE { 
        groupDeviceIndex
          INTEGER,
        groupVlanIndex
          INTEGER,
        groupIPAddress
          IpAddress,
        groupPortList
          OCTET STRING
       }

    groupDeviceIndex OBJECT-TYPE
      SYNTAX INTEGER
      MAX-ACCESS not-accessible
      STATUS current
      DESCRIPTION
        "
        设备索引号。        
        For OLT Agent, set to corresponding OLT device
        For ONU Agent, set to 0
        "
      ::= { igmpForwardingEntry 1 }

    groupVlanIndex OBJECT-TYPE
      SYNTAX INTEGER
      MAX-ACCESS not-accessible
      STATUS current
      DESCRIPTION
        "
        Vlan索引号"
      ::= { igmpForwardingEntry 2 }

    
    groupIPAddress OBJECT-TYPE
      SYNTAX IpAddress
      MAX-ACCESS not-accessible
      STATUS current
      DESCRIPTION
        "
        组IP地址索引号"
      ::= { igmpForwardingEntry 3 }
    
    groupPortList OBJECT-TYPE
      SYNTAX OCTET STRING
      MAX-ACCESS read-only
      STATUS current
      DESCRIPTION
        "
        Forwarding port list
        1. OLT
        -------------------------------------------------------------------
        It is presented by member port list. Each member port is identified
        by 4-byte format, same as TC of EponDeviceIndex. The actual length of
        this string depends of the number of member ports in the port list.
        The relationship is:
        Length of the string = 4 * (NUM of member ports)  
        For example, if device 1, port 1/2 and 2/3 is the member ports, 
        then this object will be presented as:
        01 01 02 00 01 02 03 00
        
        2. ONU
        -------------------------------------------------------------------
        It is presented by member port list. Each member port is identified
        by 2-byte format, One for slot ID, the last for port ID. The actual 
        length of this string depends of the number of member ports. If the 
        ONU is fixed (not modulized), set slot ID to 0, the NMS could ignore 
        the slot info.
        Note that, slot here shall follow the last byte definition of 
        EponCardIndex to indicate the main-slot and sub-slot index.  
        The relationship is:
        Length of the string = 2 * (NUM of member ports)  
        For example, if port 1/2 and 3/4 is the member ports of the group, 
        then the object is presented as:
        01 02 03 04       
        "
      ::= { igmpForwardingEntry 4 }
    
    controllededMulticastTable OBJECT-IDENTITY
      STATUS current
      DESCRIPTION 
        "
        可控组播表"
      ::= { igmpManagementObjects 4 }
    
     controlledMulticastUserAuthorityTable OBJECT-TYPE
      SYNTAX SEQUENCE OF ControlledMulticastUserAuthorityEntry
      MAX-ACCESS not-accessible
      STATUS current
      DESCRIPTION
        "
        可控组播用户权限表
        "
      ::= { controllededMulticastTable 1 }
    
    controlledMulticastUserAuthorityEntry OBJECT-TYPE
      SYNTAX ControlledMulticastUserAuthorityEntry
      MAX-ACCESS not-accessible
      STATUS current
      DESCRIPTION
        " "
      INDEX { cmDeviceIndex, cmCardIndex, cmPortIndex }
      ::= { controlledMulticastUserAuthorityTable 1 }
    
    ControlledMulticastUserAuthorityEntry ::=
      SEQUENCE { 
        cmDeviceIndex
          EponDeviceIndex,
        cmCardIndex
          EponCardIndex,
        cmPortIndex 
          EponPortIndex,
        multicastPackageList
          OCTET STRING,
        igmpGlobalBW
          Unsigned32,
        igmpGlobalBWUsed  
          Unsigned32,
        cmUserAuthorityRowStatus
          RowStatus         
       }

    cmDeviceIndex OBJECT-TYPE
      SYNTAX EponDeviceIndex
      MAX-ACCESS not-accessible
      STATUS current
      DESCRIPTION
        "
        设备索引号        
        For OLT Agent, set to corresponding device/slot/port/ONU
        For ONU Agent, set to 0"
      ::= { controlledMulticastUserAuthorityEntry 1 }

    cmCardIndex  OBJECT-TYPE
      SYNTAX EponCardIndex
      MAX-ACCESS not-accessible
      STATUS current
      DESCRIPTION
        "
        板卡索引号        
        Set to corresponding UNI slot
        "
      ::= { controlledMulticastUserAuthorityEntry 2 }

    cmPortIndex OBJECT-TYPE
      SYNTAX EponPortIndex
      MAX-ACCESS not-accessible
      STATUS current
      DESCRIPTION
        "
        Port ID        
        Set to corresponding UNI port
        "
      ::= { controlledMulticastUserAuthorityEntry 3 }
    
    multicastPackageList OBJECT-TYPE
      SYNTAX OCTET STRING (SIZE(0..250))
      MAX-ACCESS read-create
      STATUS current
      DESCRIPTION
        "
        可控组播组列表.        
        用法类似于cmProxyList,每个bit对应于cmIndex"
      ::= { controlledMulticastUserAuthorityEntry 4 }

    igmpGlobalBW OBJECT-TYPE
      SYNTAX Unsigned32
      UNITS "kbps"
      MAX-ACCESS read-create
      STATUS current
      DESCRIPTION
        "
        IGMP全局带宽池大小 - 该端口支持的最大组播带宽
        单位：kbps"
      ::= { controlledMulticastUserAuthorityEntry 5 }
    
    igmpGlobalBWUsed OBJECT-TYPE
      SYNTAX Unsigned32
      UNITS "kbps"
      MAX-ACCESS read-only
      STATUS current
      DESCRIPTION
        "
        IGMP全局带宽池当前使用大小 - 该端口当前实际使用的组播带宽        
        单位：kbps"
      ::= { controlledMulticastUserAuthorityEntry 6 }

    cmUserAuthorityRowStatus OBJECT-TYPE
      SYNTAX RowStatus
      MAX-ACCESS read-create
      STATUS current
      DESCRIPTION
        ""
      ::= { controlledMulticastUserAuthorityEntry 7 }
    
    controlledMulticastPackageTable OBJECT-TYPE
      SYNTAX SEQUENCE OF ControlledMulticastPackageEntry
      MAX-ACCESS not-accessible
      STATUS current
      DESCRIPTION
        "
        可控组播业务包表"
      ::= { controllededMulticastTable 2 }
    
    controlledMulticastPackageEntry OBJECT-TYPE
      SYNTAX ControlledMulticastPackageEntry
      MAX-ACCESS not-accessible
      STATUS current
      DESCRIPTION
        " "
      INDEX { cmIndex }
      ::= { controlledMulticastPackageTable 1 }
    
    ControlledMulticastPackageEntry ::=
      SEQUENCE { 
        cmIndex
          INTEGER,
        cmName
          OCTET STRING,
        cmProxyList
          OCTET STRING,
        multicastUserAuthority
          INTEGER,
        maxRequestChannelNum
          INTEGER,
        singlePreviewTime
          INTEGER,
        totalPreviewTime
          INTEGER,
        previewResetTime
          INTEGER,
        previewCount
          INTEGER,
        cmRowStatus
          RowStatus
       }

    cmIndex OBJECT-TYPE
      SYNTAX INTEGER (1..2000)
      MAX-ACCESS not-accessible
      STATUS current
      DESCRIPTION
        "
        该可控组播业务包的索引(流水号)"
      ::= { controlledMulticastPackageEntry 1 }
    
    cmName OBJECT-TYPE
      SYNTAX OCTET STRING (SIZE(0..256))
      MAX-ACCESS read-create
      STATUS current
      DESCRIPTION
        "
        该可控组播业务包名称"
      ::= { controlledMulticastPackageEntry 2 }
    
    cmProxyList OBJECT-TYPE
      SYNTAX OCTET STRING (SIZE (0..250))
      MAX-ACCESS read-create
      STATUS current
      DESCRIPTION
        "
        该可控组播业务包支持的Proxy列表
        采用类似INTERNET比特顺序,从左到右的OCTET分别为OCTET 0, OCTET 1, ...
        每个OCTET的bit从左到右分别为bit0,bit1,...,bit7。
        按照bit和OCTET由小到大的顺序,每个bit对应于igmpProxyParaTable中的
        一个proxyIndex,如果bit置位,表示该proxyIndex支持,否则不支持。        
        举例来说,如果规划了80个频道,proxyIndex范围为1..80,用10个字节表示
        proxy列表,假设该PON口只支持频道列表1,15,38,对应的cmProxyList可以
        设置成0x80 02 00 00 04 00 00 00 00 00"
      ::= { controlledMulticastPackageEntry 3 }
    
    multicastUserAuthority OBJECT-TYPE
      SYNTAX INTEGER
        {
        permit(1),
        preview(2),
        deny(3)
        }
      MAX-ACCESS read-create
      STATUS current
      DESCRIPTION
        "
        用户权限(permit、preview、deny)"
      ::= { controlledMulticastPackageEntry 4 }

    maxRequestChannelNum OBJECT-TYPE
      SYNTAX INTEGER
      MAX-ACCESS read-create
      STATUS current
      DESCRIPTION
        "
        最大允许请求频道数"
      ::= { controlledMulticastPackageEntry 5 }
    
    singlePreviewTime OBJECT-TYPE
      SYNTAX INTEGER
      UNITS "seconds"
      MAX-ACCESS read-create
      STATUS current
      DESCRIPTION
        "
        单次预览时长,单位：秒"
      ::= { controlledMulticastPackageEntry 6 }
    
    totalPreviewTime OBJECT-TYPE
      SYNTAX INTEGER
      UNITS "seconds"
      MAX-ACCESS read-create
      STATUS current
      DESCRIPTION
        "
        预览总时长,单位：秒"
      ::= { controlledMulticastPackageEntry 7 }
    
    previewResetTime OBJECT-TYPE
      SYNTAX INTEGER
      UNITS "seconds"
      MAX-ACCESS read-create
      STATUS current
      DESCRIPTION
        "
        预览复位时间,单位：秒"
      ::= { controlledMulticastPackageEntry 8 }
    
    previewCount OBJECT-TYPE
      SYNTAX INTEGER
      MAX-ACCESS read-create
      STATUS current
      DESCRIPTION
        "
        预览次数"
      ::= { controlledMulticastPackageEntry 9 }
  
    cmRowStatus OBJECT-TYPE
      SYNTAX RowStatus
      MAX-ACCESS read-create
      STATUS current
      DESCRIPTION
        "
        行状态"
      ::= { controlledMulticastPackageEntry 10 }


igmpOnuUniTable  OBJECT-TYPE
SYNTAX      SEQUENCE OF IgmpOnuUniEntry
MAX-ACCESS  not-accessible
STATUS      current
DESCRIPTION
    "A list of igmpOnuUniTable  entries. "
::= { igmpManagementObjects 5 }

igmpOnuUniEntry OBJECT-TYPE
SYNTAX      IgmpOnuUniEntry
MAX-ACCESS  not-accessible
STATUS      current
DESCRIPTION  
    "The igmpOnuUniEntry Information"
INDEX   { uniMvlanDeviceIndex,uniMvlanCardIndex,uniMvlanPortIndex }   
::={ igmpOnuUniTable 1 }   

IgmpOnuUniEntry::= SEQUENCE {
uniMvlanDeviceIndex
EponDeviceIndex,
uniMvlanCardIndex
EponCardIndex,
uniMvlanPortIndex
EponPortIndex,
uniMvlanVid 
OCTET STRING,
uniMaxMultiNum      
INTEGER,
uniMvlanTag    
INTEGER,
uniMvlanRowstatus      
INTEGER
}

uniMvlanDeviceIndex OBJECT-TYPE
SYNTAX      EponDeviceIndex
MAX-ACCESS  not-accessible
STATUS      current
DESCRIPTION
    "设备索引 "
::= { igmpOnuUniEntry 1 }   

uniMvlanCardIndex OBJECT-TYPE
SYNTAX      EponCardIndex
MAX-ACCESS  not-accessible
STATUS      current
DESCRIPTION
    "板卡索引"
::= { igmpOnuUniEntry 2 }  

uniMvlanPortIndex OBJECT-TYPE
SYNTAX      EponPortIndex
MAX-ACCESS  read-create
STATUS      current
DESCRIPTION
    "端口索引"
::= { igmpOnuUniEntry 3 }  

uniMvlanVid OBJECT-TYPE
SYNTAX     OCTET STRING (SIZE (16))
MAX-ACCESS  read-create
STATUS      current
DESCRIPTION
    "索引(uni端口中的mvlan(1..4084)),两个字节的值表示一个VLAN ID,一个UNI端口只配置8个VLAN"
::= { igmpOnuUniEntry 4 }

uniMaxMultiNum OBJECT-TYPE
SYNTAX      INTEGER
MAX-ACCESS  read-create
STATUS      current
DESCRIPTION
    "最大组播数"
::= { igmpOnuUniEntry 5 }

uniMvlanTag OBJECT-TYPE
SYNTAX      INTEGER
MAX-ACCESS  read-create
STATUS      current
DESCRIPTION
    "是否剥离,0：剥离 1：不剥离"
::= { igmpOnuUniEntry 6 }
 
uniMvlanRowstatus OBJECT-TYPE
SYNTAX      INTEGER
MAX-ACCESS  read-create
STATUS      current
DESCRIPTION
    "行状态"
::= { igmpOnuUniEntry 7 }



    igmpOltMulticastVlanTable  OBJECT-TYPE
      SYNTAX SEQUENCE OF IgmpOltMulticastVlanEntry
      MAX-ACCESS not-accessible
      STATUS current
      DESCRIPTION
        "
	OLT 组播VLAN表"
      ::= { igmpManagementObjects 6 }
    

    igmpOltMulticastVlanEntry OBJECT-TYPE
      SYNTAX IgmpOltMulticastVlanEntry
      MAX-ACCESS not-accessible
      STATUS current
      DESCRIPTION
        " "
      INDEX { igmpOltMulticastVlanDeviceIndex, multicastVlanId  }
      ::= { igmpOltMulticastVlanTable 1 }
    
    IgmpOltMulticastVlanEntry ::=
      SEQUENCE { 
        igmpOltMulticastVlanDeviceIndex
          INTEGER,
        multicastVlanId
          INTEGER,
        mvlanMaxQueryResponseTime
          INTEGER,
        mvlanMobustVariable
          INTEGER,
        mvlanQueryInterval
          INTEGER,
        mvlanLastMemberQueryInterval
          INTEGER,
        mvlanLastMemberQueryCount
          INTEGER,
        mvlanRowstatus  
          INTEGER
       }
    
    igmpOltMulticastVlanDeviceIndex OBJECT-TYPE
      SYNTAX INTEGER
      MAX-ACCESS not-accessible
      STATUS current
      DESCRIPTION
        "
        设备索引号。        
        OLT device index"
      ::= { igmpOltMulticastVlanEntry 1 }

    multicastVlanId OBJECT-TYPE
      SYNTAX INTEGER
      MAX-ACCESS read-write
      STATUS current
      DESCRIPTION
        "
        OLT 组播VLAN ID
        "
      ::= { igmpOltMulticastVlanEntry 2 }
    
    mvlanMaxQueryResponseTime OBJECT-TYPE
      SYNTAX INTEGER
      UNITS "tenth second"
      MAX-ACCESS read-write
      STATUS optional
      DESCRIPTION
        "
        最大响应查询时间
        单位：1/10秒
        This is used for sending general query"
      ::= { igmpOltMulticastVlanEntry 3 }

    mvlanMobustVariable OBJECT-TYPE
      SYNTAX INTEGER
      MAX-ACCESS read-write
      STATUS optional
      DESCRIPTION
        "
        健壮性变量
        This is used for sending general query
        No less than 1"
      ::= { igmpOltMulticastVlanEntry 4 }

    
    mvlanQueryInterval OBJECT-TYPE
      SYNTAX INTEGER
      UNITS "seconds"
      MAX-ACCESS read-write
      STATUS optional
      DESCRIPTION
        "
        发送查询报文的时间间隔
        单位：秒
        This is used for sending general query
        "
      ::= { igmpOltMulticastVlanEntry 5 }
    
    mvlanLastMemberQueryInterval OBJECT-TYPE
      SYNTAX INTEGER
      UNITS "tenth second"
      MAX-ACCESS read-write
      STATUS optional
      DESCRIPTION
        "
        Max Response Time inserted into Group-Specific Queries sent in response 
        to Leave Group messages, and is also the amount of time between 
        Group-Specific Query messages
        "
      ::= { igmpOltMulticastVlanEntry 6 }
      
    mvlanLastMemberQueryCount OBJECT-TYPE
      SYNTAX INTEGER
      MAX-ACCESS read-create
      STATUS optional
      DESCRIPTION
        "
        Number of Group-Specific Queries sent before the router assumes there 
        are no local members
        "               
      ::= { igmpOltMulticastVlanEntry 7 }
    

mvlanRowstatus  OBJECT-TYPE
SYNTAX      INTEGER
MAX-ACCESS  read-create
STATUS      current
DESCRIPTION
    "行状态"
::= { igmpOltMulticastVlanEntry  8 }




igmpSniMulticastVlanTable   OBJECT-TYPE
SYNTAX      SEQUENCE OF IgmpSniMulticastVlanEntry
MAX-ACCESS  not-accessible
STATUS      current
DESCRIPTION
    "SNI端口组播VLAN表"
::= { igmpManagementObjects 7 }

igmpSniMulticastVlanEntry OBJECT-TYPE
SYNTAX      IgmpSniMulticastVlanEntry
MAX-ACCESS  not-accessible
STATUS      current
DESCRIPTION  
    "The igmpSniMulticastVlanEntry Information"
INDEX   { sniMultiVlanVid,sniMultiVlanDeviceIndex }   
::={ igmpSniMulticastVlanTable   1 }   

IgmpSniMulticastVlanEntry ::= SEQUENCE {
sniMultiVlanVid
INTEGER,
sniMultiVlanDeviceIndex
EponDeviceIndex,
sniMultiVlanRowstatus
INTEGER
}

sniMultiVlanVid  OBJECT-TYPE
SYNTAX    INTEGER
MAX-ACCESS  read-create
STATUS      current
DESCRIPTION
    " SNI端口组播VLAN号"
::= { igmpSniMulticastVlanEntry 1 }

sniMultiVlanDeviceIndex  OBJECT-TYPE
SYNTAX      EponDeviceIndex
MAX-ACCESS  not-accessible
STATUS      current
DESCRIPTION
    "SNI设备索引,device/slot/sni port "
::= { igmpSniMulticastVlanEntry 2 }   

sniMultiVlanRowstatus OBJECT-TYPE
SYNTAX      INTEGER
MAX-ACCESS  read-create
STATUS      current
DESCRIPTION
    "行状态"
::= { igmpSniMulticastVlanEntry 3 }



onuIgmpModeTable   OBJECT-TYPE
SYNTAX      SEQUENCE OF OnuIgmpModeEntry 
MAX-ACCESS  not-accessible
STATUS      current
DESCRIPTION
    "ONU组播模式表"
::= { igmpManagementObjects 8 }

onuIgmpModeEntry  OBJECT-TYPE
SYNTAX      OnuIgmpModeEntry 
MAX-ACCESS  not-accessible
STATUS      current
DESCRIPTION  
    "The onuIgmpModeEntry Information"
INDEX   { onuIgmpModeDeviceIndex }   
::={ onuIgmpModeTable  1 }   

OnuIgmpModeEntry ::= SEQUENCE {
onuIgmpModeDeviceIndex 
EponDeviceIndex,
onuIgmpMode
INTEGER
}

onuIgmpModeDeviceIndex  OBJECT-TYPE
SYNTAX      EponDeviceIndex
MAX-ACCESS  not-accessible
STATUS      current
DESCRIPTION
    "ONU ID "
::= { onuIgmpModeEntry 1 }   

onuIgmpMode  OBJECT-TYPE
SYNTAX    INTEGER{
disable(1),
snooping(2),
controlledMulticast(3)
}
MAX-ACCESS  read-write
STATUS      current
DESCRIPTION
    " ONU组播模式
默认组播是snooping(2)模式
"
  DEFVAL { snooping}
::= { onuIgmpModeEntry 2 }

--------------------------------------------------------------------------------
--  vlanManagementObjects [VLAN管理项](1.3.6.1.4.1.17409.2.3.7)
--------------------------------------------------------------------------------    
    vlanGlobalInfoTable OBJECT-TYPE
      SYNTAX SEQUENCE OF VlanGlobalInfoEntry
      MAX-ACCESS not-accessible
      STATUS current
      DESCRIPTION
        "
        全局VLAN信息表"
      ::= { vlanManagementObjects 1 }
    
    vlanGlobalInfoEntry OBJECT-TYPE
      SYNTAX VlanGlobalInfoEntry
      MAX-ACCESS not-accessible
      STATUS current
      DESCRIPTION
        " "
      INDEX { vlanDeviceIndex }
      ::= { vlanGlobalInfoTable 1 }
    
    VlanGlobalInfoEntry ::=
      SEQUENCE { 
        vlanDeviceIndex
          EponDeviceIndex,
        maxVlanId
          INTEGER,
        maxSupportVlans
          INTEGER,
        createdVlanNumber
          INTEGER
       }

    vlanDeviceIndex OBJECT-TYPE
      SYNTAX EponDeviceIndex
      MAX-ACCESS not-accessible
      STATUS current
      DESCRIPTION
        "
        设备索引号。        
        For OLT Agent, set to corresponding device ID
        For ONU Agent, set to 0"
      ::= { vlanGlobalInfoEntry 1 }

    maxVlanId OBJECT-TYPE
      SYNTAX INTEGER
      MAX-ACCESS read-only
      STATUS current
      DESCRIPTION
        "
        最大VLAN ID"
      ::= { vlanGlobalInfoEntry 2 }
    
    maxSupportVlans OBJECT-TYPE
      SYNTAX INTEGER
      MAX-ACCESS read-only
      STATUS current
      DESCRIPTION
        "
        最大支持的VLAN个数"
      ::= { vlanGlobalInfoEntry 3 }
    
    createdVlanNumber OBJECT-TYPE
      SYNTAX INTEGER
      MAX-ACCESS read-only
      STATUS current
      DESCRIPTION
        "
        已创建的VLAN个数"
      ::= { vlanGlobalInfoEntry 4 }

    vlanConfigGroup OBJECT-IDENTITY
      STATUS current
      DESCRIPTION 
        "
        Vlan配置组"
      ::= { vlanManagementObjects 2 }
    
    oltVlanConfigTable OBJECT-TYPE
      SYNTAX SEQUENCE OF OltVlanConfigEntry
      MAX-ACCESS not-accessible
      STATUS current
      DESCRIPTION
        "
        OLT VLAN成员配置表"
      ::= { vlanConfigGroup 1 }
    
    oltVlanConfigEntry OBJECT-TYPE
      SYNTAX OltVlanConfigEntry
      MAX-ACCESS not-accessible
      STATUS current
      DESCRIPTION
        " "
      INDEX { oltVlanIndex, oltVlanDeviceIndex}
      ::= { oltVlanConfigTable 1 }
    
    OltVlanConfigEntry ::=
      SEQUENCE {
        oltVlanIndex
          INTEGER,
        oltVlanDeviceIndex
          INTEGER,
        oltVlanName
          OCTET STRING,
        taggedPort
          OCTET STRING,
        untaggedPort
          OCTET STRING,
        oltVlanRowStatus
          RowStatus
       }
              
    oltVlanIndex  OBJECT-TYPE
      SYNTAX INTEGER
      MAX-ACCESS not-accessible
      STATUS current
      DESCRIPTION
        "
        Vlan索引号"
      ::= { oltVlanConfigEntry 1 }
            
    oltVlanDeviceIndex  OBJECT-TYPE
      SYNTAX INTEGER
      MAX-ACCESS not-accessible
      STATUS current
      DESCRIPTION
        "
        OLT设备索引号。   
        "
      ::= { oltVlanConfigEntry 2 }

    oltVlanName OBJECT-TYPE
      SYNTAX OCTET STRING (SIZE (0..128))
      MAX-ACCESS read-create
      STATUS current
      DESCRIPTION
        "
        OLT VLAN name"
      ::= { oltVlanConfigEntry 3 }
    
    taggedPort OBJECT-TYPE
      SYNTAX OCTET STRING
      MAX-ACCESS read-create
      STATUS current
      DESCRIPTION
        "
        Vlan包括的tag的PON/SNI in OLT。        
        It is presented by member port list. Each member port is identified
        by 4-byte format, same as TC of EponDeviceIndex. The actual length of
        this string depends of the number of member ports in the port list.
        The relationship is:
        Length of the string = 4 * (NUM of member ports)  
        For example, if device 1, port 1/2 and 2/3 is the member ports, 
        then this object will be presented as:
        01 01 02 00 01 02 03 00       
        "
      ::= { oltVlanConfigEntry 4 }
    
    untaggedPort OBJECT-TYPE
      SYNTAX OCTET STRING
      MAX-ACCESS read-create
      STATUS current
      DESCRIPTION
        "
        Vlan包括的Untag的PON/SNI in OLT。        
        It is presented by member port list. Each member port is identified
        by 4-byte format, same as TC of EponDeviceIndex. The actual length of
        this string depends of the number of member ports in the port list.
        The relationship is:
        Length of the string = 4 * (NUM of member ports)  
        For example, if device 1, port 1/2 and 2/3 is the member ports, 
        then this object will be presented as:
        01 01 02 00 01 02 03 00         
        "
      ::= { oltVlanConfigEntry 5 }
    
    oltVlanRowStatus OBJECT-TYPE
      SYNTAX RowStatus
      MAX-ACCESS read-create
      STATUS current
      DESCRIPTION
        "
        行状态"
      ::= { oltVlanConfigEntry 6 }
    
    onuVlanConfigTable OBJECT-TYPE
      SYNTAX SEQUENCE OF OnuVlanConfigEntry
      MAX-ACCESS not-accessible
      STATUS current
      DESCRIPTION
        "
        ONU VLAN成员配置表
        "
      ::= { vlanConfigGroup 2 }
    
    onuVlanConfigEntry OBJECT-TYPE
      SYNTAX OnuVlanConfigEntry
      MAX-ACCESS not-accessible
      STATUS current
      DESCRIPTION
        " "
      INDEX { onuVlanIndex,onuVlanDeviceIndex }
      ::= { onuVlanConfigTable 1 }
    
    OnuVlanConfigEntry ::=
      SEQUENCE { 
        onuVlanIndex
          INTEGER,
       onuVlanDeviceIndex
          EponDeviceIndex,
        onuVlanName 
          OCTET STRING,
        onuVlanTaggedPort
          OCTET STRING,
        onuVlanUntaggedPort
          OCTET STRING,
        onuVlanRowStatus
          RowStatus
       }

    onuVlanIndex OBJECT-TYPE
      SYNTAX INTEGER
      MAX-ACCESS not-accessible
      STATUS current
      DESCRIPTION
        "
        Vlan索引号"
      ::= { onuVlanConfigEntry 1 }    


    onuVlanDeviceIndex OBJECT-TYPE
      SYNTAX EponDeviceIndex
      MAX-ACCESS not-accessible
      STATUS current
      DESCRIPTION
        "
        ONU设备索引号"
      ::= { onuVlanConfigEntry 2 }  


    onuVlanName OBJECT-TYPE
      SYNTAX OCTET STRING (SIZE (0..128))
      MAX-ACCESS read-create
      STATUS current
      DESCRIPTION
        "
        ONU VLAN name"
      ::= { onuVlanConfigEntry 3 }
    
    onuVlanTaggedPort OBJECT-TYPE
      SYNTAX OCTET STRING
      MAX-ACCESS read-create
      STATUS current
      DESCRIPTION
        "
        Vlan包括的tag的UNI端口。        
        It is presented by member port list. Each member port is identified
        by 2-byte format, One for slot ID, the last for port ID. The actual 
        length of this string depends of the number of tagged member ports 
        in the VLAN. If the ONU is fixed (not modulized), set slot ID to 0,
        the NMS could ignore the slot info.        
        Note that, slot here shall follow the last byte definition of 
        EponCardIndex to indicate the main-slot and sub-slot index.  
        The relationship is:
        Length of the string = 2 * (NUM of member ports)  
        For example, if port 1/2 and 3/4 is the tagged member ports of the
        VLAN, then the object is presented as:
        01 02 03 04
        "           
      ::= { onuVlanConfigEntry 4 }
    
    onuVlanUntaggedPort OBJECT-TYPE
      SYNTAX OCTET STRING
      MAX-ACCESS read-create
      STATUS current
      DESCRIPTION
        "
        Vlan包括的Untag的UNI端口。        
        It is presented by member port list. Each member port is identified
        by 2-byte format, One for slot ID, the last for port ID. The actual 
        length of this string depends of the number of untagged member ports 
        in the VLAN. If the ONU is fixed (not modulized), set slot ID to FF,
        the NMS could ignore the slot info.  
        Note that, slot here shall follow the last byte definition of 
        EponCardIndex to indicate the main-slot and sub-slot index. 
        The relationship is:
        Length of the string = 2 * (NUM of member ports)  
        For example, if port 1/2 and 3/4 is the untagged member ports of the
        VLAN, then the object is presented as:
        01 02 03 04       
        "
      ::= { onuVlanConfigEntry 5 }
    
    onuVlanRowStatus OBJECT-TYPE
      SYNTAX RowStatus
      MAX-ACCESS read-create
      STATUS current
      DESCRIPTION
        "
        行状态"
      ::= { onuVlanConfigEntry 6 }
    
    portVlanGroup OBJECT-IDENTITY
      STATUS current
      DESCRIPTION 
        "
        端口Vlan组(sni、uni、ponport)"
      ::= { vlanManagementObjects 3 }
    
    onuPortVlanTable OBJECT-TYPE
      SYNTAX SEQUENCE OF OnuPortVlanEntry
      MAX-ACCESS not-accessible
      STATUS current
      DESCRIPTION
        "
        端口Vlan表        
        This table applies on ONU UNI.        
        1. If the table is maintained in OLT device(OLT作为SNMP Agent):
        Applied Obj  - Descriptions of Index
        ------------------------------------------------------------------
       
        ONU UNI    - Set pvlanDeviceIndex to corresponding ONU ID,
                 pvlanCardIndex, and pvlanPortIndex set to the corresponding 
                 value        
        2. If the table is maintained in ONU device(ONU作为SNMP Agent):
        pvlanDeviceIndex shall be set to 0 to indicate meaningless.
        pvlanCardIndex shall be set to corresponding slot.
        pvlanPortIndex shall be set to corresponding port.        
        "
        
      ::= { portVlanGroup 1 }
    
    onuPortVlanEntry  OBJECT-TYPE
      SYNTAX OnuPortVlanEntry  
      MAX-ACCESS not-accessible
      STATUS current
      DESCRIPTION
        " "
      INDEX { pvlanDeviceIndex, pvlanCardIndex, pvlanPortIndex}
      ::= { onuPortVlanTable 1 }
    
    OnuPortVlanEntry ::=
      SEQUENCE {
        pvlanDeviceIndex
          EponDeviceIndex,
        pvlanCardIndex
          EponCardIndex,
        pvlanPortIndex
          EponPortIndex, 
        vlanTagTpid
          OCTET STRING,
        vlanTagCfi
          TruthValue,
        vlanTagPriority
          INTEGER,
        vlanPVid
          INTEGER,
        vlanMode
          INTEGER
       }
  
    pvlanDeviceIndex OBJECT-TYPE
      SYNTAX EponDeviceIndex
      MAX-ACCESS not-accessible
      STATUS current
      DESCRIPTION
        "
        OLT/ONU设备索引号。"
      ::= { onuPortVlanEntry  1 }

    pvlanCardIndex OBJECT-TYPE
      SYNTAX EponCardIndex
      MAX-ACCESS not-accessible
      STATUS current
      DESCRIPTION
        "
        板卡索引号
        "
      ::= { onuPortVlanEntry  2 }

    pvlanPortIndex  OBJECT-TYPE
      SYNTAX EponPortIndex
      MAX-ACCESS not-accessible
      STATUS current
      DESCRIPTION
        "
        端口索引号
        "
      ::= { onuPortVlanEntry  3 }
  
    vlanTagTpid OBJECT-TYPE
      SYNTAX OCTET STRING (SIZE (2))
      MAX-ACCESS read-write
      STATUS current
      DESCRIPTION
        "
        标记的协议标识        
        It shall be presented in hexadecimal format. For example, 81 00
        to indicate 0x8100"
      ::= { onuPortVlanEntry  4 }
    
    vlanTagCfi OBJECT-TYPE
      SYNTAX TruthValue
      MAX-ACCESS read-write
      STATUS current
      DESCRIPTION
        "
        规则格式指示符"
      ::= { onuPortVlanEntry  5 }
    
    vlanTagPriority OBJECT-TYPE
      SYNTAX INTEGER (0..7)
      MAX-ACCESS read-write
      STATUS current
      DESCRIPTION
        "
        vlan优先级"
      ::= { onuPortVlanEntry  6 }
    
    vlanPVid OBJECT-TYPE
      SYNTAX INTEGER
      MAX-ACCESS read-write
      STATUS current
      DESCRIPTION
        "
        port Vlan ID"
      ::= { onuPortVlanEntry  7 }
    
    vlanMode OBJECT-TYPE
      SYNTAX INTEGER
        {

        transparent(0),
        tag(1),
        translation(2),
        aggregation(3),
        trunk(4),
        stacking(5)

        }
      MAX-ACCESS read-write
      STATUS current
      DESCRIPTION
        "
        vlan模式
        "
      ::= { onuPortVlanEntry  8 }
    
    portVlanTranslationTable OBJECT-TYPE
      SYNTAX SEQUENCE OF PortVlanTranslationEntry
      MAX-ACCESS not-accessible
      STATUS current
      DESCRIPTION
        "
        端口Vlan翻译表
        This table applies on OLT pon port, OLT SNI, OLT onu ID, ONU UNI.
        1. If the table is maintained in OLT device(OLT作为SNMP Agent):
        Applied Obj  - Descriptions of Index
        ------------------------------------------------------------------
        OLT Pon Port - OnuNum of pvtDeviceIndex shall be set to 0,
        /OLT SNI     pvtCardIndex, and pvtPortIndex set to 0 indicates
                 meaningless 
        OLT onu ID   - Set pvtDeviceIndex to corresponding ONU ID,
                 pvtCardIndex, and pvtPortIndex set to 0 indicates
                 meaningless        
        ONU UNI    - Set pvtDeviceIndex to corresponding ONU ID,
                 pvtCardIndex, and pvtPortIndex set to the corresponding 
                 value
        
        2. If the table is maintained in ONU device(ONU作为SNMP Agent):
        pvtDeviceIndex shall be set to 0 to indicate meaningless.
        pvtCardIndex shall be set to corresponding slot.
        pvtPortIndex shall be set to corresponding port.        
        "
      ::= { portVlanGroup 2 }
    
    portVlanTranslationEntry OBJECT-TYPE
      SYNTAX PortVlanTranslationEntry
      MAX-ACCESS not-accessible
      STATUS current
      DESCRIPTION
        " "
      INDEX { pvtDeviceIndex , pvtCardIndex , pvtPortIndex  , portVidIndex }
      ::= { portVlanTranslationTable 1 }    
    PortVlanTranslationEntry ::=
      SEQUENCE { 
        pvtDeviceIndex 
          EponDeviceIndex,
        pvtCardIndex 
          EponCardIndex,
        pvtPortIndex  
          EponPortIndex,
        portVidIndex
          Unsigned32,
        translationNewVid
          Unsigned32,
        translationRowStatus
          RowStatus
       }
    pvtDeviceIndex OBJECT-TYPE
      SYNTAX EponDeviceIndex
      MAX-ACCESS not-accessible
      STATUS current
      DESCRIPTION
        "
        OLT/ONU设备索引号。"
      ::= { portVlanTranslationEntry 1 }

    pvtCardIndex OBJECT-TYPE
      SYNTAX EponCardIndex
      MAX-ACCESS not-accessible
      STATUS current
      DESCRIPTION
        "
        板卡索引号"
      ::= { portVlanTranslationEntry 2 }

    pvtPortIndex  OBJECT-TYPE
      SYNTAX EponPortIndex
      MAX-ACCESS not-accessible
      STATUS current
      DESCRIPTION
        "
        端口索引号"
      ::= { portVlanTranslationEntry 3 }

    portVidIndex OBJECT-TYPE
      SYNTAX Unsigned32
      MAX-ACCESS not-accessible
      STATUS current
      DESCRIPTION
        "
        端口原始VLAN ID索引号"
      ::= { portVlanTranslationEntry 4 }
    
    translationNewVid OBJECT-TYPE
      SYNTAX Unsigned32
      MAX-ACCESS read-create
      STATUS current
      DESCRIPTION
        "
        翻译的新vlan号"
      ::= { portVlanTranslationEntry 5 }
    
    translationRowStatus OBJECT-TYPE
      SYNTAX RowStatus
      MAX-ACCESS read-create
      STATUS current
      DESCRIPTION
        "
        行状态 "
      ::= { portVlanTranslationEntry 6 }
    
    portVlanAggregationManagement OBJECT-IDENTITY
      STATUS current
      DESCRIPTION 
        "
        端口Vlan聚合管理(VLAN Aggregation)"
      ::= { portVlanGroup 3 }
    
    portVlanAggregationConfigTable OBJECT-TYPE
      SYNTAX SEQUENCE OF PortVlanAggregationConfigEntry
      MAX-ACCESS not-accessible
      STATUS current
      DESCRIPTION
        "
        端口Vlan聚合配置表
        This table applies on OLT pon port, OLT onu ID, ONU UNI.
        1. If the table is maintained in OLT device(OLT作为SNMP Agent):
        Applied Obj  - Descriptions of Index
        ------------------------------------------------------------------
        OLT Pon Port - OnuNum of pvaDeviceIndex shall be set to 0,
                 pvaCardIndex, and pvaPortIndex set to 0 indicates
                 meaningless 
        OLT onu ID   - Set pvaDeviceIndex to corresponding ONU ID,
                 pvaCardIndex, and pvaPortIndex set to 0 indicates
                 meaningless        
        ONU UNI    - Set pvaDeviceIndex to corresponding ONU ID,
                 pvaCardIndex, and pvaPortIndex set to the corresponding 
                 value
        
        2. If the table is maintained in ONU device(ONU作为SNMP Agent):
        pvaDeviceIndex shall be set to 0 to indicate meaningless.
        pvaCardIndex shall be set to corresponding slot.
        pvaPortIndex shall be set to corresponding port.        
        "
      ::= { portVlanAggregationManagement 1 }
    
    portVlanAggregationConfigEntry OBJECT-TYPE
      SYNTAX PortVlanAggregationConfigEntry
      MAX-ACCESS not-accessible
      STATUS current
      DESCRIPTION
        " "
      INDEX { pvaDeviceIndex , pvaCardIndex , pvaPortIndex  , portAggregationVidIndex }
      ::= { portVlanAggregationConfigTable 1 }
    
    PortVlanAggregationConfigEntry ::=
      SEQUENCE { 
        pvaDeviceIndex 
          EponDeviceIndex,
        pvaCardIndex 
          EponCardIndex,
        pvaPortIndex  
          EponPortIndex,
        portAggregationVidIndex 
          Unsigned32,
        aggregationVidList
          OCTET STRING,
        aggregationRowStatus
          RowStatus
       }

    pvaDeviceIndex OBJECT-TYPE
      SYNTAX EponDeviceIndex
      MAX-ACCESS not-accessible
      STATUS current
      DESCRIPTION
        "
        OLT/ONU设备索引号。"
      ::= { portVlanAggregationConfigEntry 1 }

    pvaCardIndex OBJECT-TYPE
      SYNTAX EponCardIndex
      MAX-ACCESS not-accessible
      STATUS current
      DESCRIPTION
        "
        板卡索引号"
      ::= { portVlanAggregationConfigEntry 2 }

    pvaPortIndex  OBJECT-TYPE
      SYNTAX EponPortIndex
      MAX-ACCESS not-accessible
      STATUS current
      DESCRIPTION
        "
        端口索引号"
      ::= { portVlanAggregationConfigEntry 3 }

    portAggregationVidIndex OBJECT-TYPE
      SYNTAX Unsigned32
      MAX-ACCESS not-accessible
      STATUS current
      DESCRIPTION
        "
        端口VLAN聚合组VLAN号"
      ::= { portVlanAggregationConfigEntry 4 }

    aggregationVidList OBJECT-TYPE
      SYNTAX OCTET STRING (SIZE (512))
      MAX-ACCESS read-create
      STATUS current
      DESCRIPTION
        "
        聚合的vlan ID组
        采用类似INTERNET比特顺序,从左到右的OCTET分别为OCTET 0, OCTET 1, ...
        每个OCTET的bit从左到右分别为bit0,bit1,...,bit7。
        按照bit和OCTET由小到大的顺序,每个bit对应于一个VLAN,VLAN ID范围为0..4095。
        第一个bit对应VLAN 0,最后一个bit对应VLAN 4095。
        如果bit置位,表示该包括该VLAN,否则不包括。"
      ::= { portVlanAggregationConfigEntry 5 }

    
    aggregationRowStatus OBJECT-TYPE
      SYNTAX RowStatus
      MAX-ACCESS read-create
      STATUS current
      DESCRIPTION
        "
        行状态"
      ::= { portVlanAggregationConfigEntry 6 }
    
    portVlanTrunkTable OBJECT-TYPE
      SYNTAX SEQUENCE OF PortVlanTrunkEntry
      MAX-ACCESS not-accessible
      STATUS current
      DESCRIPTION
        "
        端口Vlan trunk表(VLAN Trunk表
        This table applies on OLT pon port, OLT SNI, OLT onu ID, ONU UNI.
        1. If the table is maintained in OLT device(OLT作为SNMP Agent):
        Applied Obj  - Descriptions of Index
        ------------------------------------------------------------------
        OLT Pon Port - OnuNum of pvtDeviceIndex shall be set to 0,
        /OLT SNI     pvtCardIndex, and pvtPortIndex set to 0 indicates
                 meaningless 
        OLT onu ID   - Set pvtDeviceIndex to corresponding ONU ID,
                 pvtCardIndex, and pvtPortIndex set to 0 indicates
                 meaningless        
        ONU UNI    - Set pvtDeviceIndex to corresponding ONU ID,
                 pvtCardIndex, and pvtPortIndex set to the corresponding 
                 value
        
        2. If the table is maintained in ONU device(ONU作为SNMP Agent):
        pvtDeviceIndex shall be set to 0 to indicate meaningless.
        pvtCardIndex shall be set to corresponding slot.
        pvtPortIndex shall be set to corresponding port.        
        "
      ::= { portVlanGroup 4 }
    
    portVlanTrunkEntry OBJECT-TYPE
      SYNTAX PortVlanTrunkEntry
      MAX-ACCESS not-accessible
      STATUS current
      DESCRIPTION
        " "
      INDEX { trunkDeviceIndex, trunkCardIndex, trunkPortIndex }
      ::= { portVlanTrunkTable 1 }
    
    PortVlanTrunkEntry ::=
      SEQUENCE {
        trunkDeviceIndex
          EponDeviceIndex,
        trunkCardIndex
          EponCardIndex,
        trunkPortIndex
          EponPortIndex,
        trunkVidList
          OCTET STRING,
        portVlanTrunkRowStatus
          RowStatus
       }

    trunkDeviceIndex OBJECT-TYPE
      SYNTAX EponDeviceIndex
      MAX-ACCESS not-accessible
      STATUS current
      DESCRIPTION
        "
        设备索引号。
        "
      ::= { portVlanTrunkEntry 1 }

    trunkCardIndex OBJECT-TYPE
      SYNTAX EponCardIndex
      MAX-ACCESS not-accessible
      STATUS current
      DESCRIPTION
        "
        板卡索引号"
      ::= { portVlanTrunkEntry 2 }
    trunkPortIndex  OBJECT-TYPE
      SYNTAX EponPortIndex
      MAX-ACCESS not-accessible
      STATUS current
      DESCRIPTION
        "
        端口索引号"
      ::= { portVlanTrunkEntry 3 }
                 
    trunkVidList OBJECT-TYPE
      SYNTAX OCTET STRING (SIZE (512))
      MAX-ACCESS read-create
      STATUS current
      DESCRIPTION
        "
        Trunked Vlan List for the port
数据行数为端口数量,vlan存储为一个4096位二进制,通过在第n位标记为1,表示vlan n在此端口透传。
        采用类似INTERNET比特顺序,从左到右的OCTET分别为OCTET 0, OCTET 1, ...
        每个OCTET的bit从左到右分别为bit0,bit1,...,bit7。
        按照bit和OCTET由小到大的顺序,每个bit对应于一个VLAN,VLAN ID范围为0..4095。
        第一个bit对应VLAN 0,最后一个bit对应VLAN 4095。
        如果bit置位,表示该包括该VLAN,否则不包括。
        

        "
      ::= { portVlanTrunkEntry 4 }
    
    portVlanTrunkRowStatus OBJECT-TYPE
      SYNTAX RowStatus
      MAX-ACCESS read-create
      STATUS current
      DESCRIPTION
        "
        行状态"
      ::= { portVlanTrunkEntry 5 }
    

    oltPortVlanTable OBJECT-TYPE
      SYNTAX SEQUENCE OF OltPortVlanEntry
      MAX-ACCESS not-accessible
      STATUS current
      DESCRIPTION
        "
        SNI/PON端口Vlan表        
        This table applies on OLT pon port, OLT SNI       
        Applied Obj  - Descriptions of Index
        ------------------------------------------------------------------
        OLT Pon Port/OLT SNI - OnuNum of pvlanDeviceIndex shall be set to 0
        "
      ::= { portVlanGroup 5 }
    
    oltPortVlanEntry OBJECT-TYPE
      SYNTAX OltPortVlanEntry
      MAX-ACCESS not-accessible
      STATUS current
      DESCRIPTION
        " "
      INDEX { oltPortVlanDeviceIndex	 }
      ::= { oltPortVlanTable 1 }
    
    OltPortVlanEntry  ::=
      SEQUENCE {
        oltPortVlanDeviceIndex	
          EponDeviceIndex,
        oltPortVlanTagPriority
          INTEGER,
        oltPortVlanPVid  
          INTEGER,
        oltPortVlanMode
          INTEGER
       }
  
    oltPortVlanDeviceIndex  OBJECT-TYPE
      SYNTAX EponDeviceIndex
      MAX-ACCESS not-accessible
      STATUS current
      DESCRIPTION
        "
        SNI/PON port "
      ::= { oltPortVlanEntry 1 }
    
    oltPortVlanTagPriority  OBJECT-TYPE
      SYNTAX INTEGER (0..7)
      MAX-ACCESS read-write
      STATUS current
      DESCRIPTION
        "
        vlan优先级"
      ::= { oltPortVlanEntry 2 }
    
    oltPortVlanPVid  OBJECT-TYPE
      SYNTAX INTEGER
      MAX-ACCESS read-write
      STATUS current
      DESCRIPTION
        "
        port Vlan ID"
      ::= { oltPortVlanEntry 3 }
    
    oltPortVlanMode OBJECT-TYPE
      SYNTAX INTEGER
        {
trunk(1),
access(2),
hybird(3)
        }
      MAX-ACCESS read-write
      STATUS current
      DESCRIPTION
        "
        vlan模式
        "
      ::= { oltPortVlanEntry 4 }



	-- QinQ 配置
    qinQConfigGroup OBJECT-IDENTITY
      STATUS current
      DESCRIPTION 
        "
        QinQ配置组
        备注：要求OLT/ONU均支持QINQ,OLT可选,ONU必选"
      ::= { vlanManagementObjects 4 }
    
    portQinQConfigTable OBJECT-TYPE
      SYNTAX SEQUENCE OF PortQinQConfigEntry
      MAX-ACCESS not-accessible
      STATUS current
      DESCRIPTION
        "
        QinQ配置属性表
        This table applies on OLT pon port, OLT SNI, OLT onu ID, ONU UNI.
        1. If the table is maintained in OLT device(OLT作为SNMP agent):
        Applied Obj  - Descriptions of Index
        ------------------------------------------------------------------
        OLT Pon Port - OnuNum of pqDeviceIndex shall be set to 0,
        /OLT SNI     pqCardIndex, and pqPortIndex set to 0 indicates
                 meaningless 
        OLT onu ID   - Set pqDeviceIndex to corresponding ONU ID,
                 pqCardIndex, and pqPortIndex set to 0 indicates
                 meaningless        
        ONU UNI    - Set pqDeviceIndex to corresponding ONU ID,
                   pqCardIndex, and pqPortIndex set to the corresponding 
                   value
           
        2. If the table is maintained in ONU device(ONU作为SNMP agent):
        pqDeviceIndex shall be set to 0 to indicate meaningless.
        pqCardIndex shall be set to corresponding slot.
        pqPortIndex shall be set to corresponding port.       
        "       
      ::= { qinQConfigGroup 1 }
    
    portQinQConfigEntry OBJECT-TYPE
      SYNTAX PortQinQConfigEntry
      MAX-ACCESS not-accessible
      STATUS current
      DESCRIPTION
        " "
      INDEX { pqDeviceIndex, pqCardIndex, pqPortIndex, pqStartVlanId, pqEndVlanId }
      ::= { portQinQConfigTable 1 }
    
    PortQinQConfigEntry ::=
      SEQUENCE { 
        pqDeviceIndex
          EponDeviceIndex,
        pqCardIndex
          EponCardIndex,
        pqPortIndex
          EponPortIndex,  
        pqStartVlanId
          INTEGER,
        pqEndVlanId 
          INTEGER,
        pqSVlanId
          INTEGER,
        pqSTagCosDetermine  
          INTEGER,
        pqSTagCosNewValue
          INTEGER,        
        pqRowStatus
          RowStatus 
       }
       
    pqDeviceIndex OBJECT-TYPE
      SYNTAX EponDeviceIndex
      MAX-ACCESS not-accessible
      STATUS current
      DESCRIPTION
        "
        设备索引号"
      ::= { portQinQConfigEntry 1 }

    pqCardIndex OBJECT-TYPE
      SYNTAX EponCardIndex
      MAX-ACCESS not-accessible
      STATUS current
      DESCRIPTION
        "
        板卡索引号"
      ::= { portQinQConfigEntry 2 }

    pqPortIndex  OBJECT-TYPE
      SYNTAX EponPortIndex
      MAX-ACCESS not-accessible
      STATUS current
      DESCRIPTION
        "
        端口索引号"
      ::= { portQinQConfigEntry 3 }
                          
    pqStartVlanId OBJECT-TYPE
      SYNTAX INTEGER
      MAX-ACCESS not-accessible
      STATUS current
      DESCRIPTION
        "
        The starting VLAN ID, working together with pqEndVlanId,
        consists of a VLAN group. The VLAN ID match the VLAN group
        will be QinQed with specified outer VLAN
        "                   
      ::= { portQinQConfigEntry 4 }

    pqEndVlanId OBJECT-TYPE
      SYNTAX INTEGER
      MAX-ACCESS not-accessible
      STATUS current
      DESCRIPTION
        "
        The ending VLAN ID, working together with pqStartVlanId,
        consists of a VLAN range. The VLAN ID match the VLAN range
        will be QinQed with specified outer VLAN
        "
      ::= { portQinQConfigEntry 5 }
  
    pqSVlanId OBJECT-TYPE
      SYNTAX INTEGER
      MAX-ACCESS read-create
      STATUS current
      DESCRIPTION
        "
        The outer VLAN id to be QinQed"
      ::= { portQinQConfigEntry 6 }
    
    pqSTagCosDetermine OBJECT-TYPE
      SYNTAX INTEGER {
        redefine(1),
        copyFromCTag(2)
        }
      MAX-ACCESS read-create
      STATUS current
      DESCRIPTION
        "
        What STAG COS will be set for this QinQ instance. It could
        be either a new definition or copied from CTAG
        "
      ::= { portQinQConfigEntry 7 }

    pqSTagCosNewValue OBJECT-TYPE
      SYNTAX INTEGER (0..7)     
      MAX-ACCESS read-create
      STATUS current
      DESCRIPTION
        "
        The new STAG COS value if pqSTagCosDetermine is selected as
        redefine(1)
        "
      DEFVAL { 0 }
      ::= { portQinQConfigEntry 8 }

    pqRowStatus OBJECT-TYPE
      SYNTAX RowStatus      
      MAX-ACCESS read-create
      STATUS current
      DESCRIPTION
        "
        "
      ::= { portQinQConfigEntry 9 }

--------------------------------------------------------------------------------
--  qosManagementObjects[ Qos管理项](1.3.6.1.4.1.17409.2.3.8)
-------------------------------------------------------------------------------- 

    qosGlobalSetTable OBJECT-TYPE
      SYNTAX SEQUENCE OF QosGlobalSetEntry
      MAX-ACCESS not-accessible
      STATUS current
      DESCRIPTION
        "Global QoS parameters."
      ::= { qosManagementObjects 1 }
    
    qosGlobalSetEntry OBJECT-TYPE
      SYNTAX QosGlobalSetEntry
      MAX-ACCESS not-accessible
      STATUS current
      DESCRIPTION
        ""
      INDEX { qosGlobalSetDeviceIndex }
      ::= { qosGlobalSetTable 1 }    
    QosGlobalSetEntry ::=
      SEQUENCE { 
        qosGlobalSetDeviceIndex
          EponDeviceIndex,
        qosGlobalSetMaxQueueCount
          INTEGER,
        qosGlobalSetMode
          INTEGER
       }

    qosGlobalSetDeviceIndex OBJECT-TYPE
      SYNTAX EponDeviceIndex
      MAX-ACCESS not-accessible
      STATUS current
      DESCRIPTION
        "
        Device index        
        For OLT Agent- Set to corresponding device
        For ONU Agent - Set to 0
        "
      ::= { qosGlobalSetEntry 1 }
    
    qosGlobalSetMaxQueueCount OBJECT-TYPE
      SYNTAX INTEGER (1..256)
      MAX-ACCESS read-only
      STATUS current
      DESCRIPTION
        "
        最大队列数,该设备支持的最大队列数。如果最大队列数为8,则队列编号为0-7。"
      ::= { qosGlobalSetEntry 2 }

    qosGlobalSetMode OBJECT-TYPE
      SYNTAX INTEGER 
        {
          deviceBased(1),
          portBased(2)
        }
      MAX-ACCESS read-write
      STATUS current
      DESCRIPTION
        "
        Define how to set QoS parameter
        deviceBased(1)  - When set, only the table started with deviceBase is applicable
        portBased(2)  - When set, only the table started with portBase is applicable
        "
      ::= { qosGlobalSetEntry 3 }
    
    deviceBaseQosMapTable OBJECT-TYPE
      SYNTAX SEQUENCE OF DeviceBaseQosMapEntry
      MAX-ACCESS not-accessible
      STATUS current
      DESCRIPTION
        "Deviced based setting.        
        It is used to define how to map QoS options to queue"
      ::= { qosManagementObjects 2 }
    
    deviceBaseQosMapEntry OBJECT-TYPE
      SYNTAX DeviceBaseQosMapEntry
      MAX-ACCESS not-accessible
      STATUS current
      DESCRIPTION
        ""
      INDEX { deviceBaseQosMapDeviceIndex, deviceBaseQosMapRuleIndex }
      ::= { deviceBaseQosMapTable 1 }
    
    DeviceBaseQosMapEntry ::=
      SEQUENCE { 
        deviceBaseQosMapDeviceIndex
          EponDeviceIndex,
        deviceBaseQosMapRuleIndex
          INTEGER,
        deviceBaseQosMapOctet
          OCTET STRING
       }

    deviceBaseQosMapDeviceIndex OBJECT-TYPE
      SYNTAX EponDeviceIndex
      MAX-ACCESS not-accessible
      STATUS current
      DESCRIPTION
        "
        Device index        
        For OLT Agent - Set to corresponding device/slot/port
        For ONU Agent - Set to 0

        "
      ::= { deviceBaseQosMapEntry 1 }
    
    deviceBaseQosMapRuleIndex OBJECT-TYPE
      SYNTAX INTEGER
        {
        cos(1),
        tos(2),
        diffserv(3)
        }
      MAX-ACCESS not-accessible
      STATUS current
      DESCRIPTION
        "
        映射规则编号"
      ::= { deviceBaseQosMapEntry 2 }
    
    deviceBaseQosMapOctet OBJECT-TYPE
      SYNTAX OCTET STRING (SIZE (8 | 64))
      MAX-ACCESS read-write
      STATUS current
      DESCRIPTION
        "
        映射值。
        长度为8字节,或64字节。每字节表示一个映射关系。
        队列编号不能超过对应的qosGlobalSetMaxQueueCount值,如果qosGlobalSetMaxQueueCount为8,则队列编号为0-7。        
        对于 cos,长度为 8字节,每个字节分别表示cos0-7 映射到的队列编号。
        对于 tos,长度为 16字节,每个字节分别表示tos0-15 映射到的队列编号。
        对于 diffserv,长度为64字节,每个字节分别表示diffserv0-63映射到的队列编号。        
        举例如下：
        get 1.3.6.1.4.1.17409.2.3.8.3.1.3.deviceBaseQosMapDeviceIndex(410100101).cos(1) = hex(00 00 01 02 03 03 04 04)
        则映射关系为：
        cos 0 -> queue 0
        cos 1 -> queue 0
        cos 2 -> queue 1
        cos 3 -> queue 2
        cos 4 -> queue 3
        cos 5 -> queue 3
        cos 6 -> queue 4
        cos 7 -> queue 4
        "
      ::= { deviceBaseQosMapEntry 3 }    

    deviceBaseQosPolicyTable OBJECT-TYPE
      SYNTAX SEQUENCE OF DeviceBaseQosPolicyEntry
      MAX-ACCESS not-accessible
      STATUS current
      DESCRIPTION
        "Deviced based setting
        
        It is used to define QoS specification"
      ::= { qosManagementObjects 3 }
    
    deviceBaseQosPolicyEntry OBJECT-TYPE
      SYNTAX DeviceBaseQosPolicyEntry
      MAX-ACCESS not-accessible
      STATUS current
      DESCRIPTION
        ""
      INDEX { deviceBaseQosPolicyDeviceIndex }
      ::= { deviceBaseQosPolicyTable 1 }
    
    DeviceBaseQosPolicyEntry ::=
      SEQUENCE { 
        deviceBaseQosPolicyDeviceIndex
          EponDeviceIndex,
        deviceBaseQosPolicyMode
          INTEGER,
        deviceBaseQosPolicyWeightOctet
          OCTET STRING,
        deviceBaseQosPolicySpBandwidthRange
          OCTET STRING
       }

    deviceBaseQosPolicyDeviceIndex OBJECT-TYPE
      SYNTAX EponDeviceIndex
      MAX-ACCESS not-accessible
      STATUS current
      DESCRIPTION
        "
        Device index        
        For OLT Agent - Set to corresponding device/slot/port
        For ONU Agent - Set to 0
        "
      ::= { deviceBaseQosPolicyEntry 1 }
    
    deviceBaseQosPolicyMode OBJECT-TYPE
      SYNTAX INTEGER
        {
        sp(1),
        wrr(2),
        spWrr(3),
        wfp(4)
        }
      MAX-ACCESS read-write
      STATUS current
      DESCRIPTION
        "
        调度模式"
      ::= { deviceBaseQosPolicyEntry 2 }
    
    deviceBaseQosPolicyWeightOctet OBJECT-TYPE
      SYNTAX OCTET STRING
      MAX-ACCESS read-write
      STATUS current
      DESCRIPTION
        "
        权重值。        
        长度等于队列数目,每字节表示一个队列的权重。
        对于 sp,读写该节点无意义,读时始终为全0。
        对于 wrr,每字节描述一个队列的权重。权重的范围为1-100,全部队列权重之和应等于100。
        对于 spWrr,每字节描述一个队列的权重。权重范围为0-100,权重为0表示该队列用sp模式,权重值非0的队列权重之和应等于100。
        对于 wfp,读写该节点无意义,读时始终为全0。        
        举例如下：
        get 1.3.6.1.4.1.17409.2.3.8.4.1.2.deviceBaseQosPolicyDeviceIndex(410100101). = wrr(2)
        get 1.3.6.1.4.1.17409.2.3.8.4.1.3.deviceBaseQosPolicyDeviceIndex(410100101). = hex(5 5 5 5 10 20 20 30)
        
        说明：共8个队列
        queue 0 权重为 5
        queue 1 权重为 5
        queue 2 权重为 5
        queue 3 权重为 5
        queue 4 权重为 10
        queue 5 权重为 20
        queue 6 权重为 20
        queue 7 权重为 30
        
        "
      ::= { deviceBaseQosPolicyEntry 3 }
    
    deviceBaseQosPolicySpBandwidthRange OBJECT-TYPE
      SYNTAX OCTET STRING
      MAX-ACCESS read-write
      STATUS current
      DESCRIPTION
        "
        Define SP assured bandwidth for each queue.        
        The size of this object is 4*(number of queue). For each queue, use 4 octets 
        to represend the assured bandwidth for the queue. The four-octet could be mapped
        to an unsigned integer, in units of kbps. The sequence of the map is from queue 
        0 to queue max (for example, 7).        
        For example, 00 00 00 10  00 00 01 00  00 00 00 00  00 00 00 00
                     00 00 10 00  00 00 00 01  00 01 01 00  00 00 11 11                     
        It means, 8 queues and the assured bandwidth for each queue as:        
        queue 0  16kbps
        queue 1  256kbps
        queue 2  0 
        queue 3  0
        queue 4  4096kbps
        queue 5  1kbps
        queue 6  65792kbps
        queue 7  65535kbps
        "
      ::= { deviceBaseQosPolicyEntry 4 }
    
    portBaseQosMapTable OBJECT-TYPE
      SYNTAX SEQUENCE OF PortBaseQosMapEntry
      MAX-ACCESS not-accessible
      STATUS current
      DESCRIPTION
        ""
      ::= { qosManagementObjects 4 }
    
    portBaseQosMapEntry OBJECT-TYPE
      SYNTAX PortBaseQosMapEntry
      MAX-ACCESS not-accessible
      STATUS current
      DESCRIPTION
        ""
      INDEX { portBaseQosMapDeviceIndex, portBaseQosMapCardIndex, portBaseQosMapPortIndex, portBaseQosMapRuleIndex }
      ::= { portBaseQosMapTable 1 }
    
    PortBaseQosMapEntry ::=
      SEQUENCE { 
        portBaseQosMapDeviceIndex
          EponDeviceIndex,
        portBaseQosMapCardIndex
          EponPortIndex,
        portBaseQosMapPortIndex
          EponPortIndex,
        portBaseQosMapRuleIndex
          INTEGER,
        portBaseQosMapOctet
          OCTET STRING
       }

    portBaseQosMapDeviceIndex OBJECT-TYPE
      SYNTAX EponDeviceIndex
      MAX-ACCESS not-accessible
      STATUS current
      DESCRIPTION
        "
        Device index        
        For OLT Agent, set to corresponding SNI port or PON port
        For ONU Agent, set to 0

        "
      ::= { portBaseQosMapEntry 1 }
    
    portBaseQosMapCardIndex OBJECT-TYPE
      SYNTAX EponPortIndex
      MAX-ACCESS not-accessible
      STATUS current
      DESCRIPTION
        "
        板卡索引号        
        For OLT Agent, set to 0
        For ONU Agent, set to corresponding slot
        "
      ::= { portBaseQosMapEntry 2 }
    
    portBaseQosMapPortIndex OBJECT-TYPE
      SYNTAX EponPortIndex
      MAX-ACCESS not-accessible
      STATUS current
      DESCRIPTION
        "
        端口索引        
        For OLT Agent, set to 0
        For ONU Agent, set to corresponding port
        "
      ::= { portBaseQosMapEntry 3 }
    
    portBaseQosMapRuleIndex OBJECT-TYPE
      SYNTAX INTEGER
        {
        cos(1),
        tos(2),
        diffserv(3)
        }
      MAX-ACCESS not-accessible
      STATUS current
      DESCRIPTION
        "
        映射规则编号"
      ::= { portBaseQosMapEntry 4 }
    
    portBaseQosMapOctet OBJECT-TYPE
      SYNTAX OCTET STRING (SIZE (8..64))
      MAX-ACCESS read-write
      STATUS current
      DESCRIPTION
        "
        映射值。
        长度为8字节,或64字节。每字节表示一个映射关系。
        队列编号不能超过对应的qosGlobalSetMaxQueueCount值,如果qosGlobalSetMaxQueueCount为8,则队列编号为0-7。        
        对于 cos,长度为 8字节,每个字节分别表示cos0-7 映射到的队列编号。
        对于 tos,长度为 16字节,每个字节分别表示tos0-16 映射到的队列编号。
        对于 diffserv,长度为64字节,每个字节分别表示diffserv0-64映射到的队列编号。        
        举例如下：
        get 1.3.6.1.4.1.17409.2.3.8.3.1.3.deviceBaseQosMapDeviceIndex(410100101).cos(1) = hex(00 00 01 02 03 03 04 04)
        则映射关系为：
        cos 0 -> queue 0
        cos 1 -> queue 0
        cos 2 -> queue 1
        cos 3 -> queue 2
        cos 4 -> queue 3
        cos 5 -> queue 3
        cos 6 -> queue 4
        cos 7 -> queue 4
        "
      ::= { portBaseQosMapEntry 5 }
    
    portBaseQosPolicyTable OBJECT-TYPE
      SYNTAX SEQUENCE OF PortBaseQosPolicyEntry
      MAX-ACCESS not-accessible
      STATUS current
      DESCRIPTION
        "Description."
      ::= { qosManagementObjects 5 }
    
    portBaseQosPolicyEntry OBJECT-TYPE
      SYNTAX PortBaseQosPolicyEntry
      MAX-ACCESS not-accessible
      STATUS current
      DESCRIPTION
        ""
      INDEX { portBaseQosPolicyDeviceIndex, portBaseQosPolicyCardIndex, portBaseQosPolicyPortIndex }
      ::= { portBaseQosPolicyTable 1 }
    
    PortBaseQosPolicyEntry ::=
      SEQUENCE { 
        portBaseQosPolicyDeviceIndex
          EponDeviceIndex,
        portBaseQosPolicyCardIndex
          EponPortIndex,
        portBaseQosPolicyPortIndex
          EponPortIndex,
        portBaseQosPolicyMode
          INTEGER,
        portBaseQosPolicyWeightOctet
          OCTET STRING,
        portBaseQosPolicySpBandwidthRange
          OCTET STRING
       }
    portBaseQosPolicyDeviceIndex OBJECT-TYPE
      SYNTAX EponDeviceIndex
      MAX-ACCESS not-accessible
      STATUS current
      DESCRIPTION
        "
        Device index
        For OLT Agent, set to corresponding SNI port or PON port
        For ONU Agent, set to 0

        "
      ::= { portBaseQosPolicyEntry 1 }
    
    portBaseQosPolicyCardIndex OBJECT-TYPE
      SYNTAX EponPortIndex
      MAX-ACCESS not-accessible
      STATUS current
      DESCRIPTION
        "
        板卡索引号        
        For OLT Agent, set to 0
        For ONU Agent, set to corresponding slot
        "
      ::= { portBaseQosPolicyEntry 2 }
    
    portBaseQosPolicyPortIndex OBJECT-TYPE
      SYNTAX EponPortIndex
      MAX-ACCESS not-accessible
      STATUS current
      DESCRIPTION
        "
        端口索引        
        For OLT Agent, set to 0
        For ONU Agent, set to corresponding port
        "
      ::= { portBaseQosPolicyEntry 3 }
    
    portBaseQosPolicyMode OBJECT-TYPE
      SYNTAX INTEGER
        {
        sp(1),
        wrr(2),
        spWrr(3),
        wfp(4)
        }
      MAX-ACCESS read-write
      STATUS current
      DESCRIPTION
        "
        调度模式        
        sp 严格优先级
        wrr 加权轮循
        spWrr sp+wrr混合
        wfp 加权公平排队"
      ::= { portBaseQosPolicyEntry 4 }
    
    portBaseQosPolicyWeightOctet OBJECT-TYPE
      SYNTAX OCTET STRING (SIZE (1..256))
      MAX-ACCESS read-write
      STATUS current
      DESCRIPTION
        "
        权重值        
        长度等于队列数目,每字节表示一个队列的权重。        
        对于 sp,读写该节点无意义,读时始终为全0。
        对于 wrr,每字节描述一个队列的权重。权重的范围为1-100,全部队列权重之和应等于100。
        对于 spWrr,每字节描述一个队列的权重。权重范围为0-100,权重为0表示该队列用sp模式,权重值非0的队列权重之和应等于100。
        对于 wfp,读写该节点无意义,读时始终为全0。        
        举例如下：
        get 1.3.6.1.4.1.17409.2.3.8.4.1.2.portBaseQosPolicyDeviceIndex(410100101). = wrr(2)
        get 1.3.6.1.4.1.17409.2.3.8.4.1.3.portBaseQosPolicyDeviceIndex(410100101). = hex(5 5 5 5 10 20 20 30)        
        说明：共8个队列
        queue 0 权重为 5
        queue 1 权重为 5
        queue 2 权重为 5
        queue 3 权重为 5
        queue 4 权重为 10
        queue 5 权重为 20
        queue 6 权重为 20
        queue 7 权重为 30        
        "
      ::= { portBaseQosPolicyEntry 5 }
    
    portBaseQosPolicySpBandwidthRange OBJECT-TYPE
      SYNTAX OCTET STRING
      MAX-ACCESS read-write
      STATUS current
      DESCRIPTION
        "     
        Sp+wrr模式下使用
        Define SP assured bandwidth for each queue.        
        The size of this object is 4*(number of queue). For each queue, use 4 octets 
        to represend the assured bandwidth for the queue. The four-octet could be mapped
        to an unsigned integer, in units of kbps. The sequence of the map is from queue 
        0 to queue max (for example, 7).        
        For example, 00 00 00 10  00 00 01 00  00 00 00 00  00 00 00 00
                     00 00 10 00  00 00 00 01  00 01 01 00  00 00 11 11                     
        It means, 8 queues and the assured bandwidth for each queue as:        
        queue 0  16kbps
        queue 1  256kbps
        queue 2  0 
        queue 3  0
        queue 4  4096kbps
        queue 5  1kbps
        queue 6  65792kbps
        queue 7  65535kbps
        "
      ::= { portBaseQosPolicyEntry 6 }


--------------------------------------------------------------------------------
--  stpManagementObjects[STP管理项](1.3.6.1.4.1.17409.2.3.9)
-------------------------------------------------------------------------------- 

    stpGlobalSetTable OBJECT-TYPE
      SYNTAX SEQUENCE OF StpGlobalSetEntry
      MAX-ACCESS not-accessible
      STATUS current
      DESCRIPTION
        "
        STP全局表"
      ::= { stpManagementObjects 1 }
    
    stpGlobalSetEntry OBJECT-TYPE
      SYNTAX StpGlobalSetEntry
      MAX-ACCESS not-accessible
      STATUS current
      DESCRIPTION
        ""
      INDEX { stpGlobalSetIndex }
      ::= { stpGlobalSetTable 1 }
    
    StpGlobalSetEntry ::=
      SEQUENCE { 
        stpGlobalSetIndex
          EponDeviceIndex,
        stpGlobalSetVersion
          INTEGER,
        stpGlobalSetPriority
          INTEGER,
        stpGlobalSetTimeSinceTopologyChange
          TimeTicks,
        stpGlobalSetTopChanges
          Counter32,
        stpGlobalSetDesignatedRoot
          BridgeId,
        stpGlobalSetRootCost
          INTEGER,
        stpGlobalSetRootPort
          OCTET STRING,
        stpGlobalSetMaxAge
          Timeout,
        stpGlobalSetHelloTime
          Timeout,
        stpGlobalSetHoldTime
          INTEGER,
        stpGlobalSetForwardDelay
          Timeout,
        stpGlobalSetBridgeMaxAge
          Timeout,
        stpGlobalSetBridgeHelloTime
          Timeout,
        stpGlobalSetBridgeForwardDelay
          Timeout,
        stpGlobalSetRstpTxHoldCount
          INTEGER,
        stpGlobalSetEnable
          TruthValue
       }

    stpGlobalSetIndex OBJECT-TYPE
      SYNTAX EponDeviceIndex
      MAX-ACCESS not-accessible
      STATUS current
      DESCRIPTION
        "
        索引号        
        For OLT Agent - Set to corresponding device
        For ONU Agent - Set to 0
        "
      ::= { stpGlobalSetEntry 1 }
    
    stpGlobalSetVersion OBJECT-TYPE
      SYNTAX INTEGER
        {
        rstp(1),
        stp(2)
        }
      MAX-ACCESS read-write
      STATUS current
      DESCRIPTION
        "
        生成树协议版本。"
      DEFVAL { rstp }
      ::= { stpGlobalSetEntry 2 }
    
    stpGlobalSetPriority OBJECT-TYPE
      SYNTAX INTEGER (0..65535)
      MAX-ACCESS read-write
      STATUS current
      DESCRIPTION
        "
        优先级。
        在支持IEEE 802.1d或者IEEE 802.1w的网桥上,取值范围是0-61440,步长是4096。"
      ::= { stpGlobalSetEntry 3 }
    
    stpGlobalSetTimeSinceTopologyChange OBJECT-TYPE
      SYNTAX TimeTicks
      MAX-ACCESS read-only
      STATUS current
      DESCRIPTION
        "
        变更时间,网桥实体检测到最近一次拓扑改变之后经历的时间。"
      ::= { stpGlobalSetEntry 4 }    
    stpGlobalSetTopChanges OBJECT-TYPE
      SYNTAX Counter32
      UNITS "topology changes"
      MAX-ACCESS read-only
      STATUS current
      DESCRIPTION
        "
        变更次数,网桥重启或初始化化拓扑的变更次数。"
      ::= { stpGlobalSetEntry 5 }
    
    stpGlobalSetDesignatedRoot OBJECT-TYPE
      SYNTAX BridgeId
      MAX-ACCESS read-only
      STATUS current
      DESCRIPTION
        "
        根桥,指定根桥的BridgeId。"
      ::= { stpGlobalSetEntry 6 }
    
    stpGlobalSetRootCost OBJECT-TYPE
      SYNTAX INTEGER
      MAX-ACCESS read-only
      STATUS current
      DESCRIPTION
        "
        根路径开销,网桥到根桥的路径消耗。"
      ::= { stpGlobalSetEntry 7 }
    
    stpGlobalSetRootPort OBJECT-TYPE
      SYNTAX OCTET STRING  (SIZE (3))
      MAX-ACCESS read-only
      STATUS current
      DESCRIPTION
        "
        根端口,是连接本网桥和根网桥的端口,它提供的路径消耗最小
        The port is presented by three octets, in sequence of device ID, slot,
        and port.
        For ONU Agent, device ID is meaningless and shall set 0. Slot and port shall
        be set to corresponding value.
        For OLT Agent, device ID, slot, and port shall be set to corresponding value.
        For example, 
        01 02 03 means device 1, slot 2, port 3 is root port.
        0x00 04 05 means ONU slot 4, port 5 is root port.
        "
      ::= { stpGlobalSetEntry 8 }
    
    stpGlobalSetMaxAge OBJECT-TYPE
      SYNTAX Timeout
      UNITS "centi-seconds"
      MAX-ACCESS read-only
      STATUS current
      DESCRIPTION
        "
        老化时间,端口从网络中学习到的生成树协议信息的老化时间,单位：1/100 secs。"
      ::= { stpGlobalSetEntry 9 }
    
    stpGlobalSetHelloTime OBJECT-TYPE
      SYNTAX Timeout
      UNITS "centi-seconds"
      MAX-ACCESS read-only
      STATUS current
      DESCRIPTION
        "
        报文发送间隔,网桥在任意端口发送配置网桥PDU的时间间隔。"
      ::= { stpGlobalSetEntry 10 }
    
    stpGlobalSetHoldTime OBJECT-TYPE
      SYNTAX INTEGER
      UNITS "centi-seconds"
      MAX-ACCESS read-only
      STATUS current
      DESCRIPTION
        "
        维持时间,在这个时间间隔内,本网桥不会发送两个以上配置网桥PDU。"
      ::= { stpGlobalSetEntry 11 }
    
    stpGlobalSetForwardDelay OBJECT-TYPE
      SYNTAX Timeout
      UNITS "centi-seconds"
      MAX-ACCESS read-only
      STATUS current
      DESCRIPTION
        "
        转换时延,控制一个端口多快地改变自己的生成状态,决定了本端口开始转发前,在监听状态和学习状态滞留多长时间。
        当一个发现一个拓扑变更,并且正在处理时,这个值也用来控制动态过滤表的老化时间。
        "
      ::= { stpGlobalSetEntry 12 }
    
    stpGlobalSetBridgeMaxAge OBJECT-TYPE
      SYNTAX Timeout (600..4000)
      UNITS "centi-seconds"
      MAX-ACCESS read-write
      STATUS current
      DESCRIPTION
        "
        如果本网桥是根网桥,那么所有网桥把这个值用作老化时间。"
      ::= { stpGlobalSetEntry 13 }
    
    stpGlobalSetBridgeHelloTime OBJECT-TYPE
      SYNTAX Timeout (100..1000)
      UNITS "centi-seconds"
      MAX-ACCESS read-write
      STATUS current
      DESCRIPTION
        "
        如果本网桥是根网桥,那么所有网桥把这个值用作报文发送的时间间隔。"
      ::= { stpGlobalSetEntry 14 }
    
    stpGlobalSetBridgeForwardDelay OBJECT-TYPE
      SYNTAX Timeout (400..3000)
      UNITS "centi-seconds"
      MAX-ACCESS read-write
      STATUS current
      DESCRIPTION
        "
        如果本网桥是根网桥,那么所有网桥把这个值用于转换时延。"
      ::= { stpGlobalSetEntry 15 }
    
    stpGlobalSetRstpTxHoldCount OBJECT-TYPE
      SYNTAX INTEGER (1..10)
      MAX-ACCESS read-write
      STATUS current
      DESCRIPTION
        "
        传输限速,对RSTP,用于限制端口的报文发送速率。"
      DEFVAL { 3 }
      ::= { stpGlobalSetEntry 16 }
    
    stpGlobalSetEnable OBJECT-TYPE
      SYNTAX TruthValue
      MAX-ACCESS read-write
      STATUS current
      DESCRIPTION
        "
        使能状态,启用或关闭STP。true(1)为开启。"
      ::= { stpGlobalSetEntry 17 }
    
    stpPortTable OBJECT-TYPE
      SYNTAX SEQUENCE OF StpPortEntry
      MAX-ACCESS not-accessible
      STATUS current
      DESCRIPTION
        "
        STP端口表"
      ::= { stpManagementObjects 2 }
    
    stpPortEntry OBJECT-TYPE
      SYNTAX StpPortEntry
      MAX-ACCESS not-accessible
      STATUS current
      DESCRIPTION
        ""
      INDEX { stpPortStpIndex, stpPortCardIndex, stpPortIndex }
      ::= { stpPortTable 1 }
    
    StpPortEntry ::=
      SEQUENCE { 
        stpPortStpIndex
          EponDeviceIndex,
        stpPortCardIndex
          EponCardIndex,
        stpPortIndex
          EponPortIndex,
        stpPortStatus
          INTEGER,
        stpPortPriority
          INTEGER,
        stpPortPathCost
          INTEGER,
        stpPortDesignatedRoot
          BridgeId,
        stpPortDesignatedCost
          INTEGER,
        stpPortDesignatedBridge
          BridgeId,
        stpPortDesignatedPort
          Gauge32,
        stpPortForwardTransitions
          Unsigned32,
        stpPortRstpProtocolMigration
          TruthValue,
        stpPortRstpAdminEdgePort
          TruthValue,
        stpPortRstpOperEdgePort
          TruthValue,
        stpPortPointToPointAdminStatus
          INTEGER,
        stpPortPointToPointOperStatus
          TruthValue,
        stpPortEnabled
          TruthValue
       }

    stpPortStpIndex OBJECT-TYPE
      SYNTAX EponDeviceIndex
      MAX-ACCESS not-accessible
      STATUS current
      DESCRIPTION
        "
        索引号。        
        For OLT Agent - Set to corresponding device/SLOT/PORT
        For ONU Agent - Set to 0
        "
      ::= { stpPortEntry 1 }
    
    stpPortCardIndex OBJECT-TYPE
      SYNTAX EponCardIndex
      MAX-ACCESS not-accessible
      STATUS current
      DESCRIPTION
        "
        Epon板卡索引号        
        For OLT Agent, set to 0
        For ONU Agent, set to correspond card index"
      ::= { stpPortEntry 2 }
    
    stpPortIndex OBJECT-TYPE
      SYNTAX EponPortIndex
      MAX-ACCESS not-accessible
      STATUS current
      DESCRIPTION
        "
        端口号,对OLT为SNI/PON port,对ONU为UNI端口号。        
        For OLT Agent, set to 0
        For ONU Agent, set to correspond port index"
      ::= { stpPortEntry 3 }
    
    stpPortStatus OBJECT-TYPE
      SYNTAX INTEGER
        {
        disabled(1),
        blocking(2),
        listening(3),
        learning(4),
        forwarding(5),
        broken(6)
        }
      MAX-ACCESS read-only
      STATUS current
      DESCRIPTION
        "
端口状态,由生成树协议的应用程序定义,对于被禁用STP的端口,这个状态应该为disable。"
      ::= { stpPortEntry 4 }
    
    stpPortPriority OBJECT-TYPE
      SYNTAX INTEGER (0..255)
      MAX-ACCESS read-write
      STATUS current
      DESCRIPTION
        "
        端口优先级"
      ::= { stpPortEntry 5 }
    
    stpPortPathCost OBJECT-TYPE
      SYNTAX INTEGER (1..200000000)
      MAX-ACCESS read-write
      STATUS current
      DESCRIPTION
        "
端口路径开销,本端口在通往生成树根的路径上增加的路径消耗802.1D-1998推荐这个参数的默认值跟连接LAN的速度成反比。"
      ::= { stpPortEntry 6 }
    
    stpPortDesignatedRoot OBJECT-TYPE
      SYNTAX BridgeId
      MAX-ACCESS read-only
      STATUS current
      DESCRIPTION
        "
指定根网桥,在配置BPDU中被记录为根的网桥的标识符,这些配置BPDU由指定网桥发送,而指定网桥用于跟这个端口相连的网段。"
      ::= { stpPortEntry 7 }
    
    stpPortDesignatedCost OBJECT-TYPE
      SYNTAX INTEGER
      MAX-ACCESS read-only
      STATUS current
      DESCRIPTION
        "
指定路径开销,跟本端口相连的网段的指定端口的路径消耗,这个值会跟接受到的网桥PDU中的根路径消耗字段进行比较。"
      ::= { stpPortEntry 8 }
    
    stpPortDesignatedBridge OBJECT-TYPE
      SYNTAX BridgeId
      MAX-ACCESS read-only
      STATUS current
      DESCRIPTION
        "
        指定网桥ID,本端口认为的本端口的网段的指定网桥的标识符。"
      ::= { stpPortEntry 9 }
    
    stpPortDesignatedPort OBJECT-TYPE
      SYNTAX Gauge32
      MAX-ACCESS read-only
      STATUS current
      DESCRIPTION
        "
        指定端口,指定网桥上用于本端口网段的端口的标识符。"
      ::= { stpPortEntry 10 }
    
    stpPortForwardTransitions OBJECT-TYPE
      SYNTAX Unsigned32
      UNITS "seconds"
      MAX-ACCESS read-only
      STATUS current
      DESCRIPTION
        "
        本端口已经从学习状态转变到转发状态的时间。"
      ::= { stpPortEntry 11 }
    
    stpPortRstpProtocolMigration OBJECT-TYPE
      SYNTAX TruthValue
      MAX-ACCESS read-write
      STATUS current
      DESCRIPTION
        "
协议迁移,如果操作在RSTP模式,将这个节点设置为TRUE(1)会强制这个端口发送RSTP BPDU,读操作无意,总返回FALSE(2)。"
      ::= { stpPortEntry 12 }
    
    stpPortRstpAdminEdgePort OBJECT-TYPE
      SYNTAX TruthValue
      MAX-ACCESS read-write
      STATUS current
      DESCRIPTION
        "
边缘端口管理状态,指定该端口是否为边缘端口,设置该节点将导致相应的stpPortRstpOperEdgePort节点设置成同样的值。
        当设置成true(1),但端口上收到一个BPDU时,stpPortRstpOperEdgePort将变成false(2)。
        "
      ::= { stpPortEntry 13 }
    
    stpPortRstpOperEdgePort OBJECT-TYPE
      SYNTAX TruthValue
      MAX-ACCESS read-only
      STATUS current
      DESCRIPTION
        "
边缘端口状态,这个节点被初始化成stpPortRstpAdminEdgePort的值,接收到一个BPDU时被设置成false(2)。"
      ::= { stpPortEntry 14 }    
    stpPortPointToPointAdminStatus OBJECT-TYPE
      SYNTAX INTEGER
        {
        forceFalse(0),
        forceTrue(1),
        auto(2)
        }
      MAX-ACCESS read-write
      STATUS current
      DESCRIPTION
        "
        连接到本端口网段的点对点管理状态。"
      ::= { stpPortEntry 15 }
    
    stpPortPointToPointOperStatus OBJECT-TYPE
      SYNTAX TruthValue
      MAX-ACCESS read-only
      STATUS current
      DESCRIPTION
        "
        连接到本端口网段的点对点实际状态。"
      ::= { stpPortEntry 16 }
    
    stpPortEnabled OBJECT-TYPE
      SYNTAX TruthValue
      MAX-ACCESS read-write
      STATUS current
      DESCRIPTION
        "
        端口使能状态,true(1)为开启。"
      ::= { stpPortEntry 17 }
   
--------------------------------------------------------------------------------
--  performanceStatisticObjects[性能统计属性管理项](1.3.6.1.4.1.17409.2.3.10)
-------------------------------------------------------------------------------- 
        
    curStatsTable OBJECT-TYPE
      SYNTAX SEQUENCE OF CurStatsEntry
      MAX-ACCESS not-accessible
      STATUS current
      DESCRIPTION
        "实时性能"
      ::= { performanceStatisticObjects 1 }        
    curStatsEntry OBJECT-TYPE
      SYNTAX CurStatsEntry
      MAX-ACCESS not-accessible
      STATUS current
      DESCRIPTION
        "实时性能"
      INDEX { curStatsDeviceIndex, curStatsCardIndex, curStatsPortIndex }
      ::= { curStatsTable 1 }
        
    CurStatsEntry ::=
      SEQUENCE { 
        curStatsDeviceIndex
          EponDeviceIndex,
        curStatsCardIndex
          EponCardIndex,
        curStatsPortIndex
          EponPortIndex,
        curStatsInOctets
          Counter64,
        curStatsInPkts
          Counter64,
        curStatsInBroadcastPkts
          Counter64,
        curStatsInMulticastPkts
          Counter64,
        curStatsInPkts64Octets
          Counter64,
        curStatsInPkts65to127Octets
          Counter64,
        curStatsInPkts128to255Octets
          Counter64,
        curStatsInPkts256to511Octets
          Counter64,
        curStatsInPkts512to1023Octets
          Counter64,
        curStatsInPkts1024to1518Octets
          Counter64,
        curStatsInPkts1519to1522Octets
          Counter64,
        curStatsInUndersizePkts
          Counter64,
        curStatsInOversizePkts
          Counter64,
        curStatsInFragments
          Counter64,
        curStatsInMpcpFrames
          Counter64,
        curStatsInMpcpOctets
          Counter64,
        curStatsInOAMFrames
          Counter64,
        curStatsInOAMOctets
          Counter64,
        curStatsInCRCErrorPkts
          Counter64,
        curStatsInDropEvents
          Counter64,
        curStatsInJabbers
          Counter64,
        curStatsInCollision
          Counter64,
        curStatsOutOctets
          Counter64,
        curStatsOutPkts
          Counter64,
        curStatsOutBroadcastPkts
          Counter64,
        curStatsOutMulticastPkts
          Counter64,
        curStatsOutPkts64Octets
          Counter64,
        curStatsOutPkts65to127Octets
          Counter64,
        curStatsOutPkts128to255Octets
          Counter64,
        curStatsOutPkts256to511Octets
          Counter64,
        curStatsOutPkts512to1023Octets
          Counter64,
        curStatsOutPkts1024to1518Octets
          Counter64,
        curStatsOutPkts1519o1522Octets
          Counter64,
        curStatsOutUndersizePkts
          Counter64,
        curStatsOutOversizePkts
          Counter64,
        curStatsOutFragments
          Counter64,
        curStatsOutMpcpFrames
          Counter64,
        curStatsOutMpcpOctets
          Counter64,
        curStatsOutOAMFrames
          Counter64,
        curStatsOutOAMOctets
          Counter64,
        curStatsOutCRCErrorPkts
          Counter64,
        curStatsOutDropEvents
          Counter64,
        curStatsOutJabbers
          Counter64,
        curStatsOutCollision
          Counter64,
        curStatsStatusAndAction
          INTEGER
       }

    curStatsDeviceIndex OBJECT-TYPE
      SYNTAX EponDeviceIndex
      MAX-ACCESS not-accessible
      STATUS current
      DESCRIPTION
        "设备索引号        
        For OLT Agent, set to corresponding device/slot/port
        For ONU Agent, set to 0"
      ::= { curStatsEntry 1 }
    
    curStatsCardIndex OBJECT-TYPE
      SYNTAX EponCardIndex
      MAX-ACCESS not-accessible
      STATUS current
      DESCRIPTION
        "板卡索引号        
        For OLT Agent, set to 0
        For ONU Agent, set to corresponding slot
        "
      ::= { curStatsEntry 2 }    
    curStatsPortIndex OBJECT-TYPE
      SYNTAX EponPortIndex
      MAX-ACCESS not-accessible
      STATUS current
      DESCRIPTION
        "端口索引号         
        For OLT Agent, set to 0
        For ONU Agent, set to corresponding port
        "
      ::= { curStatsEntry 3 }
    
    curStatsInOctets OBJECT-TYPE
      SYNTAX Counter64
      MAX-ACCESS read-only
      STATUS current
      DESCRIPTION
        "接收字节数"
      ::= { curStatsEntry 4 }
    
    curStatsInPkts OBJECT-TYPE
      SYNTAX Counter64
      MAX-ACCESS read-only
      STATUS current
      DESCRIPTION
        "接收帧数"
      ::= { curStatsEntry 5 }
    
    curStatsInBroadcastPkts OBJECT-TYPE
      SYNTAX Counter64
      MAX-ACCESS read-only
      STATUS current
      DESCRIPTION
        "接收广播帧数"
      ::= { curStatsEntry 6 }
    
    curStatsInMulticastPkts OBJECT-TYPE
      SYNTAX Counter64
      MAX-ACCESS read-only
      STATUS current
      DESCRIPTION
        "接收组播帧数"
      ::= { curStatsEntry 7 }
    
    curStatsInPkts64Octets OBJECT-TYPE
      SYNTAX Counter64
      MAX-ACCESS read-only
      STATUS current
      DESCRIPTION
        "接收64字节包数"
      ::= { curStatsEntry 8 }
    
    curStatsInPkts65to127Octets OBJECT-TYPE
      SYNTAX Counter64
      MAX-ACCESS read-only
      STATUS current
      DESCRIPTION
        "接收65～127字节包数"
      ::= { curStatsEntry 9 }
    
    curStatsInPkts128to255Octets OBJECT-TYPE
      SYNTAX Counter64
      MAX-ACCESS read-only
      STATUS current
      DESCRIPTION
        "接收128～255字节包数"
      ::= { curStatsEntry 10 }
    
    curStatsInPkts256to511Octets OBJECT-TYPE
      SYNTAX Counter64
      MAX-ACCESS read-only
      STATUS current
      DESCRIPTION
        "接收256～511字节包数"
      ::= { curStatsEntry 11 }
    
    curStatsInPkts512to1023Octets OBJECT-TYPE
      SYNTAX Counter64
      MAX-ACCESS read-only
      STATUS current
      DESCRIPTION
        "接收512～1023字节包数"
      ::= { curStatsEntry 12 }
    
    curStatsInPkts1024to1518Octets OBJECT-TYPE
      SYNTAX Counter64
      MAX-ACCESS read-only
      STATUS current
      DESCRIPTION
        "接收1024～1518字节包数"
      ::= { curStatsEntry 13 }
    
    curStatsInPkts1519to1522Octets OBJECT-TYPE
      SYNTAX Counter64
      MAX-ACCESS read-only
      STATUS current
      DESCRIPTION
        "接收1519～1522字节包数"
      ::= { curStatsEntry 14 }
    
    curStatsInUndersizePkts OBJECT-TYPE
      SYNTAX Counter64
      MAX-ACCESS read-only
      STATUS current
      DESCRIPTION
        "接收超短帧数"
      ::= { curStatsEntry 15 }
    
    curStatsInOversizePkts OBJECT-TYPE
      SYNTAX Counter64
      MAX-ACCESS read-only
      STATUS current
      DESCRIPTION
        "接收超长帧数"
      ::= { curStatsEntry 16 }
    
    curStatsInFragments OBJECT-TYPE
      SYNTAX Counter64
      MAX-ACCESS read-only
      STATUS current
      DESCRIPTION
        "接收碎片数"
      ::= { curStatsEntry 17 }
    
    curStatsInMpcpFrames OBJECT-TYPE
      SYNTAX Counter64
      MAX-ACCESS read-only
      STATUS current
      DESCRIPTION
        "接收MPCP帧数"
      ::= { curStatsEntry 18 }
    
    curStatsInMpcpOctets OBJECT-TYPE
      SYNTAX Counter64
      MAX-ACCESS read-only
      STATUS current
      DESCRIPTION
        "接收MPCP字节数"
      ::= { curStatsEntry 19 }
    
    curStatsInOAMFrames OBJECT-TYPE
      SYNTAX Counter64
      MAX-ACCESS read-only
      STATUS current
      DESCRIPTION
        "接收OAM帧数"
      ::= { curStatsEntry 20 }
    
    curStatsInOAMOctets OBJECT-TYPE
      SYNTAX Counter64
      MAX-ACCESS read-only
      STATUS current
      DESCRIPTION
        "接收OAM字节数"
      ::= { curStatsEntry 21 }
    
    curStatsInCRCErrorPkts OBJECT-TYPE
      SYNTAX Counter64
      MAX-ACCESS read-only
      STATUS current
      DESCRIPTION
        "接收CRC错误帧"
      ::= { curStatsEntry 22 }
    
    curStatsInDropEvents OBJECT-TYPE
      SYNTAX Counter64
      MAX-ACCESS read-only
      STATUS current
      DESCRIPTION
        "接收丢包事件次数"
      ::= { curStatsEntry 23 }
    
    curStatsInJabbers OBJECT-TYPE
      SYNTAX Counter64
      MAX-ACCESS read-only
      STATUS current
      DESCRIPTION
        "接收超长错帧数"
      ::= { curStatsEntry 24 }
    
    curStatsInCollision OBJECT-TYPE
      SYNTAX Counter64
      MAX-ACCESS read-only
      STATUS current
      DESCRIPTION
        "接收碰撞帧数"
      ::= { curStatsEntry 25 }
    
    curStatsOutOctets OBJECT-TYPE
      SYNTAX Counter64
      MAX-ACCESS read-only
      STATUS current
      DESCRIPTION
        "发送字节数"
      ::= { curStatsEntry 26 }
    
    curStatsOutPkts OBJECT-TYPE
      SYNTAX Counter64
      MAX-ACCESS read-only
      STATUS current
      DESCRIPTION
        "发送帧数"
      ::= { curStatsEntry 27 }
    
    curStatsOutBroadcastPkts OBJECT-TYPE
      SYNTAX Counter64
      MAX-ACCESS read-only
      STATUS current
      DESCRIPTION
        "发送广播帧数"
      ::= { curStatsEntry 28 }
    
    curStatsOutMulticastPkts OBJECT-TYPE
      SYNTAX Counter64
      MAX-ACCESS read-only
      STATUS current
      DESCRIPTION
        "发送组播帧数"
      ::= { curStatsEntry 29 }
    
    curStatsOutPkts64Octets OBJECT-TYPE
      SYNTAX Counter64
      MAX-ACCESS read-only
      STATUS current
      DESCRIPTION
        "发送64字节包数"
      ::= { curStatsEntry 30 }
    
    curStatsOutPkts65to127Octets OBJECT-TYPE
      SYNTAX Counter64
      MAX-ACCESS read-only
      STATUS current
      DESCRIPTION
        "发送65～127字节包数"
      ::= { curStatsEntry 31 }
    
    curStatsOutPkts128to255Octets OBJECT-TYPE
      SYNTAX Counter64
      MAX-ACCESS read-only
      STATUS current
      DESCRIPTION
        "发送128～255字节包数"
      ::= { curStatsEntry 32 }
    
    curStatsOutPkts256to511Octets OBJECT-TYPE
      SYNTAX Counter64
      MAX-ACCESS read-only
      STATUS current
      DESCRIPTION
        "发送256～511字节包数"
      ::= { curStatsEntry 33 }
    
    curStatsOutPkts512to1023Octets OBJECT-TYPE
      SYNTAX Counter64
      MAX-ACCESS read-only
      STATUS current
      DESCRIPTION
        "发送512～1023字节包数"
      ::= { curStatsEntry 34 }    
    curStatsOutPkts1024to1518Octets OBJECT-TYPE
      SYNTAX Counter64
      MAX-ACCESS read-only
      STATUS current
      DESCRIPTION
        "发送1024～1518字节包数"
      ::= { curStatsEntry 35 }
    
    curStatsOutPkts1519o1522Octets OBJECT-TYPE
      SYNTAX Counter64
      MAX-ACCESS read-only
      STATUS current
      DESCRIPTION
        "发送1519～1522字节包数"
      ::= { curStatsEntry 36 }
    
    curStatsOutUndersizePkts OBJECT-TYPE
      SYNTAX Counter64
      MAX-ACCESS read-only
      STATUS current
      DESCRIPTION
        "发送超短帧数"
      ::= { curStatsEntry 37 }
    
    curStatsOutOversizePkts OBJECT-TYPE
      SYNTAX Counter64
      MAX-ACCESS read-only
      STATUS current
      DESCRIPTION
        "发送超长帧数"
      ::= { curStatsEntry 38 }
    
    curStatsOutFragments OBJECT-TYPE
      SYNTAX Counter64
      MAX-ACCESS read-only
      STATUS current
      DESCRIPTION
        "发送碎片数"
      ::= { curStatsEntry 39 }
    
    curStatsOutMpcpFrames OBJECT-TYPE
      SYNTAX Counter64
      MAX-ACCESS read-only
      STATUS current
      DESCRIPTION
        "发送MPCP帧数"
      ::= { curStatsEntry 40 }
    
    curStatsOutMpcpOctets OBJECT-TYPE
      SYNTAX Counter64
      MAX-ACCESS read-only
      STATUS current
      DESCRIPTION
        "发送MPCP字节数"
      ::= { curStatsEntry 41 }
    
    curStatsOutOAMFrames OBJECT-TYPE
      SYNTAX Counter64
      MAX-ACCESS read-only
      STATUS current
      DESCRIPTION
        "发送OAM帧数"
      ::= { curStatsEntry 42 }
    
    curStatsOutOAMOctets OBJECT-TYPE
      SYNTAX Counter64
      MAX-ACCESS read-only
      STATUS current
      DESCRIPTION
        "发送OAM字节数"
      ::= { curStatsEntry 43 }
    
    curStatsOutCRCErrorPkts OBJECT-TYPE
      SYNTAX Counter64
      MAX-ACCESS read-only
      STATUS current
      DESCRIPTION
        "发送CRC错误帧"
      ::= { curStatsEntry 44 }
    
    curStatsOutDropEvents OBJECT-TYPE
      SYNTAX Counter64
      MAX-ACCESS read-only
      STATUS current
      DESCRIPTION
        "发送丢包事件次数"
      ::= { curStatsEntry 45 }
    
    curStatsOutJabbers OBJECT-TYPE
      SYNTAX Counter64
      MAX-ACCESS read-only
      STATUS current
      DESCRIPTION
        "发送超长错帧数"
      ::= { curStatsEntry 46 }
    
    curStatsOutCollision OBJECT-TYPE
      SYNTAX Counter64
      MAX-ACCESS read-only
      STATUS current
      DESCRIPTION
        "发送碰撞帧数"
      ::= { curStatsEntry 47 }
    
    curStatsStatusAndAction OBJECT-TYPE
      SYNTAX INTEGER
        {
        none(1),
        clean(2)
        }
      MAX-ACCESS read-write
      STATUS current
      DESCRIPTION
        "当前统计状态及操作
        clean(2) 统计量清零"
      ::= { curStatsEntry 48 }
    
    stats15Table OBJECT-TYPE
      SYNTAX SEQUENCE OF Stats15Entry
      MAX-ACCESS not-accessible
      STATUS current
      DESCRIPTION
        "15 minutes performance data"
      ::= { performanceStatisticObjects 2 }
    
    stats15Entry OBJECT-TYPE
      SYNTAX Stats15Entry
      MAX-ACCESS not-accessible
      STATUS current
      DESCRIPTION
        ""
      INDEX { stats15DeviceIndex, stats15CardIndex, stats15PortIndex, stats15Index }
      ::= { stats15Table 1 }
    
    Stats15Entry ::=
      SEQUENCE { 
        stats15DeviceIndex
          EponDeviceIndex,
        stats15CardIndex
          EponCardIndex,
        stats15PortIndex
          EponPortIndex,
        stats15Index
          EponStats15MinRecordType,
        stats15InOctets
          Counter64,
        stats15InPkts
          Counter64,
        stats15InBroadcastPkts
          Counter64,
        stats15InMulticastPkts
          Counter64,
        stats15InPkts64Octets
          Counter64,
        stats15InPkts65to127Octets
          Counter64,
        stats15InPkts128to255Octets
          Counter64,
        stats15InPkts256to511Octets
          Counter64,
        stats15InPkts512to1023Octets
          Counter64,
        stats15InPkts1024to1518Octets
          Counter64,
        stats15InPkts1519to1522Octets
          Counter64,
        stats15InUndersizePkts
          Counter64,
        stats15InOversizePkts
          Counter64,
        stats15InFragments
          Counter64,
        stats15InMpcpFrames
          Counter64,
        stats15InMpcpOctets
          Counter64,
        stats15InOAMFrames
          Counter64,
        stats15InOAMOctets
          Counter64,
        stats15InCRCErrorPkts
          Counter64,
        stats15InDropEvents
          Counter64,
        stats15InJabbers
          Counter64,
        stats15InCollision
          Counter64,
        stats15OutOctets
          Counter64,
        stats15OutPkts
          Counter64,
        stats15OutBroadcastPkts
          Counter64,
        stats15OutMulticastPkts
          Counter64,
        stats15OutPkts64Octets
          Counter64,
        stats15OutPkts65to127Octets
          Counter64,
        stats15OutPkts128to255Octets
          Counter64,
        stats15OutPkts256to511Octets
          Counter64,
        stats15OutPkts512to1023Octets
          Counter64,
        stats15OutPkts1024to1518Octets
          Counter64,
        stats15OutPkts1519o1522Octets
          Counter64,
        stats15OutUndersizePkts
          Counter64,
        stats15OutOversizePkts
          Counter64,
        stats15OutFragments
          Counter64,
        stats15OutMpcpFrames
          Counter64,
        stats15OutMpcpOctets
          Counter64,
        stats15OutOAMFrames
          Counter64,
        stats15OutOAMOctets
          Counter64,
        stats15OutCRCErrorPkts
          Counter64,
        stats15OutDropEvents
          Counter64,
        stats15OutJabbers
          Counter64,
        stats15OutCollision
          Counter64,
        stats15StatusAndAction
          INTEGER,
        stats15ValidityTag  
          TruthValue,
        stats15ElapsedTime  
          Counter32,
        stats15EndTime    
          DateAndTime
       }

    stats15DeviceIndex OBJECT-TYPE
      SYNTAX EponDeviceIndex
      MAX-ACCESS not-accessible
      STATUS current
      DESCRIPTION
        "设备索引号        
        For OLT Agent, set to corresponding device/slot/port
        For ONU Agent, set to 0       "
      ::= { stats15Entry 1 }
    
    stats15CardIndex OBJECT-TYPE
      SYNTAX EponCardIndex
      MAX-ACCESS not-accessible
      STATUS current
      DESCRIPTION
        "板卡索引号        
        For OLT Agent, set to 0
        For ONU Agent, set to corresponding slot
        "
      ::= { stats15Entry 2 }
    
    stats15PortIndex OBJECT-TYPE
      SYNTAX EponPortIndex
      MAX-ACCESS not-accessible
      STATUS current
      DESCRIPTION
        "端口索引号        
        For OLT Agent, set to 0
        For ONU Agent, set to corresponding port
        "
      ::= { stats15Entry 3 }
    
    stats15Index OBJECT-TYPE
      SYNTAX EponStats15MinRecordType
      MAX-ACCESS not-accessible
      STATUS current
      DESCRIPTION
        "
        顺序索引号
        "
      ::= { stats15Entry 4 }
    
    stats15InOctets OBJECT-TYPE
      SYNTAX Counter64
      MAX-ACCESS read-only
      STATUS current
      DESCRIPTION
        "接收字节数"
      ::= { stats15Entry 5 }
    
    stats15InPkts OBJECT-TYPE
      SYNTAX Counter64
      MAX-ACCESS read-only
      STATUS current
      DESCRIPTION
        "接收帧数"
      ::= { stats15Entry 6 }
    
    stats15InBroadcastPkts OBJECT-TYPE
      SYNTAX Counter64
      MAX-ACCESS read-only
      STATUS current
      DESCRIPTION
        "接收广播帧数"
      ::= { stats15Entry 7 }
    
    stats15InMulticastPkts OBJECT-TYPE
      SYNTAX Counter64
      MAX-ACCESS read-only
      STATUS current
      DESCRIPTION
        "接收组播帧数"
      ::= { stats15Entry 8 }
    
    stats15InPkts64Octets OBJECT-TYPE
      SYNTAX Counter64
      MAX-ACCESS read-only
      STATUS current
      DESCRIPTION
        "接收64字节包数"
      ::= { stats15Entry 9 }
    
    stats15InPkts65to127Octets OBJECT-TYPE
      SYNTAX Counter64
      MAX-ACCESS read-only
      STATUS current
      DESCRIPTION
        "接收65～127字节包数"
      ::= { stats15Entry 10 }
    
    stats15InPkts128to255Octets OBJECT-TYPE
      SYNTAX Counter64
      MAX-ACCESS read-only
      STATUS current
      DESCRIPTION
        "接收128～255字节包数"
      ::= { stats15Entry 11 }
    
    stats15InPkts256to511Octets OBJECT-TYPE
      SYNTAX Counter64
      MAX-ACCESS read-only
      STATUS current
      DESCRIPTION
        "接收256～511字节包数"
      ::= { stats15Entry 12 }
    
    stats15InPkts512to1023Octets OBJECT-TYPE
      SYNTAX Counter64
      MAX-ACCESS read-only
      STATUS current
      DESCRIPTION
        "接收512～1023字节包数"
      ::= { stats15Entry 13 }
    
    stats15InPkts1024to1518Octets OBJECT-TYPE
      SYNTAX Counter64
      MAX-ACCESS read-only
      STATUS current
      DESCRIPTION
        "接收1024～1518字节包数"
      ::= { stats15Entry 14 }
    
    stats15InPkts1519to1522Octets OBJECT-TYPE
      SYNTAX Counter64
      MAX-ACCESS read-only
      STATUS current
      DESCRIPTION
        "接收1519～1522字节包数"
      ::= { stats15Entry 15 }
    
    stats15InUndersizePkts OBJECT-TYPE
      SYNTAX Counter64
      MAX-ACCESS read-only
      STATUS current
      DESCRIPTION
        "接收超短帧数"
      ::= { stats15Entry 16 }
    
    stats15InOversizePkts OBJECT-TYPE
      SYNTAX Counter64
      MAX-ACCESS read-only
      STATUS current
      DESCRIPTION
        "接收超长帧数"
      ::= { stats15Entry 17 }    
    stats15InFragments OBJECT-TYPE
      SYNTAX Counter64
      MAX-ACCESS read-only
      STATUS current
      DESCRIPTION
        "接收碎片数"
      ::= { stats15Entry 18 }
    
    stats15InMpcpFrames OBJECT-TYPE
      SYNTAX Counter64
      MAX-ACCESS read-only
      STATUS current
      DESCRIPTION
        "接收MPCP帧数"
      ::= { stats15Entry 19 }
    
    stats15InMpcpOctets OBJECT-TYPE
      SYNTAX Counter64
      MAX-ACCESS read-only
      STATUS current
      DESCRIPTION
        "接收MPCP字节数"
      ::= { stats15Entry 20 }
    
    stats15InOAMFrames OBJECT-TYPE
      SYNTAX Counter64
      MAX-ACCESS read-only
      STATUS current
      DESCRIPTION
        "接收OAM帧数"
      ::= { stats15Entry 21 }
    
    stats15InOAMOctets OBJECT-TYPE
      SYNTAX Counter64
      MAX-ACCESS read-only
      STATUS current
      DESCRIPTION
        "接收OAM字节数"
      ::= { stats15Entry 22 }
    
    stats15InCRCErrorPkts OBJECT-TYPE
      SYNTAX Counter64
      MAX-ACCESS read-only
      STATUS current
      DESCRIPTION
        "接收CRC错误帧"
      ::= { stats15Entry 23 }
    
    stats15InDropEvents OBJECT-TYPE
      SYNTAX Counter64
      MAX-ACCESS read-only
      STATUS current
      DESCRIPTION
        "接收丢包事件次数"
      ::= { stats15Entry 24 }
    
    stats15InJabbers OBJECT-TYPE
      SYNTAX Counter64
      MAX-ACCESS read-only
      STATUS current
      DESCRIPTION
        "接收超长错帧数"
      ::= { stats15Entry 25 }
    
    stats15InCollision OBJECT-TYPE
      SYNTAX Counter64
      MAX-ACCESS read-only
      STATUS current
      DESCRIPTION
        "接收碰撞帧数"
      ::= { stats15Entry 26 }
    
    stats15OutOctets OBJECT-TYPE
      SYNTAX Counter64
      MAX-ACCESS read-only
      STATUS current
      DESCRIPTION
        "发送字节数"
      ::= { stats15Entry 27 }
    
    stats15OutPkts OBJECT-TYPE
      SYNTAX Counter64
      MAX-ACCESS read-only
      STATUS current
      DESCRIPTION
        "发送帧数"
      ::= { stats15Entry 28 }
    
    stats15OutBroadcastPkts OBJECT-TYPE
      SYNTAX Counter64
      MAX-ACCESS read-only
      STATUS current
      DESCRIPTION
        "发送广播帧数"
      ::= { stats15Entry 29 }
    
    stats15OutMulticastPkts OBJECT-TYPE
      SYNTAX Counter64
      MAX-ACCESS read-only
      STATUS current
      DESCRIPTION
        "发送组播帧数"
      ::= { stats15Entry 30 }
    
    stats15OutPkts64Octets OBJECT-TYPE
      SYNTAX Counter64
      MAX-ACCESS read-only
      STATUS current
      DESCRIPTION
        "发送64字节包数"
      ::= { stats15Entry 31 }
    
    stats15OutPkts65to127Octets OBJECT-TYPE
      SYNTAX Counter64
      MAX-ACCESS read-only
      STATUS current
      DESCRIPTION
        "发送65～127字节包数"
      ::= { stats15Entry 32 }
    
    stats15OutPkts128to255Octets OBJECT-TYPE
      SYNTAX Counter64
      MAX-ACCESS read-only
      STATUS current
      DESCRIPTION
        "发送128～255字节包数"
      ::= { stats15Entry 33 }
    
    stats15OutPkts256to511Octets OBJECT-TYPE
      SYNTAX Counter64
      MAX-ACCESS read-only
      STATUS current
      DESCRIPTION
        "发送256～511字节包数"
      ::= { stats15Entry 34 }
    
    stats15OutPkts512to1023Octets OBJECT-TYPE
      SYNTAX Counter64
      MAX-ACCESS read-only
      STATUS current
      DESCRIPTION
        "发送512～1023字节包数"
      ::= { stats15Entry 35 }
    
    stats15OutPkts1024to1518Octets OBJECT-TYPE
      SYNTAX Counter64
      MAX-ACCESS read-only
      STATUS current
      DESCRIPTION
        "发送1024～1518字节包数"
      ::= { stats15Entry 36 }
    
    stats15OutPkts1519o1522Octets OBJECT-TYPE
      SYNTAX Counter64
      MAX-ACCESS read-only
      STATUS current
      DESCRIPTION
        "发送1519～1522字节包数"
      ::= { stats15Entry 37 }
    
    stats15OutUndersizePkts OBJECT-TYPE
      SYNTAX Counter64
      MAX-ACCESS read-only
      STATUS current
      DESCRIPTION
        "发送超短帧数"
      ::= { stats15Entry 38 }
    
    stats15OutOversizePkts OBJECT-TYPE
      SYNTAX Counter64
      MAX-ACCESS read-only
      STATUS current
      DESCRIPTION
        "发送超长帧数"
      ::= { stats15Entry 39 }
    
    stats15OutFragments OBJECT-TYPE
      SYNTAX Counter64
      MAX-ACCESS read-only
      STATUS current
      DESCRIPTION
        "发送碎片数"
      ::= { stats15Entry 40 }
    
    stats15OutMpcpFrames OBJECT-TYPE
      SYNTAX Counter64
      MAX-ACCESS read-only
      STATUS current
      DESCRIPTION
        "发送MPCP帧数"
      ::= { stats15Entry 41 }
    
    stats15OutMpcpOctets OBJECT-TYPE
      SYNTAX Counter64
      MAX-ACCESS read-only
      STATUS current
      DESCRIPTION
        "发送MPCP字节数"
      ::= { stats15Entry 42 }
    
    stats15OutOAMFrames OBJECT-TYPE
      SYNTAX Counter64
      MAX-ACCESS read-only
      STATUS current
      DESCRIPTION
        "发送OAM帧数"
      ::= { stats15Entry 43 }
    
    stats15OutOAMOctets OBJECT-TYPE
      SYNTAX Counter64
      MAX-ACCESS read-only
      STATUS current
      DESCRIPTION
        "发送OAM字节数"
      ::= { stats15Entry 44 }    
    stats15OutCRCErrorPkts OBJECT-TYPE
      SYNTAX Counter64
      MAX-ACCESS read-only
      STATUS current
      DESCRIPTION
        "发送CRC错误帧"
      ::= { stats15Entry 45 }
    stats15OutDropEvents OBJECT-TYPE
      SYNTAX Counter64
      MAX-ACCESS read-only
      STATUS current
      DESCRIPTION
        "发送丢包事件次数"
      ::= { stats15Entry 46 }
    
    stats15OutJabbers OBJECT-TYPE
      SYNTAX Counter64
      MAX-ACCESS read-only
      STATUS current
      DESCRIPTION
        "发送超长错帧数"
      ::= { stats15Entry 47 }
    
    stats15OutCollision OBJECT-TYPE
      SYNTAX Counter64
      MAX-ACCESS read-only
      STATUS current
      DESCRIPTION
        "发送碰撞帧数"
      ::= { stats15Entry 48 }
    
    stats15StatusAndAction OBJECT-TYPE
      SYNTAX INTEGER
        {
        none(1),
        clean(2)
        }
      MAX-ACCESS read-write
      STATUS current
      DESCRIPTION
        "当前统计状态及操作
        clean(2) 统计量清零"
      ::= { stats15Entry 49 }
    stats15ValidityTag OBJECT-TYPE
      SYNTAX TruthValue
      MAX-ACCESS read-only
      STATUS current
      DESCRIPTION
        "Whether or not the current 15-min PM data is valid"
      ::= { stats15Entry 50 }

    stats15ElapsedTime OBJECT-TYPE
      SYNTAX Counter32
      UNITS "seconds"
      MAX-ACCESS read-only
      STATUS current
      DESCRIPTION
        "
        It is elapsed time, since start of this 15-min interval.
        It is only valid for current PM data. For history PM data, set to 0.
        "
      ::= { stats15Entry 51 }

    stats15EndTime OBJECT-TYPE
      SYNTAX DateAndTime
      MAX-ACCESS read-only
      STATUS current
      DESCRIPTION
        "
        It is time, when the PM history data is created.
        It is only valid for history PM data.
        "
      ::= { stats15Entry 52 }
    
    stats24Table OBJECT-TYPE
      SYNTAX SEQUENCE OF Stats24Entry
      MAX-ACCESS not-accessible
      STATUS current
      DESCRIPTION
        "1-day performance data"
      ::= { performanceStatisticObjects 3 }
    
    stats24Entry OBJECT-TYPE
      SYNTAX Stats24Entry
      MAX-ACCESS not-accessible
      STATUS current
      DESCRIPTION
        ""
      INDEX { stats24DeviceIndex, stats24CardIndex, stats24PortIndex, stats24Index }
      ::= { stats24Table 1 }
    
    Stats24Entry ::=
      SEQUENCE { 
        stats24DeviceIndex
          EponDeviceIndex,
        stats24CardIndex
          EponCardIndex,
        stats24PortIndex
          EponPortIndex,
        stats24Index
          EponStats24HourRecordType,
        stats24InOctets
          Counter64,
        stats24InPkts
          Counter64,
        stats24InBroadcastPkts
          Counter64,
        stats24InMulticastPkts
          Counter64,
        stats24InPkts64Octets
          Counter64,
        stats24InPkts65to127Octets
          Counter64,
        stats24InPkts128to255Octets
          Counter64,
        stats24InPkts256to511Octets
          Counter64,
        stats24InPkts512to1023Octets
          Counter64,
        stats24InPkts1024to1518Octets
          Counter64,
        stats24InPkts1519to1522Octets
          Counter64,
        stats24InUndersizePkts
          Counter64,
        stats24InOversizePkts
          Counter64,
        stats24InFragments
          Counter64,
        stats24InMpcpFrames
          Counter64,
        stats24InMpcpOctets
          Counter64,
        stats24InOAMFrames
          Counter64,
        stats24InOAMOctets
          Counter64,
        stats24InCRCErrorPkts
          Counter64,
        stats24InDropEvents
          Counter64,
        stats24InJabbers
          Counter64,
        stats24InCollision
          Counter64,
        stats24OutOctets
          Counter64,
        stats24OutPkts
          Counter64,
        stats24OutBroadcastPkts
          Counter64,
        stats24OutMulticastPkts
          Counter64,
        stats24OutPkts64Octets
          Counter64,
        stats24OutPkts65to127Octets
          Counter64,
        stats24OutPkts128to255Octets
          Counter64,
        stats24OutPkts256to511Octets
          Counter64,
        stats24OutPkts512to1023Octets
          Counter64,
        stats24OutPkts1024to1518Octets
          Counter64,
        stats24OutPkts1519o1522Octets
          Counter64,
        stats24OutUndersizePkts
          Counter64,
        stats24OutOversizePkts
          Counter64,
        stats24OutFragments
          Counter64,
        stats24OutMpcpFrames
          Counter64,
        stats24OutMpcpOctets
          Counter64,
        stats24OutOAMFrames
          Counter64,
        stats24OutOAMOctets
          Counter64,
        stats24OutCRCErrorPkts
          Counter64,
        stats24OutDropEvents
          Counter64,
        stats24OutJabbers
          Counter64,
        stats24OutCollision
          Counter64,
        stats24StatusAndAction
          INTEGER,
        stats24ValidityTag  
          TruthValue,
        stats24ElapsedTime  
          Counter32,
        stats24EndTime    
          DateAndTime
       }

    stats24DeviceIndex OBJECT-TYPE
      SYNTAX EponDeviceIndex
      MAX-ACCESS not-accessible
      STATUS current
      DESCRIPTION
        "设备索引号        
        For OLT Agent, set to corresponding device/slot/port
        For ONU Agent, set to 0
        "
      ::= { stats24Entry 1 }
    
    stats24CardIndex OBJECT-TYPE
      SYNTAX EponCardIndex
      MAX-ACCESS not-accessible
      STATUS current
      DESCRIPTION
        "板卡索引号        
        For OLT Agent, set to 0
        For ONU Agent, set to corresponding slot
        "
      ::= { stats24Entry 2 }
    
    stats24PortIndex OBJECT-TYPE
      SYNTAX EponPortIndex
      MAX-ACCESS not-accessible
      STATUS current
      DESCRIPTION
        "端口索引号        
        For OLT Agent, set to 0
        For ONU Agent, set to corresponding port
        "
      ::= { stats24Entry 3 }
    
    stats24Index OBJECT-TYPE
      SYNTAX EponStats24HourRecordType
      MAX-ACCESS not-accessible
      STATUS current
      DESCRIPTION
        "顺序索引号"
      ::= { stats24Entry 4 }
    
    stats24InOctets OBJECT-TYPE
      SYNTAX Counter64
      MAX-ACCESS read-only
      STATUS current
      DESCRIPTION
        "接收字节数"
      ::= { stats24Entry 5 }
    
    stats24InPkts OBJECT-TYPE
      SYNTAX Counter64
      MAX-ACCESS read-only
      STATUS current
      DESCRIPTION
        "接收帧数"
      ::= { stats24Entry 6 }
    
    stats24InBroadcastPkts OBJECT-TYPE
      SYNTAX Counter64
      MAX-ACCESS read-only
      STATUS current
      DESCRIPTION
        "接收广播帧数"
      ::= { stats24Entry 7 }
    
    stats24InMulticastPkts OBJECT-TYPE
      SYNTAX Counter64
      MAX-ACCESS read-only
      STATUS current
      DESCRIPTION
        "接收组播帧数"
      ::= { stats24Entry 8 }
    
    stats24InPkts64Octets OBJECT-TYPE
      SYNTAX Counter64
      MAX-ACCESS read-only
      STATUS current
      DESCRIPTION
        "接收64字节包数"
      ::= { stats24Entry 9 }
    
    stats24InPkts65to127Octets OBJECT-TYPE
      SYNTAX Counter64
      MAX-ACCESS read-only
      STATUS current
      DESCRIPTION
        "接收65～127字节包数"
      ::= { stats24Entry 10 }
    
    stats24InPkts128to255Octets OBJECT-TYPE
      SYNTAX Counter64
      MAX-ACCESS read-only
      STATUS current
      DESCRIPTION
        "接收128～255字节包数"
      ::= { stats24Entry 11 }
    
    stats24InPkts256to511Octets OBJECT-TYPE
      SYNTAX Counter64
      MAX-ACCESS read-only
      STATUS current
      DESCRIPTION
        "接收256～511字节包数"
      ::= { stats24Entry 12 }
    
    stats24InPkts512to1023Octets OBJECT-TYPE
      SYNTAX Counter64
      MAX-ACCESS read-only
      STATUS current
      DESCRIPTION
        "接收512～1023字节包数"
      ::= { stats24Entry 13 }
    
    stats24InPkts1024to1518Octets OBJECT-TYPE
      SYNTAX Counter64
      MAX-ACCESS read-only
      STATUS current
      DESCRIPTION
        "接收1024～1518字节包数"
      ::= { stats24Entry 14 }
    
    stats24InPkts1519to1522Octets OBJECT-TYPE
      SYNTAX Counter64
      MAX-ACCESS read-only
      STATUS current
      DESCRIPTION
        "接收1519～1522字节包数"
      ::= { stats24Entry 15 }
    
    stats24InUndersizePkts OBJECT-TYPE
      SYNTAX Counter64
      MAX-ACCESS read-only
      STATUS current
      DESCRIPTION
        "接收超短帧数"
      ::= { stats24Entry 16 }
    
    stats24InOversizePkts OBJECT-TYPE
      SYNTAX Counter64
      MAX-ACCESS read-only
      STATUS current
      DESCRIPTION
        "接收超长帧数"
      ::= { stats24Entry 17 }
    
    stats24InFragments OBJECT-TYPE
      SYNTAX Counter64
      MAX-ACCESS read-only
      STATUS current
      DESCRIPTION
        "接收碎片数"
      ::= { stats24Entry 18 }
    
    stats24InMpcpFrames OBJECT-TYPE
      SYNTAX Counter64
      MAX-ACCESS read-only
      STATUS current
      DESCRIPTION
        "接收MPCP帧数"
      ::= { stats24Entry 19 }
    
    stats24InMpcpOctets OBJECT-TYPE
      SYNTAX Counter64
      MAX-ACCESS read-only
      STATUS current
      DESCRIPTION
        "接收MPCP字节数"
      ::= { stats24Entry 20 }
    
    stats24InOAMFrames OBJECT-TYPE
      SYNTAX Counter64
      MAX-ACCESS read-only
      STATUS current
      DESCRIPTION
        "接收OAM帧数"
      ::= { stats24Entry 21 }
    
    stats24InOAMOctets OBJECT-TYPE
      SYNTAX Counter64
      MAX-ACCESS read-only
      STATUS current
      DESCRIPTION
        "接收OAM字节数"
      ::= { stats24Entry 22 }
    
    stats24InCRCErrorPkts OBJECT-TYPE
      SYNTAX Counter64
      MAX-ACCESS read-only
      STATUS current
      DESCRIPTION
        "接收CRC错误帧"
      ::= { stats24Entry 23 }
    
    stats24InDropEvents OBJECT-TYPE
      SYNTAX Counter64
      MAX-ACCESS read-only
      STATUS current
      DESCRIPTION
        "接收丢包事件次数"
      ::= { stats24Entry 24 }
    
    stats24InJabbers OBJECT-TYPE
      SYNTAX Counter64
      MAX-ACCESS read-only
      STATUS current
      DESCRIPTION
        "接收超长错帧数"
      ::= { stats24Entry 25 }
    
    stats24InCollision OBJECT-TYPE
      SYNTAX Counter64
      MAX-ACCESS read-only
      STATUS current
      DESCRIPTION
        "接收碰撞帧数"
      ::= { stats24Entry 26 }
    
    stats24OutOctets OBJECT-TYPE
      SYNTAX Counter64
      MAX-ACCESS read-only
      STATUS current
      DESCRIPTION
        "发送字节数"
      ::= { stats24Entry 27 }
    
    stats24OutPkts OBJECT-TYPE
      SYNTAX Counter64
      MAX-ACCESS read-only
      STATUS current
      DESCRIPTION
        "发送帧数"
      ::= { stats24Entry 28 }
    
    stats24OutBroadcastPkts OBJECT-TYPE
      SYNTAX Counter64
      MAX-ACCESS read-only
      STATUS current
      DESCRIPTION
        "发送广播帧数"
      ::= { stats24Entry 29 }
    
    stats24OutMulticastPkts OBJECT-TYPE
      SYNTAX Counter64
      MAX-ACCESS read-only
      STATUS current
      DESCRIPTION
        "发送组播帧数"
      ::= { stats24Entry 30 }
    
    stats24OutPkts64Octets OBJECT-TYPE
      SYNTAX Counter64
      MAX-ACCESS read-only
      STATUS current
      DESCRIPTION
        "发送64字节包数"
      ::= { stats24Entry 31 }
    
    stats24OutPkts65to127Octets OBJECT-TYPE
      SYNTAX Counter64
      MAX-ACCESS read-only
      STATUS current
      DESCRIPTION
        "发送65～127字节包数"
      ::= { stats24Entry 32 }
    
    stats24OutPkts128to255Octets OBJECT-TYPE
      SYNTAX Counter64
      MAX-ACCESS read-only
      STATUS current
      DESCRIPTION
        "发送128～255字节包数"
      ::= { stats24Entry 33 }
    
    stats24OutPkts256to511Octets OBJECT-TYPE
      SYNTAX Counter64
      MAX-ACCESS read-only
      STATUS current
      DESCRIPTION
        "发送256～511字节包数"
      ::= { stats24Entry 34 }
    
    stats24OutPkts512to1023Octets OBJECT-TYPE
      SYNTAX Counter64
      MAX-ACCESS read-only
      STATUS current
      DESCRIPTION
        "发送512～1023字节包数"
      ::= { stats24Entry 35 }
    
    stats24OutPkts1024to1518Octets OBJECT-TYPE
      SYNTAX Counter64
      MAX-ACCESS read-only
      STATUS current
      DESCRIPTION
        "发送1024～1518字节包数"
      ::= { stats24Entry 36 }
    
    stats24OutPkts1519o1522Octets OBJECT-TYPE
      SYNTAX Counter64
      MAX-ACCESS read-only
      STATUS current
      DESCRIPTION
        "发送1519～1522字节包数"
      ::= { stats24Entry 37 }
    
    stats24OutUndersizePkts OBJECT-TYPE
      SYNTAX Counter64
      MAX-ACCESS read-only
      STATUS current
      DESCRIPTION
        "发送超短帧数"
      ::= { stats24Entry 38 }
    
    stats24OutOversizePkts OBJECT-TYPE
      SYNTAX Counter64
      MAX-ACCESS read-only
      STATUS current
      DESCRIPTION
        "发送超长帧数"
      ::= { stats24Entry 39 }
    
    stats24OutFragments OBJECT-TYPE
      SYNTAX Counter64
      MAX-ACCESS read-only
      STATUS current
      DESCRIPTION
        "发送碎片数"
      ::= { stats24Entry 40 }
    
    stats24OutMpcpFrames OBJECT-TYPE
      SYNTAX Counter64
      MAX-ACCESS read-only
      STATUS current
      DESCRIPTION
        "发送MPCP帧数"
      ::= { stats24Entry 41 }
    
    stats24OutMpcpOctets OBJECT-TYPE
      SYNTAX Counter64
      MAX-ACCESS read-only
      STATUS current
      DESCRIPTION
        "发送MPCP字节数"
      ::= { stats24Entry 42 }
    
    stats24OutOAMFrames OBJECT-TYPE
      SYNTAX Counter64
      MAX-ACCESS read-only
      STATUS current
      DESCRIPTION
        "发送OAM帧数"
      ::= { stats24Entry 43 }
    
    stats24OutOAMOctets OBJECT-TYPE
      SYNTAX Counter64
      MAX-ACCESS read-only
      STATUS current
      DESCRIPTION
        "发送OAM字节数"
      ::= { stats24Entry 44 }
    
    stats24OutCRCErrorPkts OBJECT-TYPE
      SYNTAX Counter64
      MAX-ACCESS read-only
      STATUS current
      DESCRIPTION
        "发送CRC错误帧"
      ::= { stats24Entry 45 }
    
    stats24OutDropEvents OBJECT-TYPE
      SYNTAX Counter64
      MAX-ACCESS read-only
      STATUS current
      DESCRIPTION
        "发送丢包事件次数"
      ::= { stats24Entry 46 }
    
    stats24OutJabbers OBJECT-TYPE
      SYNTAX Counter64
      MAX-ACCESS read-only
      STATUS current
      DESCRIPTION
        "发送超长错帧数"
      ::= { stats24Entry 47 }
    
    stats24OutCollision OBJECT-TYPE
      SYNTAX Counter64
      MAX-ACCESS read-only
      STATUS current
      DESCRIPTION
        "发送碰撞帧数"
      ::= { stats24Entry 48 }
    
    stats24StatusAndAction OBJECT-TYPE
      SYNTAX INTEGER
        {
        none(1),
        clear(2)
        }
      MAX-ACCESS read-write
      STATUS current
      DESCRIPTION
        "当前统计状态及操作
        clear(2) 统计量清零"
      ::= { stats24Entry 49 }

    stats24ValidityTag OBJECT-TYPE
      SYNTAX TruthValue
      MAX-ACCESS read-only
      STATUS current
      DESCRIPTION
        "Whether or not the current 1-day PM data is valid"
      ::= { stats24Entry 50 }

    stats24ElapsedTime OBJECT-TYPE
      SYNTAX Counter32
      UNITS "seconds"
      MAX-ACCESS read-only
      STATUS current
      DESCRIPTION
        "
        It is elapsed time, since start of this 1-day interval.
        It is only valid for current PM data. For history PM data, set to 0.
        "
      ::= { stats24Entry 51 }

    stats24EndTime OBJECT-TYPE
      SYNTAX DateAndTime
      MAX-ACCESS read-only
      STATUS current
      DESCRIPTION
        "
        It is time, when the PM history data is created.
        It is only valid for history PM data.
        "
      ::= { stats24Entry 52 }

    perfStatsGlobalSet  OBJECT-IDENTITY
      STATUS current
      DESCRIPTION 
        ""
      ::= { performanceStatisticObjects 4 }
    
    perfStats15MinMaxRecord OBJECT-TYPE
      SYNTAX EponStats15MinRecordType
      MAX-ACCESS read-write
      STATUS current
      DESCRIPTION
        "15分钟性能统计的最大记录数, 不能是0"
      DEFVAL { 96 }
      ::= { perfStatsGlobalSet 1 }
    
    perfStats24HourMaxRecord OBJECT-TYPE
      SYNTAX EponStats24HourRecordType
      MAX-ACCESS read-write
      STATUS current
      DESCRIPTION
        "24小时性能统计的最大记录数, 不能是0"
      DEFVAL { 7 }
      ::= { perfStatsGlobalSet 2 }
    
    perfStatsThresholdTable OBJECT-TYPE
      SYNTAX SEQUENCE OF PerfStatsThresholdEntry
      MAX-ACCESS not-accessible
      STATUS current
      DESCRIPTION
        "门限管理"
      ::= { performanceStatisticObjects 5 }
    
    perfStatsThresholdEntry OBJECT-TYPE
      SYNTAX PerfStatsThresholdEntry
      MAX-ACCESS not-accessible
      STATUS current
      DESCRIPTION
        "门限管理"
      INDEX { perfStatsThresholdDeviceIndex, perfStatsThresholdCardIndex, perfStatsThresholdPortIndex, perfStatsThresholdTypeIndex }
      ::= { perfStatsThresholdTable 1 }
    
    PerfStatsThresholdEntry ::=
      SEQUENCE { 
        perfStatsThresholdDeviceIndex
          EponDeviceIndex,
        perfStatsThresholdCardIndex
          EponCardIndex,
        perfStatsThresholdPortIndex
          EponPortIndex,
        perfStatsThresholdTypeIndex
          EponStatsThresholdType,
        perfStatsThresholdUpper
          Counter64,
        perfStatsThresholdLower
          Counter64,
        perfStatsThresholdRowStatus
          RowStatus
       }

    perfStatsThresholdDeviceIndex OBJECT-TYPE
      SYNTAX EponDeviceIndex
      MAX-ACCESS not-accessible
      STATUS current
      DESCRIPTION
        "设备索引号        
        定义同curStatsDeviceIndex"
      ::= { perfStatsThresholdEntry 1 }
    
    perfStatsThresholdCardIndex OBJECT-TYPE
      SYNTAX EponCardIndex
      MAX-ACCESS not-accessible
      STATUS current
      DESCRIPTION
        "板卡索引号        
        定义同curStatsCardIndex"
      ::= { perfStatsThresholdEntry 2 }
    
    perfStatsThresholdPortIndex OBJECT-TYPE
      SYNTAX EponPortIndex
      MAX-ACCESS not-accessible
      STATUS current
      DESCRIPTION
        "端口索引号        
        定义同curStatsPortIndex"
      ::= { perfStatsThresholdEntry 3 }
    
    perfStatsThresholdTypeIndex OBJECT-TYPE
      SYNTAX EponStatsThresholdType
      MAX-ACCESS not-accessible
      STATUS current
      DESCRIPTION
        "门限类型；
1、EponStatsThresholdType为“50  Temperature”温度时，单位是摄氏度，偏移量+100，比如门限设置为75摄氏度，实际是-25摄氏度来进行比较判定；
2、EponStatsThresholdType为“51  Voltage”温度时，单位是“centi-mv”；
3、EponStatsThresholdType为“52  TXPower”和“53  RXPower”时，单位以centi-dBuV为准"
      ::= { perfStatsThresholdEntry 4 }
    
    perfStatsThresholdUpper OBJECT-TYPE
      SYNTAX Counter64
      MAX-ACCESS read-create
      STATUS current
      DESCRIPTION
        "阈值上限"
      ::= { perfStatsThresholdEntry 5 }
    
    perfStatsThresholdLower OBJECT-TYPE
      SYNTAX Counter64
      MAX-ACCESS read-create
      STATUS current
      DESCRIPTION
        "阈值下限"
      ::= { perfStatsThresholdEntry 6 }
    
    perfStatsThresholdRowStatus OBJECT-TYPE
      SYNTAX RowStatus
      MAX-ACCESS read-create
      STATUS current
      DESCRIPTION
        "行状态(添加、删除、修改)"
      ::= { perfStatsThresholdEntry 7 }


--------------------------------------------------------------------------------
--  AlarmManagementObjects[告警管理项](1.3.6.1.4.1.17409.2.2.11)
-------------------------------------------------------------------------------- 
       
    eponNotifications OBJECT IDENTIFIER ::= { eponTrapObjectGroup 1 }
    
    eponAlarmNotification NOTIFICATION-TYPE
      OBJECTS { eponTrapSequenceNumber, eponTrapOccurTime, eponTrapCode, eponTrapInstance, 
      eponTrapSeverity, eponTrapCorrelationId, eponTrapAdditionalText
         }
      STATUS current
      DESCRIPTION 
        "Alarm TRAP definition"
      ::= { eponNotifications 1 }

    eponEventNotification NOTIFICATION-TYPE
      OBJECTS { eponTrapSequenceNumber, eponTrapOccurTime, eponTrapCode, eponTrapInstance, 
      eponTrapAdditionalText
         }
      STATUS current
      DESCRIPTION 
        "Event TRAP definition"
      ::= { eponNotifications 2 }

    eponTrapObjects OBJECT IDENTIFIER ::= { eponTrapObjectGroup 2 }
    -- trap信息上报的oid顺序7641523
    eponTrapInstance OBJECT-TYPE
      SYNTAX EponAlarmInstance
      MAX-ACCESS accessible-for-notify
      STATUS current
      DESCRIPTION
        "Alarm instance, indicates the detailed managed object, which
        detects faults.
        "
      ::= { eponTrapObjects 1 }
    
    eponTrapCorrelationId OBJECT-TYPE
      SYNTAX Unsigned32
      MAX-ACCESS accessible-for-notify
      STATUS current
      DESCRIPTION
        "The unique sequence number for the alarm to be cleared, for alarm clearing. 
        Set to 0 for alarm reporting"
      ::= { eponTrapObjects 2 }
    
    eponTrapAdditionalText OBJECT-TYPE
      SYNTAX OCTET STRING ( SIZE (0..256) )
      MAX-ACCESS accessible-for-notify
      STATUS current
      DESCRIPTION
        "Additional info to the alarm, for further desciption of the
        alarm. The format of it shall be related to each kind alarm
        defined in alarm reference table"
      ::= { eponTrapObjects 3 }
    
    eponTrapCode OBJECT-TYPE
      SYNTAX EponAlarmCode
      MAX-ACCESS accessible-for-notify
      STATUS current
      DESCRIPTION
        "
        告警代码,见附录A.3"
      ::= { eponTrapObjects 4 }
    
    eponTrapSeverity OBJECT-TYPE
      SYNTAX EponSeverityType
      MAX-ACCESS accessible-for-notify
      STATUS current
      DESCRIPTION
        "
        告警严重程度。"
      ::= { eponTrapObjects 5 }
    
    eponTrapOccurTime OBJECT-TYPE
      SYNTAX DateAndTime
      MAX-ACCESS accessible-for-notify
      STATUS current
      DESCRIPTION
        "
        告警产生时间。"
      ::= { eponTrapObjects 6 }
    
    eponTrapSequenceNumber OBJECT-TYPE
      SYNTAX Unsigned32
      MAX-ACCESS accessible-for-notify
      STATUS current
      DESCRIPTION
        "
        A unique sequence number for each trap generated by node. The sequence 
        number shall be reset to 1 when node restarts.         
        The alarm sequence number shall be independent of the event sequence 
        number. Each shall be self-governed.

        --------------------------------------------------------------------------------            
        The sequence ID of alarm shall be assigned from the order of transmitting 
        trap to the NMS, instead of the order of alarm occurance. Therefore the NMS 
        will receive the continuous sequence ID.
            
        1.  When device is in active/standby mode, sequence ID shall be synchronized 
          between active and standby control module.
        2.  When control module switchover takes place, the current sequence ID shall 
          keep the synchronized value.
        3.  When device restarts, sequence ID shall start from 1.
        4.  It shall be increased per alarm trap including both alarm raising and clear.
        5.  Non-zero value shall be used. When reaches the maximum number, it shall 
        roll back to 1.          

        --------------------------------------------------------------------------------        
        The sequence ID of event shall be assigned from the order of transmitting 
        trap to the NMS. Therefore the NMS will receive the continuous sequence ID.            
        1.  When device is in active/standby mode, sequence ID shall be synchronized 
          between active and standby control module.
        2.  When control module switchover takes place, the current sequence ID shall 
          keep the synchronized value.
        3.  When device restarts, sequence ID shall start from 1.
        4.  It shall be increased per event trap.
        5.  Non-zero value shall be used. When reaches the maximum number, it shall 
        roll back to 1.        
        "
      ::= { eponTrapObjects 7 }
    
    activeAlarmTable OBJECT-TYPE
      SYNTAX SEQUENCE OF ActiveAlarmEntry
      MAX-ACCESS not-accessible
      STATUS current
      DESCRIPTION
        "Active alarm table
        
        The device shall maintain this table, to maintain all outstanding 
        (not cleared) alarms generated by the device, including:
        1. Not hit device local alarm filter. That means had been reported to
           trap receiver (NMS or EMS)
        2. Hit local alarm filter. That means not trap is reported to trap receiver
           for the alarm.
        
        The device shall maintain two numbers:
        1. Alarm sequence number: As described in eponTrapSequenceNumber, it is initially
           set to 1 when device restarts, increases per trap reported to trap receiver,
           and rollover to 1 once it reaches the maximum value. 
           From NMS's view, traps received from a nodes will be consecutive, by identifying 
           the alarm sequence number carried in alarm trap. If breaks, means some trap 
           may be lost, since packet loss between NMS and NE. 
        2. Alarm raising number: This is maintained by NE internally and does not intend for
           being acknowledged by external manage system. It is designed to uniquely indentify
           each alarm raised by NE, excluding duplicates. Once one alarm raised, despite 
           whether it is hit by alarm filter, NE shall assign a raising number to it. So, it
           major functionality is to uniquely identify alarms hit NE local alarm filter, since 
           this kindly alarm will not be reported to NMS, and hence no alarm sequence number
           is assigned to it.
           It is initially  set to 1 when device restarts, increases per alarm generation (
           excluding duplicates), and rollover to 1 once it reaches the maximum value. 
        
        FUNCTION DESCRIPTION OF ACTIVE ALARM TABLE:         
        ALARM RAISING
        ----------------------        
        1. When NE detects one fault and associates to one kind of alarm, it shall check whether
           there is same alarm in active alarm table, which is indexed by alarm code and alarm
           instance. If hits, it means duplicates, update the corresponding entry of the table.
           Otherwise,
        2. The alarm is not a duplicate. Assign an alarm raising number. Check whether the
 alarm hits local alarm filters. If hits, set alarm sequence number to 0.
           Create an entry into active alarm table. Otherwise,
        3. Assign an alarm sequence number to the alarm. Create an entry into active alarm
 table. Report the alarm trap to all trap receivers.
           
        ALARM CLEARING
        ----------------------        
        1. When NE detects one fault is cleared and associates to one kind of alarm, it shall 
           check whether there is corresponding alarm in active alarm table, which is indexed
by alarm code and alarm instance. If no hit, escape this clear event. Upon a hit,
if the alarm sequence number is 0, move the active alarm entry to history alarm
table and update the corresponding fields. At this case, historyAlarmCorrelationId
and historyAlarmSeqNum will be set to 0.
           Otherwise,
        2. Assign an alarm sequence number to the clear trap. Report the alarm clear trap to 
           all trap receivers. Move the active alarm entry to history alarm table and update 
           the corresponding fields. At this case, activeAlarmSeqNum shall be copied to 
           historyAlarmCorrelationId, and historyAlarmSeqNum shall be set to the new alarm
           sequence number for the clear trap.
        
        ALARM SYNCHRONIZATION BETWEEN NE AND NMS
        ---------------------------------------------        
        1. Once NMS finds the alarm sequence number in reported alarm traps is not continuous,
           it will walk active or history alarm table of the NE for the lost seuqence number.
        "
      ::= { eponAlarmObjGroup 1 }
    
    activeAlarmEntry OBJECT-TYPE
      SYNTAX ActiveAlarmEntry
      MAX-ACCESS not-accessible
      STATUS current
      DESCRIPTION
        ""
      INDEX { activeAlarmSeqNum, activeAlarmRaisingNumber }
      ::= { activeAlarmTable 1 }
    
    ActiveAlarmEntry ::=
      SEQUENCE { 
        activeAlarmSeqNum
          Unsigned32,
        activeAlarmCode
          EponAlarmCode,
        activeAlarmInstance
          EponAlarmInstance,
        activeAlarmSeverity
          EponSeverityType,       
        activeAlarmRaisingNumber
          Unsigned32,
        activeAlarmFirstOccurTime
          DateAndTime,
        activeAlarmLastOccurTime
          DateAndTime,
        activeAlarmRepeats
          Counter32,
        activeAlarmConfirm
          TruthValue,
        activeAlarmAdditionalText
          OCTET STRING  
       }

    activeAlarmSeqNum OBJECT-TYPE
      SYNTAX Unsigned32
      MAX-ACCESS not-accessible
      STATUS current
      DESCRIPTION
        "Alarm sequence number
        
        The definition refered to the description of activeAlarmTable"
      ::= { activeAlarmEntry 1 }
    
    activeAlarmCode OBJECT-TYPE
      SYNTAX EponAlarmCode
      MAX-ACCESS read-only
      STATUS current
      DESCRIPTION
        "
        告警代码,见附录A.3
        "
      ::= { activeAlarmEntry 2 }    
    activeAlarmInstance OBJECT-TYPE
      SYNTAX EponAlarmInstance
      MAX-ACCESS read-only
      STATUS current
      DESCRIPTION
        "Alarm instance, indicates the detailed managed object"
      ::= { activeAlarmEntry 3 }
    
    activeAlarmSeverity OBJECT-TYPE
      SYNTAX EponSeverityType
      MAX-ACCESS read-only
      STATUS current
      DESCRIPTION
        "
        告警严重程度。"     
        ::= { activeAlarmEntry 4 }

    activeAlarmRaisingNumber OBJECT-TYPE
      SYNTAX Unsigned32
      MAX-ACCESS not-accessible
      STATUS current
      DESCRIPTION
        "Alarm raising number.        
        The definition refered to the description of activeAlarmTable"
      ::= { activeAlarmEntry 5 }
                                   
    activeAlarmFirstOccurTime OBJECT-TYPE
      SYNTAX DateAndTime
      MAX-ACCESS read-only
      STATUS current
      DESCRIPTION
        "
        告警初始发生的时间        
        The time stamp when alarm occurs, which triggered to create the 
        active alarm entry."
      ::= { activeAlarmEntry 6 }

    activeAlarmLastOccurTime OBJECT-TYPE
      SYNTAX DateAndTime
      MAX-ACCESS read-only
      STATUS current
      DESCRIPTION
        "
        The time stamp when alarm occurs, where the alarm is duplicated 
        with existed active alarm entry, and it was the latest one. "
      ::= { activeAlarmEntry 7 }
    
    activeAlarmRepeats OBJECT-TYPE
      SYNTAX Counter32
      MAX-ACCESS read-only
      STATUS current
      DESCRIPTION
        "Number of repeated alarms for this active alarm entry"
      ::= { activeAlarmEntry 8 }
  
    activeAlarmConfirm OBJECT-TYPE
      SYNTAX TruthValue
      MAX-ACCESS read-write
      STATUS current
      DESCRIPTION
        "
        告警确认        
        Node shall not clear an active alarm, upon the confirmation 
        of the active alarm, but just mark an acknowledged status.
        
        An alarm will only be cleared once the clear condition hits."
      ::= { activeAlarmEntry 9 }

    activeAlarmAdditionalText OBJECT-TYPE
      SYNTAX OCTET STRING (SIZE (0..256))
      MAX-ACCESS read-only
      STATUS current
      DESCRIPTION
        "Additional info to the alarm, for further desciption of the
        alarm. The format of it shall be related to each kind alarm
        defined in alarm reference table"
      ::= { activeAlarmEntry 10 }

    historyAlarmTable OBJECT-TYPE
      SYNTAX SEQUENCE OF HistoryAlarmEntry
      MAX-ACCESS not-accessible
      STATUS current
      DESCRIPTION
        "History alarm table.        
        The device shall maintain this table, to maintain all cleared 
        alarms generated by the device, including:        
        1. Not hit device local alarm filter. That means had been reported to
           trap receiver (NMS or EMS)
        2. Hit local alarm filter. That means not trap is reported to trap receiver
           for the alarm.        
        The number of history alarm enteries in the table could be device-specific.
        However, it is recommended no less than 200 entries.        
        The detailed function definition refers to that given in description of
        activeAlarmTable.
        "
      ::= { eponAlarmObjGroup 2 }
    
    historyAlarmEntry OBJECT-TYPE
      SYNTAX HistoryAlarmEntry
      MAX-ACCESS not-accessible
      STATUS current
      DESCRIPTION
        ""
      INDEX { historyAlarmSeqNum, historyAlarmRaisingNumber }
      ::= { historyAlarmTable 1 }
    
    HistoryAlarmEntry ::=
      SEQUENCE { 
        historyAlarmSeqNum
          Unsigned32,
        historyAlarmCode
          EponAlarmCode,
        historyAlarmInstance
          EponAlarmInstance,
        historyAlarmSeverity
          EponSeverityType,       
        historyAlarmRaisingNumber
          Unsigned32,
        historyAlarmFirstOccurTime
          DateAndTime,
        historyAlarmLastOccurTime
          DateAndTime,
        historyAlarmRepeats
          Counter32,
        historyAlarmCorrelationId
          Unsigned32,
        historyAlarmAdditionalText
          OCTET STRING,
        historyAlarmClearTime
          DateAndTime 
       }

    historyAlarmSeqNum OBJECT-TYPE
      SYNTAX Unsigned32
      MAX-ACCESS not-accessible
      STATUS current
      DESCRIPTION
        "Alarm sequence number
        
        The definition refered to the description of historyAlarmTable"
      ::= { historyAlarmEntry 1 }
    
    historyAlarmCode OBJECT-TYPE
      SYNTAX EponAlarmCode
      MAX-ACCESS read-only
      STATUS current
      DESCRIPTION
        "
        告警代码,见附录A.3
        "
      ::= { historyAlarmEntry 2 }
    
    historyAlarmInstance OBJECT-TYPE
      SYNTAX EponAlarmInstance
      MAX-ACCESS read-only
      STATUS current
      DESCRIPTION
        "Alarm instance, indicates the detailed managed object"
      ::= { historyAlarmEntry 3 }
    
    historyAlarmSeverity OBJECT-TYPE
      SYNTAX EponSeverityType
      MAX-ACCESS read-only
      STATUS current
      DESCRIPTION
        "
        告警严重程度。"     
        ::= { historyAlarmEntry 4 }

    historyAlarmRaisingNumber OBJECT-TYPE
      SYNTAX Unsigned32
      MAX-ACCESS not-accessible
      STATUS current
      DESCRIPTION
        "Alarm raising number.        
        The definition refered to the description of historyAlarmTable"
      ::= { historyAlarmEntry 5 }
                                   
    historyAlarmFirstOccurTime OBJECT-TYPE
      SYNTAX DateAndTime
      MAX-ACCESS read-only
      STATUS current
      DESCRIPTION
        "
        告警初始发生的时间        
        The time stamp when alarm occurs, which triggered to create the 
        history alarm entry."
      ::= { historyAlarmEntry 6 }

    historyAlarmLastOccurTime OBJECT-TYPE
      SYNTAX DateAndTime
      MAX-ACCESS read-only
      STATUS current
      DESCRIPTION
        "
        The time stamp when alarm occurs, where the alarm is duplicated 
        with existed history alarm entry, and it was the latest one. "
      ::= { historyAlarmEntry 7 }
    
    historyAlarmRepeats OBJECT-TYPE
      SYNTAX Counter32
      MAX-ACCESS read-only
      STATUS current
      DESCRIPTION
        "Number of repeated alarms for this history alarm entry"
      ::= { historyAlarmEntry 8 }
  
    historyAlarmCorrelationId OBJECT-TYPE
      SYNTAX Unsigned32
      MAX-ACCESS read-only
      STATUS current
      DESCRIPTION
        "It is the corresponding sequence ID of the alarm that to
        be cleared. "
      ::= { historyAlarmEntry 9 }
    historyAlarmAdditionalText OBJECT-TYPE
      SYNTAX OCTET STRING (SIZE (0..256))
      MAX-ACCESS read-only
      STATUS current
      DESCRIPTION
        "Additional info to the alarm, for further desciption of the
        alarm. The format of it shall be related to each kind alarm
        defined in alarm reference table"
      ::= { historyAlarmEntry 10 }

    historyAlarmClearTime OBJECT-TYPE
      SYNTAX DateAndTime
      MAX-ACCESS read-only
      STATUS current
      DESCRIPTION
        "Define when the alarm was cleared"
      ::= { historyAlarmEntry 11 }

    eventLogTable OBJECT-TYPE
      SYNTAX SEQUENCE OF EventLogEntry
      MAX-ACCESS not-accessible
      STATUS current
      DESCRIPTION
        "Event log table.        
        The device shall maintain this table, to maintain all events had
        be reported by the device, including:
        1.  The event table shall be saved in RAM memory and shall be flushed 
          when OLT restarts.
        2.  The event log table shall support no less than 200 entries.  When 
          the event log table is full, the oldest entry in the table shall be 
          removed first. 
        3.  When OLT is configured with control module redundancy, active controller
          shall automatically synchronize the events in event log table  b/w active 
          and standby.
        "
      ::= { eponAlarmObjGroup 3 }
    
    eventLogEntry OBJECT-TYPE
      SYNTAX EventLogEntry
      MAX-ACCESS not-accessible
      STATUS current
      DESCRIPTION
        ""
      INDEX { eventSeqNum }
      ::= { eventLogTable 1 }
    
    EventLogEntry ::=
      SEQUENCE { 
        eventSeqNum
          Unsigned32,
        eventCode
          EponAlarmCode,
        eventInstance
          EponAlarmInstance,
        eventOccurTime
          DateAndTime,
        eventAdditionalText
          OCTET STRING
       }

    eventSeqNum OBJECT-TYPE
      SYNTAX Unsigned32
      MAX-ACCESS not-accessible
      STATUS current
      DESCRIPTION
        "Event sequence number
        
        The definition refered to the description of eponTrapSequenceNumber"
      ::= { eventLogEntry 1 }
    
    eventCode OBJECT-TYPE
      SYNTAX EponAlarmCode
      MAX-ACCESS read-only
      STATUS current
      DESCRIPTION
        "
        事件代码,见附录A.3
        "
      ::= { eventLogEntry 2 }
  
    eventInstance OBJECT-TYPE
      SYNTAX EponAlarmInstance
      MAX-ACCESS read-only
      STATUS current
      DESCRIPTION
        "Event instance, indicates the detailed managed object"
      ::= { eventLogEntry 3 }
                                  
    eventOccurTime OBJECT-TYPE
      SYNTAX DateAndTime
      MAX-ACCESS read-only
      STATUS current
      DESCRIPTION
        "
        The time stamp when event occurs"
      ::= { eventLogEntry 4 }

    eventAdditionalText OBJECT-TYPE
      SYNTAX OCTET STRING (SIZE (0..256))
      MAX-ACCESS read-only
      STATUS current
      DESCRIPTION
        "Additional info to the event, for further desciption of the
        event. The format of it shall be related to each kind event
        defined in event reference table"
      ::= { eventLogEntry 5 }
    
    eponManagementAddrTable OBJECT-TYPE
      SYNTAX SEQUENCE OF EponManagementAddrEntry
      MAX-ACCESS not-accessible
      STATUS current
      DESCRIPTION
        "A table of transport addresses to be used in the generation
        of SNMP messages."
      ::= { eponManagementObjGroup 1 }
    
    eponManagementAddrEntry OBJECT-TYPE
      SYNTAX EponManagementAddrEntry
      MAX-ACCESS not-accessible
      STATUS current
      DESCRIPTION
        "A transport address to be used in the generation
        of SNMP operations.        
        Entries in the snmpTargetAddrTable are created and
        deleted using the snmpTargetAddrRowStatus object."
      INDEX { eponManagementAddrName }
      ::= { eponManagementAddrTable 1 }
    
    EponManagementAddrEntry ::=
      SEQUENCE { 
        eponManagementAddrName
          OCTET STRING,
        eponManagementAddrTAddress
          TAddress,
        eponManagementAddrCommunity
          OCTET STRING,
        eponManagementAddrRowStatus
          RowStatus
       }

    eponManagementAddrName OBJECT-TYPE
      SYNTAX OCTET STRING (SIZE (1..32))
      MAX-ACCESS not-accessible
      STATUS current
      DESCRIPTION
        "
        网管节点的名字"
      ::= { eponManagementAddrEntry 1 }
    
    eponManagementAddrTAddress OBJECT-TYPE
      SYNTAX TAddress
      MAX-ACCESS read-create
      STATUS current
      DESCRIPTION
        "
        网管节点的传输层地址和TRAP UDP端口号。"
      ::= { eponManagementAddrEntry 2 }
    
    eponManagementAddrCommunity OBJECT-TYPE
      SYNTAX OCTET STRING (SIZE (0..64) )
      MAX-ACCESS read-create
      STATUS current
      DESCRIPTION
        "
        发送TRAP的Community。"
      ::= { eponManagementAddrEntry 3 }
    
    eponManagementAddrRowStatus OBJECT-TYPE
      SYNTAX RowStatus
      MAX-ACCESS read-create
      STATUS current
      DESCRIPTION
        "
        增加删除一个EPON管理地址。"
      ::= { eponManagementAddrEntry 4 }
                    
END
