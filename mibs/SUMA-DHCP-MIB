--
-- SUMA-DHCP-MIB.my
-- MIB generated by MG-SOFT Visual MIB Builder Version 4.0 Build 349
-- Wednesday, November 15, 2017 at 14:45:11
--

--  SUMA-DHCP-MIB.mib
-- MIB generated by MG-SOFT Visual MIB Builder Version 4.0 Build 349
-- Wednesday, November 01, 2017 at 17:52:29
-- 
--  SUMA-DHCP-MIB.mib
-- MIB generated by MG-SOFT Visual MIB Builder Version 4.0 Build 349
-- Tuesday, October 31, 2017 at 14:52:32
-- 
--  SUMA-DHCP-MIB.my
-- MIB generated by MG-SOFT Visual MIB Builder Version 4.0 Build 349
-- Monday, October 30, 2017 at 17:36:04
-- 
--  SUMA-DHCP-MIB.mib
-- MIB generated by MG-SOFT Visual MIB Builder Version 4.0 Build 349
-- Friday, October 27, 2017 at 11:23:30
-- 
--  SUMA-VOIP-MIB.my
-- MIB generated by MG-SOFT Visual MIB Builder Version 4.0 Build 349
-- Monday, June 19, 2017 at 15:16:33
-- 
--  SUMA-GPON-MIB.my
-- MIB generated by MG-SOFT Visual MIB Builder Version 4.0 Build 349
-- Tuesday, December 20, 2016 at 09:00:41
-- 
--  SUMA-GPON-MIB.my
-- MIB generated by MG-SOFT Visual MIB Builder Version 4.0 Build 349
-- Monday, December 19, 2016 at 14:05:25
-- 
--  SUMA-GPON-MIB.my
-- MIB generated by MG-SOFT Visual MIB Builder Version 4.0 Build 349
-- Sunday, December 18, 2016 at 14:46:38
-- 
--  SUMA-GPON-MIB.mib
-- MIB generated by MG-SOFT Visual MIB Builder Version 4.0 Build 349
-- Wednesday, October 19, 2011 at 15:54:31
-- 

	SUMA-DHCP-MIB DEFINITIONS ::= BEGIN
 
		IMPORTS
			enterprises, IpAddress, Unsigned32, Counter64, OBJECT-TYPE			
				FROM SNMPv2-SMI			
			RowStatus, MacAddress, TEXTUAL-CONVENTION			
				FROM SNMPv2-TC;
	
	
--
-- Textual conventions
--
	
--  Textual conventions
-- 
-- Textual conventions
-- 
-- Textual conventions
-- 
-- Textual conventions
-- 
-- Textual conventions
-- 
-- Textual conventions
-- 
-- Textual conventions
-- 
-- Textual conventions
-- 
		TopGPonSlotIndex ::= TEXTUAL-CONVENTION
			STATUS current
			DESCRIPTION 
				"This represents the slot number in the epon shelf."
			SYNTAX INTEGER (1..18)

		TopGPonPonIndex ::= TEXTUAL-CONVENTION
			STATUS current
			DESCRIPTION 
				"This represents the PON number in the epon board."
			SYNTAX INTEGER (1..8)

		TopGPonOnuAuthNum ::= TEXTUAL-CONVENTION
			STATUS current
			DESCRIPTION 
				"This represents the ONU auth number in the epon board."
			SYNTAX INTEGER (1..128)

		TopGPonUniPortIndex ::= TEXTUAL-CONVENTION
			STATUS current
			DESCRIPTION 
				"This represents the ONU uni number in the epon board."
			SYNTAX INTEGER (1..32)

		TopGPonSniIndex ::= TEXTUAL-CONVENTION
			STATUS current
			DESCRIPTION 
				"This represents the sni port number in the uplink board."
			SYNTAX INTEGER (1..8)

		TopGPonDeviceIndex ::= TEXTUAL-CONVENTION
			STATUS current
			DESCRIPTION 
				"From MSB on, OLT slot index-8bits, PON/SNI port-8bits, 
				OnuNUM-8bits and UNI port-8bits.
				OLT PON/SNI Port - OnuNum and UNI port shall be set to 0."
			SYNTAX Unsigned32

	
--
-- Node definitions
--
	
--  Node definitions
-- 
-- Node definitions
-- 
-- Node definitions
-- 
-- Node definitions
-- 
-- Node definitions
-- 
-- Node definitions
-- 
-- Textual conventions
-- 
-- Node definitions
-- 1.3.6.1.4.1.32285
-- 1.3.6.1.4.1.32285
-- 1.3.6.1.4.1.32285
-- 1.3.6.1.4.1.32285
-- 1.3.6.1.4.1.32285
-- 1.3.6.1.4.1.32285
		-- 1.3.6.1.4.1.32285
		sumaRoot OBJECT IDENTIFIER ::= { enterprises 32285 }

		
--       1.3.6.1.4.1.32285.11
-- 1.3.6.1.4.1.32285.11
-- 1.3.6.1.4.1.32285.11
-- 1.3.6.1.4.1.32285.11
-- 1.3.6.1.4.1.32285.11
-- 1.3.6.1.4.1.32285.11
		-- 1.3.6.1.4.1.32285.11
		topvisionRoot OBJECT IDENTIFIER ::= { sumaRoot 11 }

		
--     1.3.6.1.4.1.32285.11.7
-- 1.3.6.1.4.1.32285.11.7
-- 1.3.6.1.4.1.32285.11.7
-- 1.3.6.1.4.1.32285.11.7
		-- 1.3.6.1.4.1.32285.11.7
		topvisionDhcpTree OBJECT IDENTIFIER ::= { topvisionRoot 7 }

		
-- 1.3.6.1.4.1.32285.11.7.1
		-- 1.3.6.1.4.1.32285.11.7.1
		topOltDhcpGlobalObjects OBJECT IDENTIFIER ::= { topvisionDhcpTree 1 }

		
--     1.3.6.1.4.1.32285.11.7.1.1
-- 1.3.6.1.4.1.32285.11.7.1.1
-- 1.3.6.1.4.1.32285.11.7.1.1
-- 1.3.6.1.4.1.32285.11.7.1.1
		-- 1.3.6.1.4.1.32285.11.7.1.1
		topOltDhcpEnable OBJECT-TYPE
			SYNTAX INTEGER
				{
				enable(1),
				disable(2)
				}
			MAX-ACCESS read-write
			STATUS current
			DESCRIPTION
				"Description."
			DEFVAL { disable }
			::= { topOltDhcpGlobalObjects 1 }

		
--     1.3.6.1.4.1.32285.11.7.1.2
-- 1.3.6.1.4.1.32285.11.7.1.2
-- 1.3.6.1.4.1.32285.11.7.1.2
-- 1.3.6.1.4.1.32285.11.7.1.2
		-- 1.3.6.1.4.1.32285.11.7.1.2
		topOltDhcpOpt82Enable OBJECT-TYPE
			SYNTAX INTEGER
				{
				enable(1),
				disable(2)
				}
			MAX-ACCESS read-write
			STATUS current
			DESCRIPTION
				"Description."
			DEFVAL { disable }
			::= { topOltDhcpGlobalObjects 2 }

		
--     1.3.6.1.4.1.32285.11.7.1.3
-- 1.3.6.1.4.1.32285.11.7.1.3
-- 1.3.6.1.4.1.32285.11.7.1.3
-- 1.3.6.1.4.1.32285.11.7.1.3
		-- 1.3.6.1.4.1.32285.11.7.1.3
		topOltDhcpOpt82Policy OBJECT-TYPE
			SYNTAX INTEGER
				{
				insert(1),
				replace(2)
				}
			MAX-ACCESS read-write
			STATUS current
			DESCRIPTION
				"Description."
			DEFVAL { insert }
			::= { topOltDhcpGlobalObjects 3 }

		
--     1.3.6.1.4.1.32285.11.7.1.4
-- 1.3.6.1.4.1.32285.11.7.1.4
-- 1.3.6.1.4.1.32285.11.7.1.4
-- 1.3.6.1.4.1.32285.11.7.1.4
		-- 1.3.6.1.4.1.32285.11.7.1.4
		topOltDhcpOpt82Format OBJECT-TYPE
			SYNTAX OCTET STRING (SIZE (1..127))
			MAX-ACCESS read-write
			STATUS current
			DESCRIPTION
				"Description."
			DEFVAL { "AccessNodeIdentifier/ANI_rack/ANI_frame/ANI_slot/ANI_subslot/" }
			::= { topOltDhcpGlobalObjects 4 }

		
--     1.3.6.1.4.1.32285.11.7.1.5
-- 1.3.6.1.4.1.32285.11.7.1.5
-- 1.3.6.1.4.1.32285.11.7.1.5
-- 1.3.6.1.4.1.32285.11.7.1.5
		-- 1.3.6.1.4.1.32285.11.7.1.5
		topOltDhcpSourceVerifyEnable OBJECT-TYPE
			SYNTAX INTEGER
				{
				enable(1),
				disable(2)
				}
			MAX-ACCESS read-write
			STATUS current
			DESCRIPTION
				"Description."
			DEFVAL { disable }
			::= { topOltDhcpGlobalObjects 5 }

		
--     1.3.6.1.4.1.32285.11.7.1.6
-- 1.3.6.1.4.1.32285.11.7.1.6
-- 1.3.6.1.4.1.32285.11.7.1.6
-- 1.3.6.1.4.1.32285.11.7.1.6
		-- 1.3.6.1.4.1.32285.11.7.1.6
		topOltPPPoEPlusEnable OBJECT-TYPE
			SYNTAX INTEGER
				{
				enable(1),
				disable(2)
				}
			MAX-ACCESS read-write
			STATUS current
			DESCRIPTION
				"Description."
			DEFVAL { disable }
			::= { topOltDhcpGlobalObjects 6 }

		
--     1.3.6.1.4.1.32285.11.7.1.7
-- 1.3.6.1.4.1.32285.11.7.1.7
-- 1.3.6.1.4.1.32285.11.7.1.7
-- 1.3.6.1.4.1.32285.11.7.1.7
		-- 1.3.6.1.4.1.32285.11.7.1.7
		topOltPPPoEPlusPolicy OBJECT-TYPE
			SYNTAX INTEGER
				{
				insert(1),
				replace(2)
				}
			MAX-ACCESS read-write
			STATUS current
			DESCRIPTION
				"Description."
			DEFVAL { insert }
			::= { topOltDhcpGlobalObjects 7 }

		
--     1.3.6.1.4.1.32285.11.7.1.8
-- 1.3.6.1.4.1.32285.11.7.1.8
-- 1.3.6.1.4.1.32285.11.7.1.8
-- 1.3.6.1.4.1.32285.11.7.1.8
		-- 1.3.6.1.4.1.32285.11.7.1.8
		topOltPPPoEPlusFormat OBJECT-TYPE
			SYNTAX OCTET STRING (SIZE (1..127))
			MAX-ACCESS read-write
			STATUS current
			DESCRIPTION
				"Description."
			DEFVAL { "AccessNodeIdentifier/ANI_rack/ANI_frame/ANI_slot/ANI_subslot/" }
			::= { topOltDhcpGlobalObjects 8 }

		
-- 1.3.6.1.4.1.32285.11.7.2
		-- 1.3.6.1.4.1.32285.11.7.2
		topOltDhcpVLANCfgTable OBJECT-TYPE
			SYNTAX SEQUENCE OF TopOltDhcpVLANCfgEntry
			MAX-ACCESS not-accessible
			STATUS current
			DESCRIPTION
				"Description."
			::= { topvisionDhcpTree 2 }

		
--     1.3.6.1.4.1.32285.11.7.2.1
-- 1.3.6.1.4.1.32285.11.7.2.1
-- 1.3.6.1.4.1.32285.11.7.2.1
-- 1.3.6.1.4.1.32285.11.7.2.1
		-- 1.3.6.1.4.1.32285.11.7.2.1
		topOltDhcpVLANCfgEntry OBJECT-TYPE
			SYNTAX TopOltDhcpVLANCfgEntry
			MAX-ACCESS not-accessible
			STATUS current
			DESCRIPTION
				"Description."
			INDEX { topOltDhcpVLANIndex }
			::= { topOltDhcpVLANCfgTable 1 }

		
		TopOltDhcpVLANCfgEntry ::=
			SEQUENCE { 
				topOltDhcpVLANIndex
					INTEGER,
				topOltDhcpVLANMode
					INTEGER,
				topOltDhcpVLANRelayMode
					INTEGER
			 }

--     1.3.6.1.4.1.32285.11.7.2.1.1
-- 1.3.6.1.4.1.32285.11.7.2.1.1
-- 1.3.6.1.4.1.32285.11.7.2.1.1
-- 1.3.6.1.4.1.32285.11.7.2.1.1
		-- 1.3.6.1.4.1.32285.11.7.2.1.1
		topOltDhcpVLANIndex OBJECT-TYPE
			SYNTAX INTEGER (1..4094)
			MAX-ACCESS not-accessible
			STATUS current
			DESCRIPTION
				"Description."
			::= { topOltDhcpVLANCfgEntry 1 }

		
--     1.3.6.1.4.1.32285.11.7.2.1.2
-- 1.3.6.1.4.1.32285.11.7.2.1.2
-- 1.3.6.1.4.1.32285.11.7.2.1.2
-- 1.3.6.1.4.1.32285.11.7.2.1.2
		-- 1.3.6.1.4.1.32285.11.7.2.1.2
		topOltDhcpVLANMode OBJECT-TYPE
			SYNTAX INTEGER
				{
				snooping(1),
				relay(2)
				}
			MAX-ACCESS read-write
			STATUS current
			DESCRIPTION
				"Description."
			DEFVAL { snooping }
			::= { topOltDhcpVLANCfgEntry 2 }

		
--     1.3.6.1.4.1.32285.11.7.2.1.3
-- 1.3.6.1.4.1.32285.11.7.2.1.3
-- 1.3.6.1.4.1.32285.11.7.2.1.3
-- 1.3.6.1.4.1.32285.11.7.2.1.3
		-- 1.3.6.1.4.1.32285.11.7.2.1.3
		topOltDhcpVLANRelayMode OBJECT-TYPE
			SYNTAX INTEGER
				{
				standard(1),
				option60(2)
				}
			MAX-ACCESS read-write
			STATUS current
			DESCRIPTION
				"Description."
			DEFVAL { standard }
			::= { topOltDhcpVLANCfgEntry 3 }

		
-- 1.3.6.1.4.1.32285.11.7.3
		-- 1.3.6.1.4.1.32285.11.7.3
		topOltDhcpVifCfgTable OBJECT-TYPE
			SYNTAX SEQUENCE OF TopOltDhcpVifCfgEntry
			MAX-ACCESS not-accessible
			STATUS current
			DESCRIPTION
				"Description."
			::= { topvisionDhcpTree 3 }

		
--     1.3.6.1.4.1.32285.11.7.3.1
-- 1.3.6.1.4.1.32285.11.7.3.1
-- 1.3.6.1.4.1.32285.11.7.3.1
-- 1.3.6.1.4.1.32285.11.7.3.1
		-- 1.3.6.1.4.1.32285.11.7.3.1
		topOltDhcpVifCfgEntry OBJECT-TYPE
			SYNTAX TopOltDhcpVifCfgEntry
			MAX-ACCESS not-accessible
			STATUS current
			DESCRIPTION
				"Description."
			INDEX { topOltDhcpVifIndex, topOltDhcpVifOpt60StrIndex }
			::= { topOltDhcpVifCfgTable 1 }

		
		TopOltDhcpVifCfgEntry ::=
			SEQUENCE { 
				topOltDhcpVifIndex
					INTEGER,
				topOltDhcpVifOpt60StrIndex
					OCTET STRING,
				topOltDhcpVifAgentAddr
					IpAddress,
				topOltDhcpVifServerGroup
					INTEGER,
				topOltDhcpVifRowStatus
					RowStatus
			 }

--     1.3.6.1.4.1.32285.11.7.3.1.1
-- 1.3.6.1.4.1.32285.11.7.3.1.1
-- 1.3.6.1.4.1.32285.11.7.3.1.1
-- 1.3.6.1.4.1.32285.11.7.3.1.1
		-- 1.3.6.1.4.1.32285.11.7.3.1.1
		topOltDhcpVifIndex OBJECT-TYPE
			SYNTAX INTEGER (1..4094)
			MAX-ACCESS not-accessible
			STATUS current
			DESCRIPTION
				"Description."
			::= { topOltDhcpVifCfgEntry 1 }

		
--     1.3.6.1.4.1.32285.11.7.3.1.2
-- 1.3.6.1.4.1.32285.11.7.3.1.2
-- 1.3.6.1.4.1.32285.11.7.3.1.2
-- 1.3.6.1.4.1.32285.11.7.3.1.2
		-- 1.3.6.1.4.1.32285.11.7.3.1.2
		topOltDhcpVifOpt60StrIndex OBJECT-TYPE
			SYNTAX OCTET STRING
			MAX-ACCESS not-accessible
			STATUS current
			DESCRIPTION
				"Description."
			::= { topOltDhcpVifCfgEntry 2 }

		
--     1.3.6.1.4.1.32285.11.7.3.1.3
-- 1.3.6.1.4.1.32285.11.7.3.1.3
-- 1.3.6.1.4.1.32285.11.7.3.1.3
-- 1.3.6.1.4.1.32285.11.7.3.1.3
		-- 1.3.6.1.4.1.32285.11.7.3.1.3
		topOltDhcpVifAgentAddr OBJECT-TYPE
			SYNTAX IpAddress
			MAX-ACCESS read-write
			STATUS current
			DESCRIPTION
				"Description."
			::= { topOltDhcpVifCfgEntry 3 }

		
--     1.3.6.1.4.1.32285.11.7.3.1.4
-- 1.3.6.1.4.1.32285.11.7.3.1.4
-- 1.3.6.1.4.1.32285.11.7.3.1.4
-- 1.3.6.1.4.1.32285.11.7.3.1.4
		-- 1.3.6.1.4.1.32285.11.7.3.1.4
		topOltDhcpVifServerGroup OBJECT-TYPE
			SYNTAX INTEGER (1..20)
			MAX-ACCESS read-write
			STATUS current
			DESCRIPTION
				"Description."
			::= { topOltDhcpVifCfgEntry 4 }

		
--     1.3.6.1.4.1.32285.11.7.3.1.5
-- 1.3.6.1.4.1.32285.11.7.3.1.5
-- 1.3.6.1.4.1.32285.11.7.3.1.5
-- 1.3.6.1.4.1.32285.11.7.3.1.5
		-- 1.3.6.1.4.1.32285.11.7.3.1.5
		topOltDhcpVifRowStatus OBJECT-TYPE
			SYNTAX RowStatus
			MAX-ACCESS read-create
			STATUS current
			DESCRIPTION
				"Description."
			::= { topOltDhcpVifCfgEntry 5 }

		
-- 1.3.6.1.4.1.32285.11.7.4
		-- 1.3.6.1.4.1.32285.11.7.4
		topOltDhcpServerGroupTable OBJECT-TYPE
			SYNTAX SEQUENCE OF TopOltDhcpServerGroupEntry
			MAX-ACCESS not-accessible
			STATUS current
			DESCRIPTION
				"Description."
			::= { topvisionDhcpTree 4 }

		
--     1.3.6.1.4.1.32285.11.7.4.1
-- 1.3.6.1.4.1.32285.11.7.4.1
-- 1.3.6.1.4.1.32285.11.7.4.1
-- 1.3.6.1.4.1.32285.11.7.4.1
		-- 1.3.6.1.4.1.32285.11.7.4.1
		topOltDhcpServerGroupEntry OBJECT-TYPE
			SYNTAX TopOltDhcpServerGroupEntry
			MAX-ACCESS not-accessible
			STATUS current
			DESCRIPTION
				"Description."
			INDEX { topOltDhcpServerGroupIndex }
			::= { topOltDhcpServerGroupTable 1 }

		
		TopOltDhcpServerGroupEntry ::=
			SEQUENCE { 
				topOltDhcpServerGroupIndex
					INTEGER,
				topOltDhcpServerIpList
					OCTET STRING,
				topOltDhcpServerBindNum
					INTEGER,
				topOltDhcpServerRowStatus
					RowStatus
			 }

--     1.3.6.1.4.1.32285.11.7.4.1.1
-- 1.3.6.1.4.1.32285.11.7.4.1.1
-- 1.3.6.1.4.1.32285.11.7.4.1.1
-- 1.3.6.1.4.1.32285.11.7.4.1.1
		-- 1.3.6.1.4.1.32285.11.7.4.1.1
		topOltDhcpServerGroupIndex OBJECT-TYPE
			SYNTAX INTEGER (1..20)
			MAX-ACCESS not-accessible
			STATUS current
			DESCRIPTION
				"Description."
			::= { topOltDhcpServerGroupEntry 1 }

		
-- 1.3.6.1.4.1.32285.11.7.4.1.2
		-- 1.3.6.1.4.1.32285.11.7.4.1.2
		topOltDhcpServerIpList OBJECT-TYPE
			SYNTAX OCTET STRING (SIZE (4..20))
			MAX-ACCESS read-write
			STATUS current
			DESCRIPTION
				"Description."
			::= { topOltDhcpServerGroupEntry 2 }

		
		-- 1.3.6.1.4.1.32285.11.7.4.1.3
		topOltDhcpServerBindNum OBJECT-TYPE
			SYNTAX INTEGER
			MAX-ACCESS read-only
			STATUS current
			DESCRIPTION
				"Description."
			::= { topOltDhcpServerGroupEntry 3 }

		
--     1.3.6.1.4.1.32285.11.7.4.1.3
-- 1.3.6.1.4.1.32285.11.7.4.1.3
-- 1.3.6.1.4.1.32285.11.7.4.1.3
-- 1.3.6.1.4.1.32285.11.7.4.1.3
		-- 1.3.6.1.4.1.32285.11.7.4.1.4
		topOltDhcpServerRowStatus OBJECT-TYPE
			SYNTAX RowStatus
			MAX-ACCESS read-create
			STATUS current
			DESCRIPTION
				"Description."
			::= { topOltDhcpServerGroupEntry 4 }

		
-- 1.3.6.1.4.1.32285.11.7.5
		-- 1.3.6.1.4.1.32285.11.7.5
		topOltDhcpPortAttributeTable OBJECT-TYPE
			SYNTAX SEQUENCE OF TopOltDhcpPortAttributeEntry
			MAX-ACCESS not-accessible
			STATUS current
			DESCRIPTION
				"Description."
			::= { topvisionDhcpTree 5 }

		
--     1.3.6.1.4.1.32285.11.7.6.1
-- 1.3.6.1.4.1.32285.11.7.6.1
-- 1.3.6.1.4.1.32285.11.7.6.1
-- 1.3.6.1.4.1.32285.11.7.5.1
		-- 1.3.6.1.4.1.32285.11.7.5.1
		topOltDhcpPortAttributeEntry OBJECT-TYPE
			SYNTAX TopOltDhcpPortAttributeEntry
			MAX-ACCESS not-accessible
			STATUS current
			DESCRIPTION
				"Description."
			INDEX { topOltDhcpPortProtIndex, topOltDhcpPortTypeIndex, topOltDhcpSlotIndex, topOltDhcpPortIndex }
			::= { topOltDhcpPortAttributeTable 1 }

		
		TopOltDhcpPortAttributeEntry ::=
			SEQUENCE { 
				topOltDhcpPortProtIndex
					INTEGER,
				topOltDhcpPortTypeIndex
					INTEGER,
				topOltDhcpSlotIndex
					INTEGER,
				topOltDhcpPortIndex
					INTEGER,
				topOltDhcpPortCascade
					INTEGER,
				topOltDhcpPortTrans
					INTEGER,
				topOltDhcpPortTrust
					INTEGER
			 }

--     1.3.6.1.4.1.32285.11.7.6.1.1
-- 1.3.6.1.4.1.32285.11.7.6.1.1
-- 1.3.6.1.4.1.32285.11.7.6.1.1
-- 1.3.6.1.4.1.32285.11.7.5.1.1
		-- 1.3.6.1.4.1.32285.11.7.5.1.1
		topOltDhcpPortProtIndex OBJECT-TYPE
			SYNTAX INTEGER
				{
				dhcp(1),
				pppoe(2)
				}
			MAX-ACCESS not-accessible
			STATUS current
			DESCRIPTION
				"Description."
			::= { topOltDhcpPortAttributeEntry 1 }

		
--     1.3.6.1.4.1.32285.11.7.6.1.2
-- 1.3.6.1.4.1.32285.11.7.6.1.2
-- 1.3.6.1.4.1.32285.11.7.6.1.2
-- 1.3.6.1.4.1.32285.11.7.5.1.2
		-- 1.3.6.1.4.1.32285.11.7.5.1.2
		topOltDhcpPortTypeIndex OBJECT-TYPE
			SYNTAX INTEGER
				{
				trunk(1),
				fe(2),
				ge(3),
				xe(4)
				}
			MAX-ACCESS not-accessible
			STATUS current
			DESCRIPTION
				"Description."
			::= { topOltDhcpPortAttributeEntry 2 }

		
--     1.3.6.1.4.1.32285.11.7.6.1.3
-- 1.3.6.1.4.1.32285.11.7.6.1.3
-- 1.3.6.1.4.1.32285.11.7.6.1.3
-- 1.3.6.1.4.1.32285.11.7.5.1.3
		-- 1.3.6.1.4.1.32285.11.7.5.1.3
		topOltDhcpSlotIndex OBJECT-TYPE
			SYNTAX INTEGER (0..255)
			MAX-ACCESS not-accessible
			STATUS current
			DESCRIPTION
				"Description."
			::= { topOltDhcpPortAttributeEntry 3 }

		
--     1.3.6.1.4.1.32285.11.7.6.1.4
-- 1.3.6.1.4.1.32285.11.7.6.1.4
-- 1.3.6.1.4.1.32285.11.7.6.1.4
-- 1.3.6.1.4.1.32285.11.7.5.1.4
		-- 1.3.6.1.4.1.32285.11.7.5.1.4
		topOltDhcpPortIndex OBJECT-TYPE
			SYNTAX INTEGER (0..255)
			MAX-ACCESS not-accessible
			STATUS current
			DESCRIPTION
				"Description."
			::= { topOltDhcpPortAttributeEntry 4 }

		
--     1.3.6.1.4.1.32285.11.7.6.1.5
-- 1.3.6.1.4.1.32285.11.7.6.1.5
-- 1.3.6.1.4.1.32285.11.7.6.1.5
-- 1.3.6.1.4.1.32285.11.7.5.1.5
		-- 1.3.6.1.4.1.32285.11.7.5.1.5
		topOltDhcpPortCascade OBJECT-TYPE
			SYNTAX INTEGER
				{
				true(1),
				false(2)
				}
			MAX-ACCESS read-write
			STATUS current
			DESCRIPTION
				"Description."
			DEFVAL { true }
			::= { topOltDhcpPortAttributeEntry 5 }

		
--     1.3.6.1.4.1.32285.11.7.6.1.5
-- 1.3.6.1.4.1.32285.11.7.6.1.5
-- 1.3.6.1.4.1.32285.11.7.6.1.5
-- 1.3.6.1.4.1.32285.11.7.5.1.6
		-- 1.3.6.1.4.1.32285.11.7.5.1.6
		topOltDhcpPortTrans OBJECT-TYPE
			SYNTAX INTEGER
				{
				transparent(1),
				captured(2)
				}
			MAX-ACCESS read-write
			STATUS current
			DESCRIPTION
				"Description."
			DEFVAL { captured }
			::= { topOltDhcpPortAttributeEntry 6 }

		
--     1.3.6.1.4.1.32285.11.7.6.1.5
-- 1.3.6.1.4.1.32285.11.7.6.1.5
-- 1.3.6.1.4.1.32285.11.7.6.1.5
-- 1.3.6.1.4.1.32285.11.7.5.1.7
		-- 1.3.6.1.4.1.32285.11.7.5.1.7
		topOltDhcpPortTrust OBJECT-TYPE
			SYNTAX INTEGER
				{
				true(1),
				false(2)
				}
			MAX-ACCESS read-write
			STATUS current
			DESCRIPTION
				"Description."
			DEFVAL { true }
			::= { topOltDhcpPortAttributeEntry 7 }

		
-- 1.3.6.1.4.1.32285.11.7.6
		-- 1.3.6.1.4.1.32285.11.7.6
		topOltDhcpStaticIpTable OBJECT-TYPE
			SYNTAX SEQUENCE OF TopOltDhcpStaticIpEntry
			MAX-ACCESS not-accessible
			STATUS current
			DESCRIPTION
				"Description."
			::= { topvisionDhcpTree 6 }

		
--     1.3.6.1.4.1.32285.11.7.8.1
-- 1.3.6.1.4.1.32285.11.7.8.1
-- 1.3.6.1.4.1.32285.11.7.8.1
-- 1.3.6.1.4.1.32285.11.7.6.1
		-- 1.3.6.1.4.1.32285.11.7.6.1
		topOltDhcpStaticIpEntry OBJECT-TYPE
			SYNTAX TopOltDhcpStaticIpEntry
			MAX-ACCESS not-accessible
			STATUS current
			DESCRIPTION
				"Description."
			INDEX { topOltDhcpStaticIpVrfNameIndex, topOltDhcpStaticIpIndex, topOltDhcpStaticIpMaskIndex }
			::= { topOltDhcpStaticIpTable 1 }

		
		TopOltDhcpStaticIpEntry ::=
			SEQUENCE { 
				topOltDhcpStaticIpVrfNameIndex
					OCTET STRING,
				topOltDhcpStaticIpIndex
					IpAddress,
				topOltDhcpStaticIpMaskIndex
					IpAddress,
				topOltDhcpStaticIpSlot
					INTEGER,
				topOltDhcpStaticIpPort
					INTEGER,
				topOltDhcpStaticIpOnu
					INTEGER,
				topOltDhcpStaticIpRowStatus
					RowStatus
			 }

--  1.3.6.1.4.1.32285.11.7.6.1.1
		-- 1.3.6.1.4.1.32285.11.7.6.1.1
		topOltDhcpStaticIpVrfNameIndex OBJECT-TYPE
			SYNTAX OCTET STRING (SIZE (1..32))
			MAX-ACCESS not-accessible
			STATUS current
			DESCRIPTION
				"Description."
			::= { topOltDhcpStaticIpEntry 1 }

		
--     1.3.6.1.4.1.32285.11.7.8.1.1
-- 1.3.6.1.4.1.32285.11.7.8.1.1
-- 1.3.6.1.4.1.32285.11.7.8.1.1
-- 1.3.6.1.4.1.32285.11.7.6.1.2
		-- 1.3.6.1.4.1.32285.11.7.6.1.2
		topOltDhcpStaticIpIndex OBJECT-TYPE
			SYNTAX IpAddress
			MAX-ACCESS not-accessible
			STATUS current
			DESCRIPTION
				"Description."
			::= { topOltDhcpStaticIpEntry 2 }

		
--  1.3.6.1.4.1.32285.11.7.6.1.3
		-- 1.3.6.1.4.1.32285.11.7.6.1.3
		topOltDhcpStaticIpMaskIndex OBJECT-TYPE
			SYNTAX IpAddress
			MAX-ACCESS not-accessible
			STATUS current
			DESCRIPTION
				"Description."
			::= { topOltDhcpStaticIpEntry 3 }

		
--     1.3.6.1.4.1.32285.11.7.8.1.2
-- 1.3.6.1.4.1.32285.11.7.8.1.2
-- 1.3.6.1.4.1.32285.11.7.8.1.2
-- 1.3.6.1.4.1.32285.11.7.6.1.4
		-- 1.3.6.1.4.1.32285.11.7.6.1.4
		topOltDhcpStaticIpSlot OBJECT-TYPE
			SYNTAX INTEGER
			MAX-ACCESS read-create
			STATUS current
			DESCRIPTION
				"Description."
			::= { topOltDhcpStaticIpEntry 4 }

		
--     1.3.6.1.4.1.32285.11.7.8.1.3
-- 1.3.6.1.4.1.32285.11.7.8.1.3
-- 1.3.6.1.4.1.32285.11.7.8.1.3
-- 1.3.6.1.4.1.32285.11.7.6.1.5
		-- 1.3.6.1.4.1.32285.11.7.6.1.5
		topOltDhcpStaticIpPort OBJECT-TYPE
			SYNTAX INTEGER
			MAX-ACCESS read-create
			STATUS current
			DESCRIPTION
				"Description."
			::= { topOltDhcpStaticIpEntry 5 }

		
--     1.3.6.1.4.1.32285.11.7.8.1.4
-- 1.3.6.1.4.1.32285.11.7.8.1.4
-- 1.3.6.1.4.1.32285.11.7.8.1.4
-- 1.3.6.1.4.1.32285.11.7.6.1.6
		-- 1.3.6.1.4.1.32285.11.7.6.1.6
		topOltDhcpStaticIpOnu OBJECT-TYPE
			SYNTAX INTEGER
			MAX-ACCESS read-create
			STATUS current
			DESCRIPTION
				"Description."
			::= { topOltDhcpStaticIpEntry 6 }

		
--     1.3.6.1.4.1.32285.11.7.8.1.5
-- 1.3.6.1.4.1.32285.11.7.8.1.5
-- 1.3.6.1.4.1.32285.11.7.8.1.5
-- 1.3.6.1.4.1.32285.11.7.6.1.7
		-- 1.3.6.1.4.1.32285.11.7.6.1.7
		topOltDhcpStaticIpRowStatus OBJECT-TYPE
			SYNTAX RowStatus
			MAX-ACCESS read-create
			STATUS current
			DESCRIPTION
				"Description."
			::= { topOltDhcpStaticIpEntry 7 }

		
-- 1.3.6.1.4.1.32285.11.7.7
		-- 1.3.6.1.4.1.32285.11.7.7
		topOltDhcpStatisticsObjects OBJECT IDENTIFIER ::= { topvisionDhcpTree 7 }

		
--     1.3.6.1.4.1.32285.11.7.9.1
-- 1.3.6.1.4.1.32285.11.7.9.1
-- 1.3.6.1.4.1.32285.11.7.9.1
-- 1.3.6.1.4.1.32285.11.7.7.1
		-- 1.3.6.1.4.1.32285.11.7.7.1
		topOltDhcpStatRDiscover OBJECT-TYPE
			SYNTAX Counter64
			MAX-ACCESS read-only
			STATUS current
			DESCRIPTION
				"Description."
			::= { topOltDhcpStatisticsObjects 1 }

		
--     1.3.6.1.4.1.32285.11.7.9.2
-- 1.3.6.1.4.1.32285.11.7.9.2
-- 1.3.6.1.4.1.32285.11.7.9.2
-- 1.3.6.1.4.1.32285.11.7.7.2
		-- 1.3.6.1.4.1.32285.11.7.7.2
		topOltDhcpStatRRequest OBJECT-TYPE
			SYNTAX Counter64
			MAX-ACCESS read-only
			STATUS current
			DESCRIPTION
				"Description."
			::= { topOltDhcpStatisticsObjects 2 }

		
--     1.3.6.1.4.1.32285.11.7.9.3
-- 1.3.6.1.4.1.32285.11.7.9.3
-- 1.3.6.1.4.1.32285.11.7.9.3
-- 1.3.6.1.4.1.32285.11.7.7.3
		-- 1.3.6.1.4.1.32285.11.7.7.3
		topOltDhcpStatROffer OBJECT-TYPE
			SYNTAX Counter64
			MAX-ACCESS read-only
			STATUS current
			DESCRIPTION
				"Description."
			::= { topOltDhcpStatisticsObjects 3 }

		
--     1.3.6.1.4.1.32285.11.7.9.4
-- 1.3.6.1.4.1.32285.11.7.9.4
-- 1.3.6.1.4.1.32285.11.7.9.4
-- 1.3.6.1.4.1.32285.11.7.7.4
		-- 1.3.6.1.4.1.32285.11.7.7.4
		topOltDhcpStatRAck OBJECT-TYPE
			SYNTAX Counter64
			MAX-ACCESS read-only
			STATUS current
			DESCRIPTION
				"Description."
			::= { topOltDhcpStatisticsObjects 4 }

		
--     1.3.6.1.4.1.32285.11.7.9.5
-- 1.3.6.1.4.1.32285.11.7.9.5
-- 1.3.6.1.4.1.32285.11.7.9.5
-- 1.3.6.1.4.1.32285.11.7.7.5
		-- 1.3.6.1.4.1.32285.11.7.7.5
		topOltDhcpStatROther OBJECT-TYPE
			SYNTAX Counter64
			MAX-ACCESS read-only
			STATUS current
			DESCRIPTION
				"Description."
			::= { topOltDhcpStatisticsObjects 5 }

		
--     1.3.6.1.4.1.32285.11.7.9.6
-- 1.3.6.1.4.1.32285.11.7.9.6
-- 1.3.6.1.4.1.32285.11.7.9.6
-- 1.3.6.1.4.1.32285.11.7.7.6
		-- 1.3.6.1.4.1.32285.11.7.7.6
		topOltDhcpStatDDiscover OBJECT-TYPE
			SYNTAX Counter64
			MAX-ACCESS read-only
			STATUS current
			DESCRIPTION
				"Description."
			::= { topOltDhcpStatisticsObjects 6 }

		
--     1.3.6.1.4.1.32285.11.7.9.7
-- 1.3.6.1.4.1.32285.11.7.9.7
-- 1.3.6.1.4.1.32285.11.7.9.7
-- 1.3.6.1.4.1.32285.11.7.7.7
		-- 1.3.6.1.4.1.32285.11.7.7.7
		topOltDhcpStatDRequest OBJECT-TYPE
			SYNTAX Counter64
			MAX-ACCESS read-only
			STATUS current
			DESCRIPTION
				"Description."
			::= { topOltDhcpStatisticsObjects 7 }

		
--     1.3.6.1.4.1.32285.11.7.9.8
-- 1.3.6.1.4.1.32285.11.7.9.8
-- 1.3.6.1.4.1.32285.11.7.9.8
-- 1.3.6.1.4.1.32285.11.7.7.8
		-- 1.3.6.1.4.1.32285.11.7.7.8
		topOltDhcpStatDOffer OBJECT-TYPE
			SYNTAX Counter64
			MAX-ACCESS read-only
			STATUS current
			DESCRIPTION
				"Description."
			::= { topOltDhcpStatisticsObjects 8 }

		
--     1.3.6.1.4.1.32285.11.7.9.9
-- 1.3.6.1.4.1.32285.11.7.9.9
-- 1.3.6.1.4.1.32285.11.7.9.9
-- 1.3.6.1.4.1.32285.11.7.7.9
		-- 1.3.6.1.4.1.32285.11.7.7.9
		topOltDhcpStatDAck OBJECT-TYPE
			SYNTAX Counter64
			MAX-ACCESS read-only
			STATUS current
			DESCRIPTION
				"Description."
			::= { topOltDhcpStatisticsObjects 9 }

		
--     1.3.6.1.4.1.32285.11.7.9.10
-- 1.3.6.1.4.1.32285.11.7.9.10
-- 1.3.6.1.4.1.32285.11.7.9.10
-- 1.3.6.1.4.1.32285.11.7.7.10
		-- 1.3.6.1.4.1.32285.11.7.7.10
		topOltDhcpStatDOther OBJECT-TYPE
			SYNTAX Counter64
			MAX-ACCESS read-only
			STATUS current
			DESCRIPTION
				"Description."
			::= { topOltDhcpStatisticsObjects 10 }

		
--     1.3.6.1.4.1.32285.11.7.9.11
-- 1.3.6.1.4.1.32285.11.7.9.11
-- 1.3.6.1.4.1.32285.11.7.9.11
-- 1.3.6.1.4.1.32285.11.7.7.11
		-- 1.3.6.1.4.1.32285.11.7.7.11
		topOltDhcpStatDFlood OBJECT-TYPE
			SYNTAX Counter64
			MAX-ACCESS read-only
			STATUS current
			DESCRIPTION
				"Description."
			::= { topOltDhcpStatisticsObjects 11 }

		
--     1.3.6.1.4.1.32285.11.7.9.12
-- 1.3.6.1.4.1.32285.11.7.9.12
-- 1.3.6.1.4.1.32285.11.7.9.12
-- 1.3.6.1.4.1.32285.11.7.7.12
		-- 1.3.6.1.4.1.32285.11.7.7.12
		topOltDhcpStatDUnknown OBJECT-TYPE
			SYNTAX Counter64
			MAX-ACCESS read-only
			STATUS current
			DESCRIPTION
				"Description."
			::= { topOltDhcpStatisticsObjects 12 }

		
--     1.3.6.1.4.1.32285.11.7.9.13
-- 1.3.6.1.4.1.32285.11.7.9.13
-- 1.3.6.1.4.1.32285.11.7.9.13
-- 1.3.6.1.4.1.32285.11.7.7.13
		-- 1.3.6.1.4.1.32285.11.7.7.13
		topOltDhcpStatDCongestion OBJECT-TYPE
			SYNTAX Counter64
			MAX-ACCESS read-only
			STATUS current
			DESCRIPTION
				"Description."
			::= { topOltDhcpStatisticsObjects 13 }

		
--     1.3.6.1.4.1.32285.11.7.9.14
-- 1.3.6.1.4.1.32285.11.7.9.14
-- 1.3.6.1.4.1.32285.11.7.9.14
-- 1.3.6.1.4.1.32285.11.7.7.14
		-- 1.3.6.1.4.1.32285.11.7.7.14
		topOltDhcpStatTDiscover OBJECT-TYPE
			SYNTAX Counter64
			MAX-ACCESS read-only
			STATUS current
			DESCRIPTION
				"Description."
			::= { topOltDhcpStatisticsObjects 14 }

		
--     1.3.6.1.4.1.32285.11.7.9.15
-- 1.3.6.1.4.1.32285.11.7.9.15
-- 1.3.6.1.4.1.32285.11.7.9.15
-- 1.3.6.1.4.1.32285.11.7.7.15
		-- 1.3.6.1.4.1.32285.11.7.7.15
		topOltDhcpStatTRequest OBJECT-TYPE
			SYNTAX Counter64
			MAX-ACCESS read-only
			STATUS current
			DESCRIPTION
				"Description."
			::= { topOltDhcpStatisticsObjects 15 }

		
--     1.3.6.1.4.1.32285.11.7.9.16
-- 1.3.6.1.4.1.32285.11.7.9.16
-- 1.3.6.1.4.1.32285.11.7.9.16
-- 1.3.6.1.4.1.32285.11.7.7.16
		-- 1.3.6.1.4.1.32285.11.7.7.16
		topOltDhcpStatTOffer OBJECT-TYPE
			SYNTAX Counter64
			MAX-ACCESS read-only
			STATUS current
			DESCRIPTION
				"Description."
			::= { topOltDhcpStatisticsObjects 16 }

		
--     1.3.6.1.4.1.32285.11.7.9.17
-- 1.3.6.1.4.1.32285.11.7.9.17
-- 1.3.6.1.4.1.32285.11.7.9.17
-- 1.3.6.1.4.1.32285.11.7.7.17
		-- 1.3.6.1.4.1.32285.11.7.7.17
		topOltDhcpStatTAck OBJECT-TYPE
			SYNTAX Counter64
			MAX-ACCESS read-only
			STATUS current
			DESCRIPTION
				"Description."
			::= { topOltDhcpStatisticsObjects 17 }

		
--     1.3.6.1.4.1.32285.11.7.9.18
-- 1.3.6.1.4.1.32285.11.7.9.18
-- 1.3.6.1.4.1.32285.11.7.9.18
-- 1.3.6.1.4.1.32285.11.7.7.18
		-- 1.3.6.1.4.1.32285.11.7.7.18
		topOltDhcpStatTOther OBJECT-TYPE
			SYNTAX Counter64
			MAX-ACCESS read-only
			STATUS current
			DESCRIPTION
				"Description."
			::= { topOltDhcpStatisticsObjects 18 }

		
--     1.3.6.1.4.1.32285.11.7.9.19
-- 1.3.6.1.4.1.32285.11.7.9.19
-- 1.3.6.1.4.1.32285.11.7.9.19
-- 1.3.6.1.4.1.32285.11.7.7.19
		-- 1.3.6.1.4.1.32285.11.7.7.19
		topOltDhcpStatStatusAndAction OBJECT-TYPE
			SYNTAX INTEGER
				{
				none(1),
				clean(2)
				}
			MAX-ACCESS read-write
			STATUS current
			DESCRIPTION
				"Description."
			::= { topOltDhcpStatisticsObjects 19 }

		
-- 1.3.6.1.4.1.32285.11.7.8
		-- 1.3.6.1.4.1.32285.11.7.8
		topOltDhcpCpeInfoTable OBJECT-TYPE
			SYNTAX SEQUENCE OF TopOltDhcpCpeInfoEntry
			MAX-ACCESS not-accessible
			STATUS current
			DESCRIPTION
				"Description."
			::= { topvisionDhcpTree 8 }

		
--     1.3.6.1.4.1.32285.11.7.10.1
-- 1.3.6.1.4.1.32285.11.7.10.1
-- 1.3.6.1.4.1.32285.11.7.10.1
-- 1.3.6.1.4.1.32285.11.7.8.1
		-- 1.3.6.1.4.1.32285.11.7.8.1
		topOltDhcpCpeInfoEntry OBJECT-TYPE
			SYNTAX TopOltDhcpCpeInfoEntry
			MAX-ACCESS not-accessible
			STATUS current
			DESCRIPTION
				"Description."
			INDEX { topOltDhcpCpeVrfNameIndex, topOltDhcpCpeIpIndex }
			::= { topOltDhcpCpeInfoTable 1 }

		
		TopOltDhcpCpeInfoEntry ::=
			SEQUENCE { 
				topOltDhcpCpeVrfNameIndex
					OCTET STRING,
				topOltDhcpCpeIpIndex
					IpAddress,
				topOltDhcpCpeMac
					MacAddress,
				topOltDhcpCpeVlan
					INTEGER,
				topOltDhcpCpePortType
					INTEGER,
				topOltDhcpCpeSlot
					INTEGER,
				topOltDhcpCpePort
					INTEGER,
				topOltDhcpCpeOnu
					INTEGER,
				topOltDhcpCpeRemainingTime
					INTEGER
			 }

--     1.3.6.1.4.1.32285.11.7.10.1.1
-- 1.3.6.1.4.1.32285.11.7.10.1.1
-- 1.3.6.1.4.1.32285.11.7.10.1.1
-- 1.3.6.1.4.1.32285.11.7.8.1.1
		-- 1.3.6.1.4.1.32285.11.7.8.1.1
		topOltDhcpCpeVrfNameIndex OBJECT-TYPE
			SYNTAX OCTET STRING (SIZE (1..32))
			MAX-ACCESS not-accessible
			STATUS current
			DESCRIPTION
				"Description."
			::= { topOltDhcpCpeInfoEntry 1 }

		
--     1.3.6.1.4.1.32285.11.7.10.1.2
-- 1.3.6.1.4.1.32285.11.7.10.1.2
-- 1.3.6.1.4.1.32285.11.7.10.1.2
-- 1.3.6.1.4.1.32285.11.7.8.1.2
		-- 1.3.6.1.4.1.32285.11.7.8.1.2
		topOltDhcpCpeIpIndex OBJECT-TYPE
			SYNTAX IpAddress
			MAX-ACCESS not-accessible
			STATUS current
			DESCRIPTION
				"Description."
			::= { topOltDhcpCpeInfoEntry 2 }

		
--     1.3.6.1.4.1.32285.11.7.10.1.3
-- 1.3.6.1.4.1.32285.11.7.10.1.3
-- 1.3.6.1.4.1.32285.11.7.10.1.3
-- 1.3.6.1.4.1.32285.11.7.8.1.3
		-- 1.3.6.1.4.1.32285.11.7.8.1.3
		topOltDhcpCpeMac OBJECT-TYPE
			SYNTAX MacAddress
			MAX-ACCESS read-only
			STATUS current
			DESCRIPTION
				"Description."
			::= { topOltDhcpCpeInfoEntry 3 }

		
--     1.3.6.1.4.1.32285.11.7.10.1.4
-- 1.3.6.1.4.1.32285.11.7.10.1.4
-- 1.3.6.1.4.1.32285.11.7.10.1.4
-- 1.3.6.1.4.1.32285.11.7.8.1.4
		-- 1.3.6.1.4.1.32285.11.7.8.1.4
		topOltDhcpCpeVlan OBJECT-TYPE
			SYNTAX INTEGER
			MAX-ACCESS read-only
			STATUS current
			DESCRIPTION
				"Description."
			::= { topOltDhcpCpeInfoEntry 4 }

		
		-- 1.3.6.1.4.1.32285.11.7.8.1.5
		topOltDhcpCpePortType OBJECT-TYPE
			SYNTAX INTEGER
				{
				fe(2),
				ge(3),
				xe(4),
				ethagg(9),
				onu(10)
				}
			MAX-ACCESS read-only
			STATUS current
			DESCRIPTION
				"Description."
			::= { topOltDhcpCpeInfoEntry 5 }

		
--     1.3.6.1.4.1.32285.11.7.10.1.5
-- 1.3.6.1.4.1.32285.11.7.10.1.5
-- 1.3.6.1.4.1.32285.11.7.10.1.5
-- 1.3.6.1.4.1.32285.11.7.8.1.5
		-- 1.3.6.1.4.1.32285.11.7.8.1.6
		topOltDhcpCpeSlot OBJECT-TYPE
			SYNTAX INTEGER
			MAX-ACCESS read-only
			STATUS current
			DESCRIPTION
				"Description."
			::= { topOltDhcpCpeInfoEntry 6 }

		
--     1.3.6.1.4.1.32285.11.7.10.1.6
-- 1.3.6.1.4.1.32285.11.7.10.1.6
-- 1.3.6.1.4.1.32285.11.7.10.1.6
-- 1.3.6.1.4.1.32285.11.7.8.1.6
		-- 1.3.6.1.4.1.32285.11.7.8.1.7
		topOltDhcpCpePort OBJECT-TYPE
			SYNTAX INTEGER
			MAX-ACCESS read-only
			STATUS current
			DESCRIPTION
				"Description."
			::= { topOltDhcpCpeInfoEntry 7 }

		
--     1.3.6.1.4.1.32285.11.7.10.1.7
-- 1.3.6.1.4.1.32285.11.7.10.1.7
-- 1.3.6.1.4.1.32285.11.7.10.1.7
-- 1.3.6.1.4.1.32285.11.7.8.1.7
		-- 1.3.6.1.4.1.32285.11.7.8.1.8
		topOltDhcpCpeOnu OBJECT-TYPE
			SYNTAX INTEGER
			MAX-ACCESS read-only
			STATUS current
			DESCRIPTION
				"Description."
			::= { topOltDhcpCpeInfoEntry 8 }

		
		-- 1.3.6.1.4.1.32285.11.7.8.1.9
		topOltDhcpCpeRemainingTime OBJECT-TYPE
			SYNTAX INTEGER
			UNITS "second"
			MAX-ACCESS read-only
			STATUS current
			DESCRIPTION
				"Description."
			::= { topOltDhcpCpeInfoEntry 9 }

		
		-- 1.3.6.1.4.1.32285.11.7.9
		topOltPppoeStatisticsObjects OBJECT IDENTIFIER ::= { topvisionDhcpTree 9 }

		
		-- 1.3.6.1.4.1.32285.11.7.9.1
		topOltPppoeStatReceive OBJECT-TYPE
			SYNTAX Counter64
			MAX-ACCESS read-only
			STATUS current
			DESCRIPTION
				"Description."
			::= { topOltPppoeStatisticsObjects 1 }

		
		-- 1.3.6.1.4.1.32285.11.7.9.2
		topOltPppoeStatDrop OBJECT-TYPE
			SYNTAX Counter64
			MAX-ACCESS read-only
			STATUS current
			DESCRIPTION
				"Description."
			::= { topOltPppoeStatisticsObjects 2 }

		
		-- 1.3.6.1.4.1.32285.11.7.9.3
		topOltPppoeStatTransmit OBJECT-TYPE
			SYNTAX Counter64
			MAX-ACCESS read-only
			STATUS current
			DESCRIPTION
				"Description."
			::= { topOltPppoeStatisticsObjects 3 }

		
		-- 1.3.6.1.4.1.32285.11.7.9.4
		topOltPppoeStatStatusAndAction OBJECT-TYPE
			SYNTAX INTEGER
				{
				none(1),
				clean(2)
				}
			MAX-ACCESS read-write
			STATUS current
			DESCRIPTION
				"Description."
			::= { topOltPppoeStatisticsObjects 4 }

		
	
	END

--
-- SUMA-DHCP-MIB.my
--
