--
-- NSCRTV-EPONEOC-GPON-UNI-MIB.mib
-- MIB generated by MG-SOFT Visual MIB Builder Version 4.0 Build 349
-- Friday, September 30, 2016 at 09:45:40
--

	NSCRTV-EPONEOC-GPON-UNI-MIB DEFINITIONS ::= BEGIN
 
		IMPORTS
			BridgeId, Timeout			
				FROM BRIDGE-MIB			
			enterprises, TimeTicks, IpAddress, Unsigned32, Gauge32, 
			Counter32, Counter64, OBJECT-TYPE, OBJECT-IDENTITY, 
			NOTIFICATION-TYPE			
				FROM SNMPv2-SMI			
			DateAndTime, TruthValue, RowStatus, MacAddress, DisplayString, 
			TimeStamp, TEXTUAL-CONVENTION			
				FROM SNMPv2-TC;

--
-- Textual conventions
--
		GponCardIndex ::= TEXTUAL-CONVENTION
			STATUS current
			DESCRIPTION 
				"     
				For easy presenting the chassis view by NMS, bCardIndex shall be formatted
				in a following manner:                        
				    Four bytes of INTEGER, from the most significant byte to the least significant
				    bytes
				        -----------------------------------------------------------------------------
				Reserved byte Reserved byte   Reserved byte Sub-slot 2-bit Main-slot 6-bit        
				Notes:
				-----         
				1. Reserved bytes shall be set to 0.        
				2. The main-slot shall be started from 1, and shall be in a consecutive manner,
				   for all slots, including service slots, control slots, switch slots, power
				slots,FAN slots, etc.For example, 1, 2, 3          
				3. The sub-slot shall be started from 1, and shall be in a consecutive manner.
				   For example, 1, 2. If no sub-slot concept of a main-slot, set to 0.        
				4. For fixed device, if no slot concept, NE shall set both main-slot and sub-slot
				to 0, to indicate this is meaningless. For modulized device, they MUST not be
				set to 0.This definition shall applied to both OLT and ONU.        
				5. For trunk, since there is no slot concept, set main-slot to all-1 and sub-slot
				to 0. This definition shall applied to both OLT and ONU.
				
				For example, 
				0x00 00 00 0A, represents main-slot 10, no sub-slot
				0x00 00 00 42, represents main-slot 2, sub-slot 1
				0x00 00 00 3F, represents a trunk
				"
			SYNTAX Unsigned32

		GponPortIndex ::= TEXTUAL-CONVENTION
			STATUS current
			DESCRIPTION 
				"       
				The device port number shall start from 1. Nunber 0 had specific meaning, stands
				for portIndex is meaningless, for the situation defined.
				"
			SYNTAX INTEGER (0..255)

		GponDeviceIndex ::= TEXTUAL-CONVENTION
			STATUS current
			DESCRIPTION 
				"
				Gpon olt/onu
				ONU ID       
				Olt device-8bit OLT Card-8bit Pon port-8bit OnuNUM-8bit        
				Note: 
				----        
				1. OLT device must not be 0.        
				2. Card here shall confirm the last byte definition of GponCardIndex
				   to indicate the main-slot and sub-slot index.         
				3. Pon port must not be 0.
				4. The useful ONU logical ID MUST never be set to 0, where NUM of 0 has
				   another meaning, to indicate that the ONU logical ID is meaningless,
				   or said to not applied.
				        
				Usage guide:
				-----------        
				This TC could be used for OLT SNI, OLT PON port, OLT ONU ID
				ONU UNI, OLT device, trunk.         
				If the refered MIB object does not have clear definition,
				refer to the following:
				Applied Obj  - Descriptions of Index
				------------------------------------------------------------------
				OLT Pon Port - OnuNum shall be set to 0,
				OLT SNI    - Same as OLT Pon Port         
				OLT onu ID   - Set OnuNUM to corresponding ONU logical ID         
				ONU UNI    - Same as OLT ONU ID
				OLT device   - Set card, pon port and OnuNUM to 0
				Trunk    - Card to 0x3F, pon port to trunk ID, OnuNUM to 0
				         Olt device to corresponding ONU device       
				"
			SYNTAX Unsigned32


		GponStats15MinRecordType ::= TEXTUAL-CONVENTION
			STATUS current
			DESCRIPTION 
				" "
			SYNTAX INTEGER (0..96)

		GponStats24HourRecordType ::= TEXTUAL-CONVENTION
			STATUS current
			DESCRIPTION 
				" "
			SYNTAX INTEGER (0..30)



--
-- Node definitions
--
	
		-- 1.3.6.1.4.1.17409
		nscrtvRoot OBJECT IDENTIFIER ::= { enterprises 17409 }

		
		-- 1.3.6.1.4.1.17409.2
		nscrtvFTTxTree OBJECT IDENTIFIER ::= { nscrtvRoot 2 }

		
--      DESCRIPTION
		-- 1.3.6.1.4.1.17409.2.8
		gponTree OBJECT IDENTIFIER ::= { nscrtvFTTxTree 8 }
		
		
		
-- ------------------------------------------------------------------------------
-- uniObjects(1.3.6.1.4.1.17409.2.8.5)
-- ------------------------------------------------------------------------------
        -- 1.3.6.1.4.1.17409.2.8.5
		uniObjects OBJECT IDENTIFIER ::= { gponTree 5 }

		
		-- 1.3.6.1.4.1.17409.2.8.5.1
		ethAttributeTable OBJECT-TYPE
			SYNTAX SEQUENCE OF EthAttributeEntry
			MAX-ACCESS not-accessible
			STATUS current
			DESCRIPTION
				"A list of uniAttributeTable entries."
			::= { uniObjects 1 }

		
		-- 1.3.6.1.4.1.17409.2.8.5.1.1
		ethAttributeEntry OBJECT-TYPE
			SYNTAX EthAttributeEntry
			MAX-ACCESS not-accessible
			STATUS current
			DESCRIPTION
				"The uniAttributeEntry Information"
			INDEX { ethAttributeDeviceIndex, ethAttributeCardIndex, ethAttributePortIndex }
			::= { ethAttributeTable 1 }

		
		EthAttributeEntry ::=
			SEQUENCE { 
				ethAttributeDeviceIndex
					GponDeviceIndex,
				ethAttributeCardIndex
					GponCardIndex,
				ethAttributePortIndex
					GponPortIndex,
				ethAdminStatus
					INTEGER,
				ethOperationStatus
					INTEGER,
				ethDuplexRate
					INTEGER,
				ethPerfStats15minuteEnable
					TruthValue,
				ethPerfStats24hourEnable
					TruthValue
			 }

		-- 1.3.6.1.4.1.17409.2.8.5.1.1.1
		ethAttributeDeviceIndex OBJECT-TYPE
			SYNTAX GponDeviceIndex
			MAX-ACCESS not-accessible
			STATUS current
			DESCRIPTION
				"Device Index
				
				For OLT, set to corresponding ONU ID
				For ONU, set to 0
				"
			::= { ethAttributeEntry 1 }

		
		-- 1.3.6.1.4.1.17409.2.8.5.1.1.2
		ethAttributeCardIndex OBJECT-TYPE
			SYNTAX GponCardIndex
			MAX-ACCESS not-accessible
			STATUS current
			DESCRIPTION
				"Card Index            
				The value of this cardIndex depends on onuType.            
				fixed(1)        - set to 0, to indicate slot num is meaningless.
				chassisBased(2) - MUST NOT be zero            
				"
			::= { ethAttributeEntry 2 }

		
		-- 1.3.6.1.4.1.17409.2.8.5.1.1.3
		ethAttributePortIndex OBJECT-TYPE
			SYNTAX GponPortIndex
			MAX-ACCESS not-accessible
			STATUS current
			DESCRIPTION
				"Port Index"
			::= { ethAttributeEntry 3 }

		
		-- 1.3.6.1.4.1.17409.2.8.5.1.1.4
		ethAdminStatus OBJECT-TYPE
			SYNTAX INTEGER
				{
				up(1),
				down(2)
				}
			MAX-ACCESS read-write
			STATUS current
			DESCRIPTION
				"Admin Status"
			::= { ethAttributeEntry 4 }

		
		-- 1.3.6.1.4.1.17409.2.8.5.1.1.5
		ethOperationStatus OBJECT-TYPE
			SYNTAX INTEGER
				{
				up(1),
				down(2)
				}
			MAX-ACCESS read-only
			STATUS current
			DESCRIPTION
				"Operation Status"
			::= { ethAttributeEntry 5 }

		
		-- 1.3.6.1.4.1.17409.2.8.5.1.1.6
		ethDuplexRate OBJECT-TYPE
			SYNTAX INTEGER
			MAX-ACCESS read-write
			STATUS current
			DESCRIPTION			" "
			::= { ethAttributeEntry 6 }

		
		-- 1.3.6.1.4.1.17409.2.8.5.1.1.7
		ethPerfStats15minuteEnable OBJECT-TYPE
			SYNTAX TruthValue
			MAX-ACCESS read-write
			STATUS current
			DESCRIPTION
				""
			::= { ethAttributeEntry 7 }


			-- 1.3.6.1.4.1.17409.2.8.5.1.1.8
		ethPerfStats24hourEnable OBJECT-TYPE
			SYNTAX TruthValue
			MAX-ACCESS read-write
			STATUS current
			DESCRIPTION			" "
			::= { ethAttributeEntry 8 }
		
	
	END

--
-- NSCRTV-EPONEOC-GPON-UNI-MIB.my
--
