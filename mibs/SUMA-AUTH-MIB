--
-- SUMA-AUTH-MIB.my
-- MIB generated by MG-SOFT Visual MIB Builder Version 4.0 Build 349
-- Wednesday, June 14, 2017 at 16:53:48
--

--  SUMA-AUTH-MIB.mib
-- MIB generated by MG-SOFT Visual MIB Builder Version 4.0 Build 349
-- Wednesday, October 19, 2011 at 15:54:31
-- 

	SUMA-AUTH-MIB DEFINITIONS ::= BEGIN
 
		IMPORTS
			enterprises, TimeTicks, IpAddress, Unsigned32, Counter32, 
			Counter64, OBJECT-TYPE, OBJECT-IDENTITY			
				FROM SNMPv2-SMI			
			MacAddress, DisplayString, RowStatus, DateAndTime, TEXTUAL-CONVENTION			
				FROM SNMPv2-TC;
	
	
--
-- Textual conventions
--
	
		TopEponAlarmCode ::= TEXTUAL-CONVENTION
			STATUS current
			DESCRIPTION 
				"Alarm codes, uniquely indentifies each kind of alarm.
				Refer to EPON alarm definition table"
			SYNTAX INTEGER (1..65535)

		TopEPonSlotIndex ::= TEXTUAL-CONVENTION
			STATUS current
			DESCRIPTION 
				"This represents the slot number in the epon shelf."
			SYNTAX INTEGER (1..18)

		TopEPonPonIndex ::= TEXTUAL-CONVENTION
			STATUS current
			DESCRIPTION 
				"This represents the PON number in the epon board."
			SYNTAX INTEGER (1..8)

		EponDeviceIndex ::= TEXTUAL-CONVENTION
			STATUS current
			DESCRIPTION 
				"From MSB on, OLT slot index-8bits, PON/SNI port-8bits, 
				OnuNUM-8bits and UNI port-8bits.
				OLT PON/SNI Port - OnuNum and UNI port shall be set to 0."
			SYNTAX Unsigned32

		TopEPonOnuAuthNum ::= TEXTUAL-CONVENTION
			STATUS current
			DESCRIPTION 
				"This represents the ONU auth number in the epon board."
			SYNTAX INTEGER (1..128)

		TopEPonUniPortIndex ::= TEXTUAL-CONVENTION
			STATUS current
			DESCRIPTION 
				"This represents the ONU uni number in the epon board."
			SYNTAX INTEGER (1..32)

		TopEponStatsThresholdType ::= TEXTUAL-CONVENTION
			STATUS current
			DESCRIPTION 
				"1- InOctets
				2 InPkts
				3 InBroadcastPkts
				4 InMulticastPkts
				5 InPkts64Octets
				6 InPkts65to127Octets
				7 InPkts128to255Octets
				8 InPkts256to511Octets
				9 InPkts512to1023Octets
				10 InPkts1024to1518Octets
				11 InPkts1519to1522Octets
				12 InUndersizePkts
				13 InOversizePkts
				14 InFragments
				15 InMpcpFrames
				16 InMpcpOctets
				17 InOAMFrames
				18 InOAMOctets
				19 InCRCErrorPkts
				20 InDropEvents
				21 InJabbers
				22 InCollision
				23 OutOctets
				24 OutPkts
				25 OutBroadcastPkts
				26 OutMulticastPkts
				27 OutPkts64Octets
				28 OutPkts65to127Octets
				29 OutPkts128to255Octets
				30 OutPkts256to511Octets
				31 OutPkts512to1023Octets
				32 OutPkts1024to1518Octets
				33 OutPkts1519o1522Octets
				34 OutUndersizePkts
				35 OutOversizePkts
				36 OutFragments
				37 OutMpcpFrames
				38 OutMpcpOctets
				39 OutOAMFrames
				40 OutOAMOctets
				41 OutCRCErrorPkts
				42 OutDropEvents
				43 OutJabbers
				44 OutCollision
				50 Temperature
				Note:
				----------------------------------------------------------------
				1. For 50 Temperature, this parameter shall only applied to
				a. Slot level, for each service/switch/management card, for
				chassis-based system.
				b. Node-level, for fixed box.
				2. For 50 Temperature, shall be applied to both OLT and ONU
				3. For 50 Temperature, since no 15-min performance data collection
				are required, system shall ensure the temperature polling interval
				no less than 5 seconds. The alarm shall be only generated when the
				threshold is acrossed for three continuous intervals, and shall be
				cleared, when the threshold is not accrossed any more, for three
				continous intervals.
				"
			SYNTAX INTEGER (1..1024)

		TopEPonSniIndex ::= TEXTUAL-CONVENTION
			STATUS current
			DESCRIPTION 
				"This represents the sni port number in the uplink board."
			SYNTAX INTEGER (1..8)

	
--
-- Node definitions
--
	
--  Node definitions
-- 
-- 1.3.6.1.4.1.32285
		-- 1.3.6.1.4.1.32285
		sumaRoot OBJECT IDENTIFIER ::= { enterprises 32285 }

		
--  1.3.6.1.4.1.32285.11
		-- 1.3.6.1.4.1.32285.11
		topvisionRoot OBJECT IDENTIFIER ::= { sumaRoot 11 }

		-- 1.3.6.1.4.1.32285.11.2
		topvisionEponEocTree OBJECT IDENTIFIER ::= { topvisionRoot 2 }
		
		-- 1.3.6.1.4.1.32285.11.2.3
		topvisionEponTree OBJECT IDENTIFIER ::= { topvisionEponEocTree 3 }
		
		-- 1.3.6.1.4.1.32285.11.2.3.4
		topOnuObjects OBJECT IDENTIFIER ::= { topvisionEponTree 4 }
		
		-- 1.3.6.1.4.1.32285.11.2.3.4.2
		topOnuAuthMgmt OBJECT IDENTIFIER ::= { topOnuObjects 2 }
		
				-- 1.3.6.1.4.1.32285.11.2.3.4.2.4
		topOnuAuthenticationPreConfigTable OBJECT-TYPE
			SYNTAX SEQUENCE OF TopOnuAuthenticationPreConfigEntry
			MAX-ACCESS not-accessible
			STATUS current
			DESCRIPTION
				"Description."
			::= { topOnuAuthMgmt 4 }

		
		-- 1.3.6.1.4.1.32285.11.2.3.4.2.4.1
		topOnuAuthenticationPreConfigEntry OBJECT-TYPE
			SYNTAX TopOnuAuthenticationPreConfigEntry
			MAX-ACCESS not-accessible
			STATUS current
			DESCRIPTION
				"Description."
			INDEX { topOnuAuthenOnuId }
			::= { topOnuAuthenticationPreConfigTable 1 }

		
		TopOnuAuthenticationPreConfigEntry ::=
			SEQUENCE { 
				topOnuAuthenOnuId
					EponDeviceIndex,
				topOnuAuthenMacAddress
					OCTET STRING,
				topOnuAuthenAction
					INTEGER,
				topOnuAuthenRowStatus
					INTEGER
			 }

		-- 1.3.6.1.4.1.32285.11.2.3.4.2.4.1.1
		topOnuAuthenOnuId OBJECT-TYPE
			SYNTAX EponDeviceIndex
			MAX-ACCESS not-accessible
			STATUS current
			DESCRIPTION
				"Description."
			::= { topOnuAuthenticationPreConfigEntry 1 }

		
		-- 1.3.6.1.4.1.32285.11.2.3.4.2.4.1.2
		topOnuAuthenMacAddress OBJECT-TYPE
			SYNTAX OCTET STRING
			MAX-ACCESS read-create
			STATUS current
			DESCRIPTION
				"Description."
			::= { topOnuAuthenticationPreConfigEntry 2 }

		
		-- 1.3.6.1.4.1.32285.11.2.3.4.2.4.1.3
		topOnuAuthenAction OBJECT-TYPE
			SYNTAX INTEGER
			MAX-ACCESS read-create
			STATUS current
			DESCRIPTION
				"Description."
			::= { topOnuAuthenticationPreConfigEntry 3 }

		
		-- 1.3.6.1.4.1.32285.11.2.3.4.2.4.1.4
		topOnuAuthenRowStatus OBJECT-TYPE
			SYNTAX INTEGER
			MAX-ACCESS read-create
			STATUS current
			DESCRIPTION
				"Description."
			::= { topOnuAuthenticationPreConfigEntry 4 }

		
		-- 1.3.6.1.4.1.32285.11.2.3.4.2.5
		topOnuAuthenticationBlockTable OBJECT-TYPE
			SYNTAX SEQUENCE OF TopOnuAuthenticationBlockEntry
			MAX-ACCESS not-accessible
			STATUS current
			DESCRIPTION
				"Description."
			::= { topOnuAuthMgmt 5 }

		
		-- 1.3.6.1.4.1.32285.11.2.3.4.2.5.1
		topOnuAuthenticationBlockEntry OBJECT-TYPE
			SYNTAX TopOnuAuthenticationBlockEntry
			MAX-ACCESS not-accessible
			STATUS current
			DESCRIPTION
				"Description."
			INDEX { topOnuAuthenBlockOnuId }
			::= { topOnuAuthenticationBlockTable 1 }

		
		TopOnuAuthenticationBlockEntry ::=
			SEQUENCE { 
				topOnuAuthenBlockOnuId
					EponDeviceIndex,
				topOnuAuthenBlockMacAddress
					OCTET STRING,
				topAuthenTime
					DateAndTime
			 }

		-- 1.3.6.1.4.1.32285.11.2.3.4.2.5.1.1
		topOnuAuthenBlockOnuId OBJECT-TYPE
			SYNTAX EponDeviceIndex
			MAX-ACCESS not-accessible
			STATUS current
			DESCRIPTION
				"Description."
			::= { topOnuAuthenticationBlockEntry 1 }

		
		-- 1.3.6.1.4.1.32285.11.2.3.4.2.5.1.2
		topOnuAuthenBlockMacAddress OBJECT-TYPE
			SYNTAX OCTET STRING
			MAX-ACCESS read-only
			STATUS current
			DESCRIPTION
				"Description."
			::= { topOnuAuthenticationBlockEntry 2 }

		
		-- 1.3.6.1.4.1.32285.11.2.3.4.2.5.1.3
		topAuthenTime OBJECT-TYPE
			SYNTAX DateAndTime
			MAX-ACCESS read-only
			STATUS current
			DESCRIPTION
				"Description."
			::= { topOnuAuthenticationBlockEntry 3 }

	END

--
-- SUMA-AUTH-MIB.my
--
